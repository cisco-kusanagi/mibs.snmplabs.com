-- Based on R2 Voice Inter-Working Functions Specification (Rev 1.0, dated 5/14/97).
-- For Release 2.0, this MIB file, mcm2vnet.mib, shall replace existing Voice MIB 
-- file, mcmvoice.mib (Rlse 1.1).
-- 
-- MIB Revision : 1.0 dated 6-2-97
-- Change Desc. : Initial submittal - R. Carmona. 
-- 
-- MIB Revision : 1.1 dated 7-3-97
-- Change Desc. : Add VNET Traps - A. Llanes. 
-- 
-- MIB Revision : 1.2 dated 10-8-97
-- Change Desc. : Replaced MPA with 4400, and other minor changes - B. Jafari. 
-- 
-- MIB Revision : 1.3 dated 10-21-97
-- Change Desc. : Added a new signaling format type, and a new object the 
--                'mcmVNETChStatusRemoteChNodeName' - B. Jafari.
--
-- MIB Revision : 1.4 dated 10-24-97
-- Change Desc. : Added a new object to the voice switching profile
--                configuration table (operational/configuration) - B. Jafari.
--
-- MIB Revision : 1.5 dated 10-28-97
-- Change Desc. : Introduced 'lim' (logical interface module) to reflect 
--                a card's former 'slot' notation; e.g. 'slotB' is 
--                now regarded as 'limB' - B. Jafari.
--
-- MIB Revision : 1.6 dated 12-9-97
-- Change Desc. : Added two new DVM signaling protocols to
--                (mcm/nvm)VNETProfileCfgDVMSigFormat.           - S. Gaur
--
--
-- MIB Revision : 1.7 dated 1-5-98
-- Change Desc. : Reorganized the (mcm/nvm)VNETChCfgLimID, mcmVNETChStatusLimID,
--                mcmVNETChStatsLimID and mcmVNETChControlLimID enumerations to 
--                enforce better guidelines for LIM ordering on the Passport 4400. 
--                Changed all object names and descriptions that had card to LIM.
--                                                               - S. Gaur
--
-- *** RELEASE 3.0 ***
-- MIB Revision : 1.8 dated 6-24-98
-- Change Desc. : Removed and/or replaced "4400" with 
--				  "access device" wherever possible.
--				  Removed counter reset enumerations
--				  from mcmVNETChControlActionCmd 
--				  and mcmVNETSysControlActionCmd. -A. Llanes
--
-- MIB Revision : 1.9 dated 7-07-98
-- Change Desc. : Reincorporated counter reset enumerations
--				  for mcmVNETChControlActionCmd 
--				  and mcmVNETSysControlActionCmd to 
--				  support backward compatibility of 
--				  releases prior to 3.0. -A. Llanes
--
--
-- MIB Revision : 2.0 dated 7-17-98
-- Change Desc. : Added (mcm/nvm)VNETProfileCfgBckGrndNoiseLevel objects 
--		  and   (mcm/nvm)VNETProfileCfgSilenceHngOvrTime objects.	
--                as per P.Palni(DSP).                   -S. Gaur
--
--
--
-- MIB Revision : 2.1 dated 7-21-98
-- Change Desc. : Added the voiceSysStatusGroup as well as 
--		         (mcm/nvm)VNETSwProfCfgOutCallMode objects,
--                       (mcm/nvm)VNETSwProfCfgAddServerSelect objects.	
--                Added enumeration nine to mcmVNETSysControlActionCmd.
--                Modified the HELP for (mcm/nvm)VNETIngressDigFilterIngressNum
--                 and (mcm/nvm)VNEEgressDigManipPhoneNum objects.
--                Modifications made to accomodate overlap dialing.    
--                                                                     -S. Gaur
--                                                                    
-- MIB Revision : 2.2 dated 8-18-98
-- Change Desc. : Added the (mcm/nvm)VNETSwProfCfgAutoCallType objects as
--                per John Morris for Hoot'n Holler functionality.
--                                                                 -S. Gaur
--
-- MIB Revision : 2.3 dated 1-26-98 (BRI merge to 3.1 8/13/98) - M. Gonzales
-- Change Desc. : Revisions made for Release 2.1. New objects
--                are added for the ISDN BRI voice card.
--                Added objects include: (mcm/nvm)VNETProfileCfgIdlePattern,
--                (mcm/nvm)VNETProfileCfgEcanFilterLen, 
--                (mcm/nvm)VNETProfileCfgEcanEr1Improvement, 
--                (mcm/nvm)VNETProfileCfgNoiseFloorOffset,
--                (mcm/nvm)VNETProfileCfgDtmfGenBurstLet and
--                (mcm/nvm)VNETProfileCfgDtmfRegenBurstLen. 
--                Other minor changes can be viewed in the ISDN-BRI card
--                MIB requirement document written by Amir Al-Karam.
--                                                                - S. Gaur
--
-- MIB Revision : 2.4 dated 9-11-98
-- Change Desc. : Removed enumerations three and four from
--                (mcm/nvm)VNETSwProfCfgAddServerSelect
--                                                        -S. Gaur
-- MIB Revision : 2.5 dated 9-21-98
-- Change Desc. : OIDs have been reorder in (mcm/nvm)VNETSwProfCfg Tables
--				  to maintain backward compatibility with R2.0.
--				  This OID reordering in R3.0 occurred due to the introduction of 
--				  (mcm/nvm)VNETSwProfCfgAutoCallType (Hoot-n-Holler functionality)
--				  in R2.0 and R3.0.
--                                                        -A. Llanes
-- MIB Revision : 2.6 dated 10-06-98
-- Change Desc. : The range was changed to an enumeration for 
--                mcmVNETProfileCfgEcanFilterLength and the defaults 
--                were modified for mcmVNETProfileCfgDtmfGenBurstLength and
--                mcmVNETProfileCfgDtmRegenBurstLength.
--                 
--                                                        -S. Gaur
-- MIB Revision : 2.7 dated 11-02-98
-- Change Desc. : The Severity Levels were added to the traps.
--							 -F. Kottab
--                                                        -S. Gaur
-- MIB Revision : 2.8 dated 01-22-99
-- Change Desc. : Updated the description text for mcm/nvm EgressDigManipString
--				  to indicate support of the character 'H'. The symbol 'H' is 
--				  used to trigger immediate dial handling by the PBX.  
--							 -A. Llanes 
--
-- *** RELEASE 3.1 ***
-- MIB Revision : 2.25 dated 01-22-99
-- Change Desc. : Added default value for mcmVNETSwProfCfgAutoCallType
--							 -M. Ly 
--

MICOM-4400-VOICE-NETWORK-MIB DEFINITIONS ::= BEGIN
	IMPORTS
		TRAP-TYPE
			FROM RFC-1215
		Counter, IpAddress
			FROM RFC1155-SMI
		OBJECT-TYPE
			FROM RFC-1212
		DisplayString
			FROM RFC1213-MIB
		mcmSysAsciiTimeOfDay
			FROM MICOM-SYS-MIB
		micom-oscar
			FROM MICOM-OSCAR-MIB;


-- group OBJECT IDENTIFIERs

	micom-2vnet			OBJECT IDENTIFIER ::= {micom-oscar 21}
	vnet-configuration 		OBJECT IDENTIFIER ::= { micom-2vnet 1}
	vnet-control	 		OBJECT IDENTIFIER ::= { micom-2vnet 2}
	vnet-status			OBJECT IDENTIFIER ::= { micom-2vnet 3}
	vnet-statistics 		OBJECT IDENTIFIER ::= { micom-2vnet 4}


-- *** CONFIGURATION groups/tables ***

-- Note: The following groups contain 2 related groups/tables for all configuration
--       functionality. 
--	 1) The Standard or Operational Parameters (Operational) provide the
--	 SNMP management interface with the access device operational modules.
--	 Objects defined for this interface begin with the 'mcm' prefix.
--	 2) The Configuration Parameters (Configuration) provide the SNMP 
--	 management interface with a stored access device configuration. 
--	 Objects defined for this interface begin with the 'nvm' prefix.
--	


--  Operational Parameter ("mcm") Groups/Tables


--  the VNET Voice Channel Configuration Table 
--  (Standard/Operational Parameters)

--  This table provides the VNET voice channel configuration parameters
--  for identifying a voice channel with its corresponding voice profile. (Operational)

mcmVNETChCfgTable OBJECT-TYPE
	SYNTAX  SEQUENCE OF McmVNETChCfgEntry
	ACCESS  not-accessible
	STATUS  mandatory
	DESCRIPTION
	  "NAME = ; 
	   DESC = The VNET Voice Channel Configuration table. \
		  (Operational);
	   HELP = ;
	   CAPABILITIES = NET_CFG, VPN_CFG;"
	::= { vnet-configuration 1 }

mcmVNETChCfgEntry OBJECT-TYPE
	SYNTAX  McmVNETChCfgEntry
	ACCESS  not-accessible
	STATUS  mandatory
	DESCRIPTION
	  "NAME = ; 
	   DESC = An entry in the VNET Voice Channel Configuration \
		  table. (Operational);
	   HELP = ;
	   CAPABILITIES = ;"
	INDEX   { mcmVNETChCfgLimID, mcmVNETChCfgChannelID }
	::= { mcmVNETChCfgTable 1 }

McmVNETChCfgEntry ::= SEQUENCE {
	mcmVNETChCfgLimID			INTEGER,
	mcmVNETChCfgChannelID			INTEGER,
	mcmVNETChCfgVoiceProfile		INTEGER,
	mcmVNETChCfgSwitchingProfile		INTEGER,
	mcmVNETChCfgInterfaceType		INTEGER
	}

mcmVNETChCfgLimID OBJECT-TYPE
	SYNTAX	INTEGER {
		lim1 (2),
		lim2 (3),
		lim3 (4),
		lim4 (5),
		limB (6),
		limC (7),
		limD (8),
		limE (9)
		}
	ACCESS  read-only
	STATUS  mandatory
	DESCRIPTION
	  "NAME = ;
	   DESC = The card lim (logical interface module) number of a \
		  particular voice channel.  Used as an index to the \
		  VNET Voice Channel Configuration table. (Operational);
	   HELP = ;
	   CAPABILITIES = ;"
	::= { mcmVNETChCfgEntry 1 }

mcmVNETChCfgChannelID OBJECT-TYPE
	SYNTAX	INTEGER (1..12)
	ACCESS  read-only
	STATUS  mandatory
	DESCRIPTION
  "NAME = ;
	   DESC = The position of the voice channel in the lim. \
		  Used as an index to the VNET Voice \
		  Channel Configuration table. (Operational);
	   HELP = ;
	   CAPABILITIES = ;"
	::= { mcmVNETChCfgEntry 2 }

mcmVNETChCfgVoiceProfile OBJECT-TYPE
	SYNTAX	INTEGER (1..32)
	ACCESS  read-write
	STATUS  mandatory
	DESCRIPTION
	  "NAME = ; 
	   DESC = The value of this object indicates the profile \
		  to be used to configure the specified voice \
		  channel. (Operational);
	   HELP = ;
	   CAPABILITIES = ;"
	DEFVAL { 1 }
	::= { mcmVNETChCfgEntry 3 }

mcmVNETChCfgSwitchingProfile OBJECT-TYPE
	SYNTAX	INTEGER (1..32)
	ACCESS  read-write
	STATUS  mandatory
	DESCRIPTION
	  "NAME = ; 
	   DESC = The value of this object indicates the profile \
		  to be used for a switching call. (Operational);
	   HELP = ;
	   CAPABILITIES = ;"
	DEFVAL { 1 }
	::= { mcmVNETChCfgEntry 4 }

mcmVNETChCfgInterfaceType OBJECT-TYPE
	SYNTAX	INTEGER {
		not-available (1),
		enhanced-loop-start-FXS (2),
		enhanced-EandM (3),
		enhanced-loop-start-FXO (4),
		low-cost-loop-start-FXS (5),
		low-cost-EandM (6),
		low-cost-loop-start-FXO (7),
		ground-start-FXS (8),
		ground-start-FXO (9),
		three-port (10),
		dvm (11),
		bri (12)
		}
	ACCESS  read-only
	STATUS  mandatory
	DESCRIPTION
	  "NAME = ; 
	   DESC = The value of this object indicates the interface \
		  type of the specified voice channel. (Operational);
	   HELP = Upon powerup, the interface type will not be \
		  available until the DSP software is loaded and its \
		  status is reported.;
	   CAPABILITIES = ;"
	::= { mcmVNETChCfgEntry 5 }


--  the VNET Voice Profile Configuration Table 
--  (Standard/Operational Parameters)

--  This table provides the VNET voice profile configuration parameters.
--  This table is used to configure a profile of voice channel configuration
--  characteristics; of which, a subset may be used for a particular voice
--  channel (of a specific interface type) to define its configuration. (Operational)

mcmVNETProfileCfgTable OBJECT-TYPE
	SYNTAX  SEQUENCE OF McmVNETProfileCfgEntry
	ACCESS  not-accessible
	STATUS  mandatory
	DESCRIPTION
	  "NAME = ; 
	   DESC = The VNET Voice Profile Configuration table. \
		  (Operational);
	   HELP = ;
	   CAPABILITIES = NET_CFG, VPN_CFG;"
	::= { vnet-configuration 2 }

mcmVNETProfileCfgEntry OBJECT-TYPE
	SYNTAX  McmVNETProfileCfgEntry
	ACCESS  not-accessible
	STATUS  mandatory
	DESCRIPTION
	  "NAME = ; 
	   DESC = An entry in the VNET Voice Profile Configuration \
		  table. (Operational);
	   HELP = ;
	   CAPABILITIES = ;"
	INDEX   { mcmVNETProfileCfgProfileNum }
	::= { mcmVNETProfileCfgTable 1 }

McmVNETProfileCfgEntry ::= SEQUENCE {
	mcmVNETProfileCfgProfileNum		INTEGER,
	mcmVNETProfileCfgMode			INTEGER,
	mcmVNETProfileCfgDigitizingRate		INTEGER,
	mcmVNETProfileCfgInputLevelGain		INTEGER,
	mcmVNETProfileCfgOutputLevelAttn	INTEGER,
	mcmVNETProfileCfgBusyOutMode		INTEGER,
	mcmVNETProfileCfgBandwidth		INTEGER,
	mcmVNETProfileCfgBackground		INTEGER,
	mcmVNETProfileCfgBRIPulseRate		INTEGER,
	mcmVNETProfileCfgEMSigFormat		INTEGER,
	mcmVNETProfileCfgFXSSigFormat		INTEGER,
	mcmVNETProfileCfgDVMSigFormat		INTEGER,
	mcmVNETProfileCfgNumberOfRings		INTEGER,
	mcmVNETProfileCfgEMAnalOper		INTEGER,
	mcmVNETProfileCfgRingingFreq		INTEGER,
	mcmVNETProfileCfgFaxDigRate		INTEGER,
	mcmVNETProfileCfgDiscSupervision	INTEGER,
	mcmVNETProfileCfgLineImpedance		INTEGER,
	mcmVNETProfileCfgMaxOutputLevel		INTEGER,
	mcmVNETProfileCfgRegenDelay		INTEGER,
	mcmVNETProfileCfgDialDigTimeLimit	INTEGER,
	mcmVNETProfileCfgMaxNumForDig		INTEGER,
	mcmVNETProfileCfgRegenFormat		INTEGER,
	mcmVNETProfileCfgCallProgTone		INTEGER,
	mcmVNETProfileCfgDTMFDetector		INTEGER,
	mcmVNETProfileCfgJitters		INTEGER,
	mcmVNETProfileCfgEchoCanceller		INTEGER,
	mcmVNETProfileCfgAutoGainControl	INTEGER,
	mcmVNETProfileCfgCompanderFormat	INTEGER,
	mcmVNETProfileCfgPremiumVoice		INTEGER,
	mcmVNETProfileCfgEndOfDialChar		INTEGER,
        mcmVNETProfileCfgBckGrndNoiseLevel      INTEGER,
        mcmVNETProfileCfgSilenceHngOvrTime      INTEGER,
        mcmVNETProfileCfgIdlePattern            INTEGER,
        mcmVNETProfileCfgEcanFilterLength       INTEGER,
        mcmVNETProfileCfgEcanErlImprovement     INTEGER,
        mcmVNETProfileCfgNoiseFloorOffset       INTEGER,
        mcmVNETProfileCfgDtmfGenBurstLength     INTEGER,
        mcmVNETProfileCfgDtmRegenBurstLength    INTEGER
	}

mcmVNETProfileCfgProfileNum OBJECT-TYPE
	SYNTAX	INTEGER (1..32)
	ACCESS  read-only
	STATUS  mandatory
	DESCRIPTION
	  "NAME = ;
	   DESC = The value of this object indicates the profile \
		  number.  Used as an index to the VNET Voice \
		  Profile Configuration table. (Operational);
	   HELP = ;
	   CAPABILITIES = ;"
	::= { mcmVNETProfileCfgEntry 1 }

mcmVNETProfileCfgMode OBJECT-TYPE
	SYNTAX	INTEGER {
		voiceFax (1),
		voiceOnly (2)
		}
	ACCESS  read-write
	STATUS  mandatory
	DESCRIPTION
	  "NAME = ;
	   DESC = The value of this object selects the voice \
		  channel signal processing. (Operational);
	   HELP = Can be used to set to either dual mode with \
		  both voice and fax, or just voice.;
	   CAPABILITIES = ;"
	DEFVAL { voiceFax }
	::= { mcmVNETProfileCfgEntry 2 }

mcmVNETProfileCfgDigitizingRate OBJECT-TYPE
	SYNTAX	INTEGER {
		rateG729 (1),
                rateG729-8K-40MS (2)
		}
	ACCESS  read-write
	STATUS  mandatory
	DESCRIPTION
	  "NAME = ;
	   DESC = The value of this object selects the voice \
		  digitizing algorithm. (Operational);
	   HELP = Rate at which voice is digitized in \
		  designated in bits per second.;
	   CAPABILITIES = ;"
	DEFVAL { rateG729 }
	::= { mcmVNETProfileCfgEntry 3 }

mcmVNETProfileCfgInputLevelGain OBJECT-TYPE
	SYNTAX	INTEGER (-15..19)
	ACCESS  read-write
	STATUS  mandatory
	DESCRIPTION
	  "NAME = ; 
	   DESC = The value of this object selects the input \
		  signal gain in dB. (Operational);
	   HELP = For DVM, max value is 8 dB.  If more than \
		  8 dB is configured, 8 dB will be used. \
                  The range for the BRI card is -15 to 15 dB.;
	   CAPABILITIES = ;"
	DEFVAL { 0 }
	::= { mcmVNETProfileCfgEntry 4 }

mcmVNETProfileCfgOutputLevelAttn OBJECT-TYPE
	SYNTAX	INTEGER (-15..25)
	ACCESS  read-write
	STATUS  mandatory
	DESCRIPTION
	  "NAME = ; 
	   DESC = The value of this object selects the output \
		  signal attenuation in dB. (Operational);
	   HELP = For DVM, max value is 8 dB.  If more than \
		  8 dB is configured, 8 dB will be used. \
                  The range for the BRI card is -15 to 15dB.;
	   CAPABILITIES = ;"
	DEFVAL { 0 }
	::= { mcmVNETProfileCfgEntry 5 }

mcmVNETProfileCfgBusyOutMode OBJECT-TYPE
	SYNTAX	INTEGER {
		systemControlled (1),
		forceOn (2),
		forceOff (3)
		}
	ACCESS  read-write
	STATUS  mandatory
	DESCRIPTION
	  "NAME = ;
	   DESC = The value of this object selects the voice \
		  channel busy out control type. (Operational);
	   HELP = ;
	   CAPABILITIES = ;"
	DEFVAL { systemControlled }
	::= { mcmVNETProfileCfgEntry 6 }

mcmVNETProfileCfgBandwidth OBJECT-TYPE
	SYNTAX	INTEGER {
		voiceActivated (1),
		continuous (2)
		}
	ACCESS  read-write
	STATUS  mandatory
	DESCRIPTION
	  "NAME = ;
	   DESC = The value of this object selects the voice \
		  channel link bandwidth reservation style. \
		  (Operational);
	   HELP = 2 is used for forced connects or PVCs only. \
		  1 is used for switched connects.;
	   CAPABILITIES = ;"
	DEFVAL { voiceActivated }
	::= { mcmVNETProfileCfgEntry 7 }

mcmVNETProfileCfgBackground OBJECT-TYPE
	SYNTAX	INTEGER {
		regenerated (1),
		silence (2)
		}
	ACCESS  read-write
	STATUS  mandatory
	DESCRIPTION
	  "NAME = ;
	   DESC = The value of this object selects the voice \
		  channel background noise generation type. \
		  (Operational);
	   HELP = The ability of passing background noise or \ 
		  silencing the channel during idle periods. \
		  First option allows the background noise to be \
		  regenerated during the periods, whereas the \
		  second option suppresses background noise during \ 
		  idle periods.;
	   CAPABILITIES = ;"
	DEFVAL { regenerated }
	::= { mcmVNETProfileCfgEntry 8 }

mcmVNETProfileCfgBRIPulseRate OBJECT-TYPE
	SYNTAX	INTEGER {
		pulses10PerSec (1),
		pulses20PerSec (2),
		pulses125PerSec (3)
		}
	ACCESS  read-write
	STATUS  obsolete
	DESCRIPTION
	  "NAME = ;
	   DESC = The value of this object selects the voice \
		  channel pulse rate in pulses per second. \
		  (Operational);
	   HELP = NOTE: This object is used by the Partner card \
                  and not for the ISDN BRI voice card.;
	   CAPABILITIES = ;"
	DEFVAL { pulses10PerSec }
	::= { mcmVNETProfileCfgEntry 9 }

mcmVNETProfileCfgEMSigFormat OBJECT-TYPE
	SYNTAX	INTEGER {
		dc (1),
		tone2280 (2),
		pulsedDC (3),
		winkStart (4)
		}
	ACCESS  read-write
	STATUS  mandatory
	DESCRIPTION
	  "NAME = ;
	   DESC = The value of this object specifies the voice \
		  channel E&M signaling format. (Operational);
	   HELP = 2 and 3 are used for force connects only. \
		  1 (DC) is used for switched connects.;
	   CAPABILITIES = ;"
	DEFVAL { dc }
	::= { mcmVNETProfileCfgEntry 10 }

mcmVNETProfileCfgFXSSigFormat OBJECT-TYPE
	SYNTAX	INTEGER {
		repeatedRing (1),
		interruptedRing (2)
		}
	ACCESS  read-write
	STATUS  mandatory
	DESCRIPTION
	  "NAME = ;
	   DESC = The value of this object specifies the voice \
		  channel FXS signaling format. (Operational);
	   HELP = 1 is used for force connects only. \
		  2 is used for switched connects.;
	   CAPABILITIES = ;"
	DEFVAL { interruptedRing }
	::= { mcmVNETProfileCfgEntry 11 }

mcmVNETProfileCfgDVMSigFormat OBJECT-TYPE
	SYNTAX	INTEGER {
		tieTrunk (1),
		tieInvert (2),
		tone2280 (3),
		clearChannel (4),
		dC5B (5),
		dC5BInvert (6),
		r2PUNCOM (7),
		r2Q421 (8),
                dC5RonTron (9),
		israelCAS (10),
		spainCAS (11),
                winkStart (12) 
		}
	ACCESS  read-write
	STATUS  mandatory
	DESCRIPTION
	  "NAME = ;
	   DESC = The value of this object specifies the voice \
		  channel DVM signaling format. (Operational);
	   HELP = 3 and 4 are used for force connects only. \
		  1 is used for switched connects.;
	   CAPABILITIES = ;"
	DEFVAL { tieTrunk }
	::= { mcmVNETProfileCfgEntry 12 }

mcmVNETProfileCfgNumberOfRings OBJECT-TYPE
	SYNTAX	INTEGER (1..9)
	ACCESS  read-write
	STATUS  mandatory
	DESCRIPTION
	  "NAME = ;
	   DESC = The value of this object specifies when the \
		  voice channel (FXO or 3-port) will answer \
		  the call request. (Operational);
	   HELP = ;
	   CAPABILITIES = ;"
	DEFVAL { 1 }
	::= { mcmVNETProfileCfgEntry 13 }

mcmVNETProfileCfgEMAnalOper OBJECT-TYPE
	SYNTAX	INTEGER {
		twoWire (1),
		fourWire (2)
		}
	ACCESS  read-write
	STATUS  mandatory
	DESCRIPTION
	  "NAME = ;
	   DESC = The value of this object specifies the E&M \
		  voice channel operation as either 2 or 4 wire \
		  operation. (Operational);
	   HELP = ;
	   CAPABILITIES = ;"
	DEFVAL { fourWire }
	::= { mcmVNETProfileCfgEntry 14 }

mcmVNETProfileCfgRingingFreq OBJECT-TYPE
	SYNTAX	INTEGER {
		freq25Hz (1),
		freq50Hz (2)
		}
	ACCESS  read-write
	STATUS  mandatory
	DESCRIPTION
	  "NAME = ;
	   DESC = The value of this object specifies the voice \
		  channel (FXS or 3-port) ringing frequency. \
		  (Operational);
	   HELP = ;
	   CAPABILITIES = ;"
	DEFVAL { freq25Hz }
	::= { mcmVNETProfileCfgEntry 15 }

mcmVNETProfileCfgFaxDigRate OBJECT-TYPE
	SYNTAX	INTEGER {
		voiceRate (1),
		rate2400 (2),
		rate4800 (3),
		rate7200 (4),
		rate9600 (5)
		}
	ACCESS  read-write
	STATUS  mandatory
	DESCRIPTION
	  "NAME = ;
	   DESC = The value of this object selects the voice \
		  channel Fax digitizing rate in bits per second. \
		  (Operational);
	   HELP = ;
	   CAPABILITIES = ;"
	DEFVAL { voiceRate }
	::= { mcmVNETProfileCfgEntry 16 }

mcmVNETProfileCfgDiscSupervision OBJECT-TYPE
	SYNTAX	INTEGER {
		tone (1),
		powerInterrupt (2)
		}
	ACCESS  read-write
	STATUS  mandatory
	DESCRIPTION
	  "NAME = ;
	   DESC = The value of this object selects the voice \
		  channel method to detect the line disconnect. \
		  (Operational);
	   HELP = ;
	   CAPABILITIES = ;"
	DEFVAL { tone }
	::= { mcmVNETProfileCfgEntry 17 }

mcmVNETProfileCfgLineImpedance OBJECT-TYPE
	SYNTAX	INTEGER {
		impedance600Ohms (1),
		complex (2)
		}
	ACCESS  read-write
	STATUS  mandatory
	DESCRIPTION
	  "NAME = ;
	   DESC = The value of this object selects the voice \
		  channel type of line impedance. (Operational);
	   HELP = ;
	   CAPABILITIES = ;"
	DEFVAL { impedance600Ohms }
	::= { mcmVNETProfileCfgEntry 18 }

mcmVNETProfileCfgMaxOutputLevel OBJECT-TYPE
	SYNTAX	INTEGER {
		zerodBMNominal (1),
		plus7dBM (2)
		}
	ACCESS  read-write
	STATUS  mandatory
	DESCRIPTION
	  "NAME = ;
	   DESC = The value of this object specifies the voice \
		  channel maximum output level. (Operational);
	   HELP = ;
	   CAPABILITIES = ;"
	DEFVAL { zerodBMNominal }
	::= { mcmVNETProfileCfgEntry 19 }

mcmVNETProfileCfgRegenDelay OBJECT-TYPE
	SYNTAX	INTEGER (1..15)
	ACCESS  read-write
	STATUS  mandatory
	DESCRIPTION
	  "NAME = ;
	   DESC = The value of this object specifies the voice \
		  channel time (in seconds) to delay before dialing \
		  out the number (i.e., time to wait for dial tone). \
		  (Operational);
	   HELP = NOTE: This object is not required for the ISDN BRI \
                  voice card;
	   CAPABILITIES = ;"
	DEFVAL { 1 }
	::= { mcmVNETProfileCfgEntry 20 }

mcmVNETProfileCfgDialDigTimeLimit OBJECT-TYPE
	SYNTAX	INTEGER (1..15)
	ACCESS  read-write
	STATUS  mandatory
	DESCRIPTION
	  "NAME = ;
	   DESC = The value of this object specifies the voice \
		  channel inter-digit time-out time (in seconds). \
		  (Operational);
	   HELP = ;
	   CAPABILITIES = ;"
	DEFVAL { 10 }
	::= { mcmVNETProfileCfgEntry 21 }

mcmVNETProfileCfgMaxNumForDig OBJECT-TYPE
	SYNTAX	INTEGER (0..40)
	ACCESS  read-write
	STATUS  mandatory
	DESCRIPTION
	  "NAME = ;
	   DESC = The value of this object specifies the voice \
		  channel maximum number of digits that can \
		  be dialed. (Operational);
	   HELP = 0 is used for auto-call functionality.;
	   CAPABILITIES = ;"
	DEFVAL { 7 }
	::= { mcmVNETProfileCfgEntry 22 }

mcmVNETProfileCfgRegenFormat OBJECT-TYPE
	SYNTAX	INTEGER {
		dialPulse (1),
		dtmf (2)
		}
	ACCESS  read-write
	STATUS  mandatory
	DESCRIPTION
	  "NAME = ;
	   DESC = The value of this object specifies the voice \
		  channel dial digit regeneration format. \
		  (Operational);
	   HELP = NOTE: This object is not required for the ISDN \
                  BRI voice card.;
	   CAPABILITIES = ;"
	DEFVAL { dtmf }
	::= { mcmVNETProfileCfgEntry 23 }

mcmVNETProfileCfgCallProgTone OBJECT-TYPE
	SYNTAX	INTEGER {
		northAmerica (1),
		japan (2),
		unitedKingdom (3),
		europe (4),
		france (5),
		centralAmerica (6),
		chile (7),
		australia (8)
		}
	ACCESS  read-write
	STATUS  mandatory
	DESCRIPTION
	  "NAME = ;
	   DESC = The value of this object specifies the voice \
		  channel call progress tone required for different \
		  countries or areas. (Operational);
	   HELP = ;
	   CAPABILITIES = ;"
	DEFVAL { northAmerica }
	::= { mcmVNETProfileCfgEntry 24 }

mcmVNETProfileCfgDTMFDetector OBJECT-TYPE
	SYNTAX	INTEGER {
		disable (1),
		enable (2)
		}
	ACCESS  read-write
	STATUS  mandatory
	DESCRIPTION
	  "NAME = ;
	   DESC = The value of this object specifies to the voice \
		  channel whether to turn on or off the DTMF \
		  detector. (Operational);
	   HELP = ;
	   CAPABILITIES = ;"
	DEFVAL { enable }
	::= { mcmVNETProfileCfgEntry 25 }

mcmVNETProfileCfgJitters OBJECT-TYPE
	SYNTAX	INTEGER (0..200)
	ACCESS  read-write
	STATUS  mandatory
	DESCRIPTION
	  "NAME = ;
	   DESC = The value of this object specifies the voice \
		  channel maximum jitters delay (in milliseconds). \
		  (Operational);
	   HELP = ;
	   CAPABILITIES = ;"
	DEFVAL { 50 }
	::= { mcmVNETProfileCfgEntry 26 }

mcmVNETProfileCfgEchoCanceller OBJECT-TYPE
	SYNTAX	INTEGER {
		disable (1),
		enable (2)
		}
	ACCESS  read-write
	STATUS  mandatory
	DESCRIPTION
	  "NAME = ;
	   DESC = The value of this object specifies to the voice \
		  channel whether to turn on or off the echo \
		  canceller. (Operational);
	   HELP = ;
	   CAPABILITIES = ;"
	DEFVAL { enable }
	::= { mcmVNETProfileCfgEntry 27 }

mcmVNETProfileCfgAutoGainControl OBJECT-TYPE
	SYNTAX	INTEGER {
		disable (1),
		enable (2)
		}
	ACCESS  read-write
	STATUS  mandatory
	DESCRIPTION
	  "NAME = ;
	   DESC = The value of this object specifies to the voice \
		  channel whether to automatically set the input \
		  signal level. (Operational);
	   HELP = ;
	   CAPABILITIES = ;"
	DEFVAL { disable }
	::= { mcmVNETProfileCfgEntry 28 }

mcmVNETProfileCfgCompanderFormat OBJECT-TYPE
	SYNTAX	INTEGER {
		uLaw (1),
		aLaw (2)
		}
	ACCESS  read-write
	STATUS  mandatory
	DESCRIPTION
	  "NAME = ;
	   DESC = The value of this object specifies the voice \
		  channel (DVM or BRI) compander type. \
		  (Operational);
	   HELP = ;
	   CAPABILITIES = ;"
	DEFVAL { uLaw }
	::= { mcmVNETProfileCfgEntry 29 }

mcmVNETProfileCfgPremiumVoice OBJECT-TYPE
	SYNTAX	INTEGER {
		disable-compress (1),
		enable-notcompress (2)
		}
	ACCESS  read-write
	STATUS  mandatory
	DESCRIPTION
	  "NAME = ;
	   DESC = The value of this object specifies to the voice \
		  channel (DVM) whether to enable or disable the \
		  transparent voice (no compression) algorithm. \
      		  (Operational);
	   HELP = This object is also used by the ISDN BRI voice card \
                  to enable/disable Digital Lossless Switching Pattern \
                  Generation and Pattern Search.;
	   CAPABILITIES = ;"
	DEFVAL { disable-compress }
	::= { mcmVNETProfileCfgEntry 30 }

mcmVNETProfileCfgEndOfDialChar OBJECT-TYPE
	SYNTAX	INTEGER {
		disable (1),
		enable (2)
		}
	ACCESS  read-write
	STATUS  mandatory
	DESCRIPTION
	  "NAME = ;
	   DESC = The value of this object specifies to the voice \
		  channel whether '#' is used to end a dialing input. \
		  (Operational);
	   HELP = ;
	   CAPABILITIES = ;"
	DEFVAL { disable }
	::= { mcmVNETProfileCfgEntry 31 }

mcmVNETProfileCfgBckGrndNoiseLevel OBJECT-TYPE
	SYNTAX	INTEGER {
		neg25dbm0 (1),
		neg30dbm0 (2),
                neg35dbm0 (3),
                neg40dbm0 (4),
                neg45dbm0 (5)
		}
	ACCESS  read-write
	STATUS  mandatory
	DESCRIPTION
	  "NAME = ;
	   DESC = Signal input above this level is considered\
                  a voiced signal, below this level, the \
                  Voice Activity Detector (VAD), will  \
                  determine if it is a voiced signal or \
                  background noise.
		  (Operational);
	   HELP = Refer to the International \
                  Telecommunication Union(ITU-T) G.711 \
                  document for more information;
	   CAPABILITIES = ;"
	DEFVAL { neg30dbm0 }
	::= { mcmVNETProfileCfgEntry 32 }


mcmVNETProfileCfgSilenceHngOvrTime OBJECT-TYPE
	SYNTAX	INTEGER {
		msec100 (1),
		msec200 (2),
                msec300 (3),
                msec400 (4),
                msec500 (5),
                msec600 (6),
                msec700 (7),
                msec800 (8)
		}
	ACCESS  read-write
	STATUS  mandatory
	DESCRIPTION
	  "NAME = ;
	   DESC = Indicates the time delay to switch \
                  from voice to silence.\
		  (Operational);
	   HELP = ;
	   CAPABILITIES = ;"
	DEFVAL { msec300 }
	::= { mcmVNETProfileCfgEntry 33 }

mcmVNETProfileCfgIdlePattern OBJECT-TYPE
	SYNTAX	INTEGER ( 0..255 )
	ACCESS  read-write
	STATUS  mandatory
	DESCRIPTION
	  "NAME = ;
	   DESC = The value of this object represents the \
                  Idle pattern on the line when no call is up.\
                  Specific to a PBX. This is a permanent DSP \
                  configuration parameter;
	   HELP = This value can be used to detect that a call \
                  has finished and that the echo canceller should \
                  be reset and that fax mode should be terminated.;
	   CAPABILITIES = ;"
	DEFVAL { 255 }
	::= { mcmVNETProfileCfgEntry 34 }


mcmVNETProfileCfgEcanFilterLength OBJECT-TYPE
	SYNTAX	INTEGER {
                length128 (1),
                length256 (2)
                }
	ACCESS  read-write
	STATUS  mandatory
	DESCRIPTION
	  "NAME = ;
	   DESC = The value of this object specifies the filter \
                  length for echo canceller.  This is a permanent \
                  DSP configuration parameter.;
	   HELP = A length of 128 is equal to 16ms.\
                  A length of 256 is equal to 32ms.; 
--                  NOTE: The ISDN BRI voice card supports 32ms only;
	   CAPABILITIES = ;"
	DEFVAL { length256 }
	::= { mcmVNETProfileCfgEntry  35 }

mcmVNETProfileCfgEcanErlImprovement OBJECT-TYPE
	SYNTAX	INTEGER ( -18..0 )
	ACCESS  read-write
	STATUS  mandatory
	DESCRIPTION
	  "NAME = ;
	   DESC =  The value of this object is used for echo \
                  canceller Er1 improvement. This is a DSP \
                  Dynamic configuration parameter.  \
                   A signal will be attenuated by this dB \
                  amount before being passed through the \
                  echo canceller. After the echo canceller, \
                  it will be amplified by this same dB amount, \
                  for a net gain of 0 dB. \
                   This attenuation amplicfication cycle reduces \
                  the resolution of the signal ( -18 ..0 ).;
	   HELP = ;
	   CAPABILITIES = ;"
	DEFVAL { 0 }
	::= { mcmVNETProfileCfgEntry 36 }

mcmVNETProfileCfgNoiseFloorOffset OBJECT-TYPE
	SYNTAX	INTEGER ( 0..255 )
	ACCESS  read-write
	STATUS  mandatory
	DESCRIPTION
	  "NAME = ;
	   DESC = The value of this object will suppress the \
                  impulsive backround noise in order to achieve \
                  silence suppression savings.
	   HELP = ;
	   CAPABILITIES = ;"
	DEFVAL { 0 }
	::= { mcmVNETProfileCfgEntry 37 }

mcmVNETProfileCfgDtmfGenBurstLength OBJECT-TYPE
	SYNTAX	INTEGER {
                time50msec  (1),
                time60msec  (2),
                time70msec  (3),
                time100msec (4)
                }
	ACCESS  read-write
	STATUS  mandatory
	DESCRIPTION
	  "NAME = ;
	   DESC = DTMF burst generation in milliseconds.; 
	   HELP = ;
	   CAPABILITIES = ;"
	DEFVAL { time100msec }
	::= { mcmVNETProfileCfgEntry 38 }

mcmVNETProfileCfgDtmRegenBurstLength OBJECT-TYPE
	SYNTAX	INTEGER {
                time50msec  (1),
                time60msec  (2),
                time70msec  (3),
                time100msec (4)
                }
	ACCESS  read-write
	STATUS  mandatory
	DESCRIPTION
	  "NAME = ;
	   DESC = DTMF burst Regeneration length in milliseconds.;
	   HELP = ;
	   CAPABILITIES = ;"
	DEFVAL { time100msec }
	::= { mcmVNETProfileCfgEntry 39 }


--  the VNET Voice Switching Profile Configuration Table 
--  (Standard/Operational Parameters)

--  This table provides the VNET voice switching profile configuration parameters.
--  This table is used to configure a profile of voice channel switching configuration
--  characteristics; of which, a subset may be used for a particular voice channel
--  (of a specific interface type) to define its switching configuration. (Operational)

mcmVNETSwProfCfgTable OBJECT-TYPE
	SYNTAX  SEQUENCE OF McmVNETSwProfCfgEntry
	ACCESS  not-accessible
	STATUS  mandatory
	DESCRIPTION
	  "NAME = ; 
	   DESC = The VNET Voice Switching Profile Configuration \
		  table.(Operational);
	   HELP = ;
	   CAPABILITIES = NET_CFG, VPN_CFG;"
	::= { vnet-configuration 3 }

mcmVNETSwProfCfgEntry OBJECT-TYPE
	SYNTAX  McmVNETSwProfCfgEntry
	ACCESS  not-accessible
	STATUS  mandatory
	DESCRIPTION
	  "NAME = ; 
	   DESC = An entry in the VNET Voice Switching Profile \
		  Configuration table. (Operational);
	   HELP = ;
	   CAPABILITIES = ;"
	INDEX   { mcmVNETSwProfCfgProfileNum }
	::= { mcmVNETSwProfCfgTable 1 }

McmVNETSwProfCfgEntry ::= SEQUENCE {
	mcmVNETSwProfCfgProfileNum		INTEGER,
	mcmVNETSwProfCfgOutCallRestrict		INTEGER,
	mcmVNETSwProfCfgInCallRestrict		INTEGER,
	mcmVNETSwProfCfgCUGID			INTEGER,
	mcmVNETSwProfCfgRestrictClassCd		INTEGER,
	mcmVNETSwProfCfgAutoCallEntNum		INTEGER,
	mcmVNETSwProfCfgCallNegStrategy		INTEGER,
	mcmVNETSwProfCfgTransmitPriority	INTEGER,
	mcmVNETSwProfCfgAutoCallType		INTEGER,
	mcmVNETSwProfCfgAddServerSelect		INTEGER,
    mcmVNETSwProfCfgOutCallMode         INTEGER
	}

mcmVNETSwProfCfgProfileNum OBJECT-TYPE
	SYNTAX	INTEGER (1..32)
	ACCESS  read-only
	STATUS  mandatory
	DESCRIPTION
	  "NAME = ;
	   DESC = The value of this object indicates the profile \
		  number.  Used as an index to the VNET Voice \
		  Switching Profile Configuration table. \
		  (Operational);
	   HELP = ;
	   CAPABILITIES = ;"
	::= { mcmVNETSwProfCfgEntry 1 }

mcmVNETSwProfCfgOutCallRestrict OBJECT-TYPE
	SYNTAX	INTEGER {
		noRestriction (1),
		closedUserGroupCall (2),
		restrictionClassCall (3),
		bothCUGandRCCall (4),
		inhibitAll (5)
		}
	ACCESS  read-write
	STATUS  mandatory
	DESCRIPTION
	  "NAME = ;
	   DESC = The value of this object specifies how to \
		  handle outgoing calls for voice channel \
		  switching. (Operational);
	   HELP = 2: include CUG ID in outgoing call. \
		  3: include restriction class in outgoing call. \
		  4: include both CUG ID and restriction \
		  class in outgoing call. \
		  5: outgoing call is not allowed.;
	   CAPABILITIES = ;"
	DEFVAL { noRestriction }
	::= { mcmVNETSwProfCfgEntry 2 }

mcmVNETSwProfCfgInCallRestrict OBJECT-TYPE
	SYNTAX	INTEGER {
		noRestriction (1),
		checkCUGID (2),
		checkRestrictionClassCode (3),
		cUGandPublicClassInhibit (4),
		inhibitAll (5)
		}
	ACCESS  read-write
	STATUS  mandatory
	DESCRIPTION
	  "NAME = ;
	   DESC = The value of this object specifies how to \
		  handle incoming calls for voice channel \
		  switching. (Operational);
	   HELP = 2: check CUG ID in incoming call.  (Must \
		  match our CUG ID for call acceptance. \
		  3: check RCC in incoming call.  (Must be \
		  greater than or equal to our RCC for call \
		  acceptance. \
		  4: check both CUG and RCC in incoming \
		  call. \
		  5: incoming call is not allowed.;
	   CAPABILITIES = ;"
	DEFVAL { noRestriction }
	::= { mcmVNETSwProfCfgEntry 3 }

mcmVNETSwProfCfgCUGID OBJECT-TYPE
	SYNTAX	INTEGER (0..255)
	ACCESS  read-write
	STATUS  mandatory
	DESCRIPTION
	  "NAME = ;
	   DESC = The value of this object assigns the Closed \
		  User Group ID for a voice channel. (Operational);
	   HELP = ;
	   CAPABILITIES = ;"
	DEFVAL { 0 }
	::= { mcmVNETSwProfCfgEntry 4 }

mcmVNETSwProfCfgRestrictClassCd OBJECT-TYPE
	SYNTAX	INTEGER (0..255)
	ACCESS  read-write
	STATUS  mandatory
	DESCRIPTION
	  "NAME = ;
	   DESC = The value of this object assigns the Restriction \
		  Class Code for a voice channel. (Operational);
	   HELP = ;
	   CAPABILITIES = ;"
	DEFVAL { 0 }
	::= { mcmVNETSwProfCfgEntry 5 }

mcmVNETSwProfCfgAutoCallEntNum OBJECT-TYPE
	SYNTAX	INTEGER (0..32)
	ACCESS  read-write
	STATUS  mandatory
	DESCRIPTION
	  "NAME = ;
	   DESC = The value of this object provides a voice \
		  channel Auto Call destination number by \
		  specifying an index into the ingress table. \
		  (Operational);
	   HELP = 0: auto call disabled. \
		  1-32: index to the ingress table entry where \
		  the dial number is specified. \
                  The auto call for the ISDN BRI voice card is \
                  always disabled.;
	   CAPABILITIES = ;"
	DEFVAL { 0 }
	::= { mcmVNETSwProfCfgEntry 6 }

mcmVNETSwProfCfgCallNegStrategy OBJECT-TYPE
	SYNTAX	INTEGER {
		specific (1),
		bandwidth (2),
		delay (3)
		}
	ACCESS  read-write
	STATUS  mandatory
	DESCRIPTION
	  "NAME = ;
	   DESC = The value of this object specifies the preference \
		  for the voice algorithm when an outgoing call is \
		  made. (Operational);
	   HELP = specific: whatever is configured. \
		  bandwidth: bigger block size. \
		  delay: shorter block size.;
	   CAPABILITIES = ;"
	DEFVAL { specific }
	::= { mcmVNETSwProfCfgEntry 7 }

mcmVNETSwProfCfgTransmitPriority OBJECT-TYPE
	SYNTAX	INTEGER (0..15)
	ACCESS  read-write
	STATUS  mandatory
	DESCRIPTION
	  "NAME = ;
	   DESC = The value of this object assigns the priority \
		  of the voice data to be transmitted. (Operational);
	   HELP = 0: lowest priority. \
		  15: highest priority.;
	   CAPABILITIES = ;"
	DEFVAL { 11 }
	::= { mcmVNETSwProfCfgEntry 8 }

mcmVNETSwProfCfgAutoCallType OBJECT-TYPE
	SYNTAX	INTEGER {
                normal             (1),
                masterHootnHoller  (2),
                slaveHootnHoller   (3)
                }
	ACCESS  read-write
	STATUS  mandatory
	DESCRIPTION
	  "NAME = ;
	   DESC = Indicates the type of auto-call \
                  switching to be performed by the \
                  voice channel.;
	   HELP = ;
	   CAPABILITIES = ;"
	DEFVAL { normal }      
	::= { mcmVNETSwProfCfgEntry 9 }

mcmVNETSwProfCfgAddServerSelect OBJECT-TYPE
	SYNTAX	INTEGER {
                nas           (1),
                vncs          (2)
                }
	ACCESS  read-write
	STATUS  mandatory
	DESCRIPTION
	  "NAME = ;
	   DESC = Indicates which DNA server is used.;
	   HELP = ;
	   CAPABILITIES = ;"
	::= { mcmVNETSwProfCfgEntry 10 }

mcmVNETSwProfCfgOutCallMode OBJECT-TYPE
	SYNTAX	INTEGER {
                enblock-only (1),
                dynamic      (2)
                }
	ACCESS  read-write
	STATUS  mandatory
	DESCRIPTION
	  "NAME = ;
	   DESC = Indicates the type of call being made.;
	   HELP = ;
	   CAPABILITIES = ;"
	DEFVAL { dynamic }
	::= { mcmVNETSwProfCfgEntry 11 }


--  the VNET Voice Ingress Digit Filtering Configuration Table 
--  (Standard/Operational Parameters)

--  This table provides the VNET voice ingress digit filtering configuration 
--  parameters. (Operational)

mcmVNETIngressDigFilterTable OBJECT-TYPE
	SYNTAX  SEQUENCE OF McmVNETIngressDigFilterEntry
	ACCESS  not-accessible
	STATUS  mandatory
	DESCRIPTION
	  "NAME = ; 
	   DESC = The VNET Voice Ingress Digit Filtering \
		  Configuration table. (Operational);
	   HELP = ;
	   CAPABILITIES = NET_CFG, VPN_CFG;"
	::= { vnet-configuration 4 }

mcmVNETIngressDigFilterEntry OBJECT-TYPE
	SYNTAX  McmVNETIngressDigFilterEntry
	ACCESS  not-accessible
	STATUS  mandatory
	DESCRIPTION
	  "NAME = ; 
	   DESC = An entry in the VNET Voice Ingress Digit \
		  Filtering Configuration table. (Operational);
	   HELP = ;
	   CAPABILITIES = ;"
	INDEX   { mcmVNETIngressDigFilterIndex }
	::= { mcmVNETIngressDigFilterTable 1 }

McmVNETIngressDigFilterEntry ::= SEQUENCE {
	mcmVNETIngressDigFilterIndex		INTEGER,
	mcmVNETIngressDigFilterIngressNum	DisplayString,
	mcmVNETIngressDigFilterManipString	DisplayString
	}

mcmVNETIngressDigFilterIndex OBJECT-TYPE
	SYNTAX	INTEGER (1..32)
	ACCESS  read-only
	STATUS  mandatory
	DESCRIPTION
	  "NAME = ;
	   DESC = The value of this object indicates the index to \
		  the ingress table.  Used as an index to the VNET \
		  Voice Ingress Digit Filtering Configuration table. \
		  Operational);
	   HELP = ;
	   CAPABILITIES = ;"
	::= { mcmVNETIngressDigFilterEntry 1 }

mcmVNETIngressDigFilterIngressNum OBJECT-TYPE
	SYNTAX	DisplayString (SIZE (0..40))
	ACCESS  read-write
	STATUS  mandatory
	DESCRIPTION
	  "NAME = ;
	   DESC = The value of this object selects the digit \
		  pattern to be matched.  (Null terminated \
		  character string.) (Operational);
	   HELP = Valid characters are decimal digits, '#', \
		  '*', '+', '[' and ']' .;
	   CAPABILITIES = ;"
	DEFVAL { "" }
	::= { mcmVNETIngressDigFilterEntry 2 }

mcmVNETIngressDigFilterManipString OBJECT-TYPE
	SYNTAX	DisplayString (SIZE (0..40))
	ACCESS  read-write
	STATUS  mandatory
	DESCRIPTION
	  "NAME = ;
	   DESC = The value of this object selects commands \
		  to produce the ingress digits for speed dial, \
		  call redirect, and source ID insertion features. \
		  (Operational);
	   HELP = Valid characters are decimal digits, '#', \
		  '*', 'D', and 'I'.;
	   CAPABILITIES = ;"
	DEFVAL { "#" }
	::= { mcmVNETIngressDigFilterEntry 3 }


--  the VNET Voice Egress Digit Manipulation Configuration Table 
--  (Standard/Operational Parameters)

--  This table provides the VNET voice egress digit manipulation configuration 
--  parameters. (Operational)

mcmVNETEgressDigManipTable OBJECT-TYPE
	SYNTAX  SEQUENCE OF McmVNETEgressDigManipEntry
	ACCESS  not-accessible
	STATUS  mandatory
	DESCRIPTION
	  "NAME = ; 
	   DESC = The VNET Voice Egress Digit Manipulation \
		  Configuration table. (Operational);
	   HELP = ;
	   CAPABILITIES = NET_CFG, VPN_CFG;"
	::= { vnet-configuration 5 }

mcmVNETEgressDigManipEntry OBJECT-TYPE
	SYNTAX  McmVNETEgressDigManipEntry
	ACCESS  not-accessible
	STATUS  mandatory
	DESCRIPTION
	  "NAME = ; 
	   DESC = An entry in the VNET Voice Egress Digit \
		  Manipulation Configuration table. (Operational);
	   HELP = ;
	   CAPABILITIES = ;"
	INDEX   { mcmVNETEgressDigManipIndex }
	::= { mcmVNETEgressDigManipTable 1 }

McmVNETEgressDigManipEntry ::= SEQUENCE {
	mcmVNETEgressDigManipIndex		INTEGER,
	mcmVNETEgressDigManipPhoneNum		DisplayString,
	mcmVNETEgressDigManipString		DisplayString,
	mcmVNETEgressDigManipChIDList		DisplayString
	}

mcmVNETEgressDigManipIndex OBJECT-TYPE
	SYNTAX	INTEGER (1..32)
	ACCESS  read-only
	STATUS  mandatory
	DESCRIPTION
	  "NAME = ;
	   DESC = The value of this object indicates the index to \
		  the egress table.  Used as an index to the VNET \
		  Voice Egress Digit Manipulation Configuration \
		  table. Operational);
	   HELP = ;
	   CAPABILITIES = ;"
	::= { mcmVNETEgressDigManipEntry 1 }

mcmVNETEgressDigManipPhoneNum OBJECT-TYPE
	SYNTAX	DisplayString (SIZE (0..40))
	ACCESS  read-write
	STATUS  mandatory
	DESCRIPTION
	  "NAME = ;
	   DESC = The value of this object selects the phone \
		  number that voice channels are associated with. \
		  This is the number to be registered to the Address \
		  Server (RSA). (Operational);
	   HELP = Valid characters are decimal digits, '#', and '*'.;
	   CAPABILITIES = ;"
	DEFVAL { "" }
	::= { mcmVNETEgressDigManipEntry 2 }

mcmVNETEgressDigManipString OBJECT-TYPE
	SYNTAX	DisplayString (SIZE (0..40))
	ACCESS  read-write
	STATUS  mandatory
	DESCRIPTION
	  "NAME = ;
	   DESC = The value of this object selects commands \
		  to produce the egress digits for FXO, E&M, \
		  or FXS 3-Port interface.  The result is the \
		  number to be sent to the connected phone \
		  device. (Operational);
	   HELP = Valid characters are decimal digits, '#', '*', \
		  '+', 'D', 'H', and 'I'. The character 'H' is used \
		  used to trigger immediate dial handling by the PBX.;  
	   CAPABILITIES = ;"
	DEFVAL { "" }
	::= { mcmVNETEgressDigManipEntry 3 }

mcmVNETEgressDigManipChIDList OBJECT-TYPE
	SYNTAX	DisplayString (SIZE (0..70))
	ACCESS  read-write
	STATUS  mandatory
	DESCRIPTION
	  "NAME = ;
	   DESC = The value of this object selects voice channels \
		  associated with the phone number.  The valid \
		  string consists of the substring 'B1'~'B6', \
		  'C1'~'C12', 'D1'~'D12', and 'E1'~'E2'. \
		  (Operational);
	   HELP = Valid characters are decimal digits, 'B', 'C', \
		  'D', and 'E'.;
	   CAPABILITIES = ;"
	DEFVAL { "" }
	::= { mcmVNETEgressDigManipEntry 4 }



--  "Parallel" Configuration Parameter ("nvm") Groups/Tables


--  the VNET Voice Channel Configuration Table 
--  (Configuration Parameters)

--  This table provides the VNET voice channel configuration parameters
--  for identifying a voice channel with its corresponding voice profile. (Configuration)

nvmVNETChCfgTable OBJECT-TYPE
	SYNTAX  SEQUENCE OF NvmVNETChCfgEntry
	ACCESS  not-accessible
	STATUS  mandatory
	DESCRIPTION
	  "NAME = ; 
	   DESC = The VNET Voice Channel Configuration table. \
		  (Configuration);
	   HELP = ;
	   CAPABILITIES = NET_CFG, VPN_CFG;"
	::= { vnet-configuration 6 }

nvmVNETChCfgEntry OBJECT-TYPE
	SYNTAX  NvmVNETChCfgEntry
	ACCESS  not-accessible
	STATUS  mandatory
	DESCRIPTION
	  "NAME = ; 
	   DESC = An entry in the VNET Voice Channel Configuration \
		  table. (Configuration);
	   HELP = ;
	   CAPABILITIES = ;"
	INDEX   { nvmVNETChCfgLimID, nvmVNETChCfgChannelID }
	::= { nvmVNETChCfgTable 1 }

NvmVNETChCfgEntry ::= SEQUENCE {
	nvmVNETChCfgLimID			INTEGER,
	nvmVNETChCfgChannelID			INTEGER,
	nvmVNETChCfgVoiceProfile		INTEGER,
	nvmVNETChCfgSwitchingProfile		INTEGER,
	nvmVNETChCfgInterfaceType		INTEGER
	}

nvmVNETChCfgLimID OBJECT-TYPE
	SYNTAX	INTEGER {
		lim1 (2),
		lim2 (3),
		lim3 (4),
		lim4 (5),
		limB (6),
		limC (7),
		limD (8),
		limE (9)
		}
	ACCESS  read-only
	STATUS  mandatory
	DESCRIPTION
	  "NAME = ;
	   DESC = The card lim (logical interface module) number of a \
		  particular voice channel.  Used as an index to the \
		  VNET Voice Channel Configuration table. (Configuration);
	   HELP = ;
	   CAPABILITIES = ;"
	::= { nvmVNETChCfgEntry 1 }

nvmVNETChCfgChannelID OBJECT-TYPE
	SYNTAX	INTEGER (1..12)
	ACCESS  read-only
	STATUS  mandatory
	DESCRIPTION
  "NAME = ;
	   DESC = The position of the voice channel in the lim. \
		  Used as an index to the VNET Voice \
		  Channel Configuration table. (Configuration);
	   HELP = ;
	   CAPABILITIES = ;"
	::= { nvmVNETChCfgEntry 2 }

nvmVNETChCfgVoiceProfile OBJECT-TYPE
	SYNTAX	INTEGER (1..32)
	ACCESS  read-only
	STATUS  mandatory
	DESCRIPTION
	  "NAME = ; 
	   DESC = The value of this object indicates the profile \
		  to be used to configure the specified voice \
		  channel. (Configuration);
	   HELP = ;
	   CAPABILITIES = ;"
	DEFVAL { 1 }
	::= { nvmVNETChCfgEntry 3 }

nvmVNETChCfgSwitchingProfile OBJECT-TYPE
	SYNTAX	INTEGER (1..32)
	ACCESS  read-only
	STATUS  mandatory
	DESCRIPTION
	  "NAME = ; 
	   DESC = The value of this object indicates the profile \
		  to be used for a switching call. (Configuration);
	   HELP = ;
	   CAPABILITIES = ;"
	DEFVAL { 1 }
	::= { nvmVNETChCfgEntry 4 }

nvmVNETChCfgInterfaceType OBJECT-TYPE
	SYNTAX	INTEGER {
		not-available (1),
		enhanced-loop-start-FXS (2),
		enhanced-EandM (3),
		enhanced-loop-start-FXO (4),
		low-cost-loop-start-FXS (5),
		low-cost-EandM (6),
		low-cost-loop-start-FXO (7),
		ground-start-FXS (8),
		ground-start-FXO (9),
		three-port (10),
		dvm (11),
		bri (12)
		}
	ACCESS  read-only
	STATUS  mandatory
	DESCRIPTION
	  "NAME = ; 
	   DESC = The value of this object indicates the interface \
		  type of the specified voice channel. (Configuration);
	   HELP = Upon powerup, the interface type will not be \
		  available until the DSP software is loaded and its \
		  status is reported.;
	   CAPABILITIES = ;"
	::= { nvmVNETChCfgEntry 5 }


--  the VNET Voice Profile Configuration Table 
--  (Configuration Parameters)

--  This table provides the VNET voice profile configuration parameters.
--  This table is used to view a profile of voice channel configuration
--  characteristics; of which, a subset may be used for a particular voice
--  channel (of a specific interface type) to define its configuration. (Configuration)

nvmVNETProfileCfgTable OBJECT-TYPE
	SYNTAX  SEQUENCE OF NvmVNETProfileCfgEntry
	ACCESS  not-accessible
	STATUS  mandatory
	DESCRIPTION
	  "NAME = ; 
	   DESC = The VNET Voice Profile Configuration table. \
		  (Configuration);
	   HELP = ;
	   CAPABILITIES = NET_CFG, VPN_CFG;"
	::= { vnet-configuration 7 }

nvmVNETProfileCfgEntry OBJECT-TYPE
	SYNTAX  NvmVNETProfileCfgEntry
	ACCESS  not-accessible
	STATUS  mandatory
	DESCRIPTION
	  "NAME = ; 
	   DESC = An entry in the VNET Voice Profile Configuration \
		  table. (Configuration);
	   HELP = ;
	   CAPABILITIES = ;"
	INDEX   { nvmVNETProfileCfgProfileNum }
	::= { nvmVNETProfileCfgTable 1 }

NvmVNETProfileCfgEntry ::= SEQUENCE {
	nvmVNETProfileCfgProfileNum		INTEGER,
	nvmVNETProfileCfgMode			INTEGER,
	nvmVNETProfileCfgDigitizingRate		INTEGER,
	nvmVNETProfileCfgInputLevelGain		INTEGER,
	nvmVNETProfileCfgOutputLevelAttn	INTEGER,
	nvmVNETProfileCfgBusyOutMode		INTEGER,
	nvmVNETProfileCfgBandwidth		INTEGER,
	nvmVNETProfileCfgBackground		INTEGER,
	nvmVNETProfileCfgBRIPulseRate		INTEGER,
	nvmVNETProfileCfgEMSigFormat		INTEGER,
	nvmVNETProfileCfgFXSSigFormat		INTEGER,
	nvmVNETProfileCfgDVMSigFormat		INTEGER,
	nvmVNETProfileCfgNumberOfRings		INTEGER,
	nvmVNETProfileCfgEMAnalOper		INTEGER,
	nvmVNETProfileCfgRingingFreq		INTEGER,
	nvmVNETProfileCfgFaxDigRate		INTEGER,
	nvmVNETProfileCfgDiscSupervision	INTEGER,
	nvmVNETProfileCfgLineImpedance		INTEGER,
	nvmVNETProfileCfgMaxOutputLevel		INTEGER,
	nvmVNETProfileCfgRegenDelay		INTEGER,
	nvmVNETProfileCfgDialDigTimeLimit	INTEGER,
	nvmVNETProfileCfgMaxNumForDig		INTEGER,
	nvmVNETProfileCfgRegenFormat		INTEGER,
	nvmVNETProfileCfgCallProgTone		INTEGER,
	nvmVNETProfileCfgDTMFDetector		INTEGER,
	nvmVNETProfileCfgJitters		INTEGER,
	nvmVNETProfileCfgEchoCanceller		INTEGER,
	nvmVNETProfileCfgAutoGainControl	INTEGER,
	nvmVNETProfileCfgCompanderFormat	INTEGER,
	nvmVNETProfileCfgPremiumVoice		INTEGER,
	nvmVNETProfileCfgEndOfDialChar		INTEGER,
        nvmVNETProfileCfgBckGrndNoiseLevel      INTEGER,
        nvmVNETProfileCfgSilenceHngOvrTime      INTEGER,
        nvmVNETProfileCfgIdlePattern            INTEGER,
        nvmVNETProfileCfgEcanFilterLength       INTEGER,
        nvmVNETProfileCfgEcanErlImprovement     INTEGER,
        nvmVNETProfileCfgNoiseFloorOffset       INTEGER,
        nvmVNETProfileCfgDtmfGenBurstLength     INTEGER,
        nvmVNETProfileCfgDtmRegenBurstLength    INTEGER
	}

nvmVNETProfileCfgProfileNum OBJECT-TYPE
	SYNTAX	INTEGER (1..32)
	ACCESS  read-only
	STATUS  mandatory
	DESCRIPTION
	  "NAME = ;
	   DESC = The value of this object indicates the profile \
		  number.  Used as an index to the VNET Voice \
		  Profile Configuration table. (Configuration);
	   HELP = ;
	   CAPABILITIES = ;"
	::= { nvmVNETProfileCfgEntry 1 }

nvmVNETProfileCfgMode OBJECT-TYPE
	SYNTAX	INTEGER {
		voiceFax (1),
		voiceOnly (2)
		}
	ACCESS  read-only
	STATUS  mandatory
	DESCRIPTION
	  "NAME = ;
	   DESC = The value of this object selects the voice \
		  channel signal processing. (Configuration);
	   HELP = Can be used to set to either dual mode with \
		  both voice and fax, or just voice.;
	   CAPABILITIES = ;"
	DEFVAL { voiceFax }
	::= { nvmVNETProfileCfgEntry 2 }

nvmVNETProfileCfgDigitizingRate OBJECT-TYPE
	SYNTAX	INTEGER {
		rateG729 (1),
                rateG729-8k-40ms (2)
		}
	ACCESS  read-only
	STATUS  mandatory
	DESCRIPTION
	  "NAME = ;
	   DESC = The value of this object selects the voice \
		  digitizing algorithm. (Configuration);
	   HELP = Rate at which voice is digitized in \
		  designated in bits per second.;
	   CAPABILITIES = ;"
	DEFVAL { rateG729 }
	::= { nvmVNETProfileCfgEntry 3 }

nvmVNETProfileCfgInputLevelGain OBJECT-TYPE
	SYNTAX	INTEGER (-15..19)
	ACCESS  read-only
	STATUS  mandatory
	DESCRIPTION
	  "NAME = ; 
	   DESC = The value of this object selects the input \
		  signal gain in dB. (Configuration);
	   HELP = For DVM, max value is 8 dB.  If more than \
		  8 dB is configured, 8 dB will be used.\
                  The ISDN BRI voice card range is -15 to 15dB.;
	   CAPABILITIES = ;"
	DEFVAL { 0 }
	::= { nvmVNETProfileCfgEntry 4 }

nvmVNETProfileCfgOutputLevelAttn OBJECT-TYPE
	SYNTAX	INTEGER (-15..25)
	ACCESS  read-only
	STATUS  mandatory
	DESCRIPTION
	  "NAME = ; 
	   DESC = The value of this object selects the output \
		  signal attenuation in dB. (Configuration);
	   HELP = For DVM, max value is 8 dB.  If more than \
		  8 dB is configured, 8 dB will be used.;
	   CAPABILITIES = ;"
	DEFVAL { 0 }
	::= { nvmVNETProfileCfgEntry 5 }

nvmVNETProfileCfgBusyOutMode OBJECT-TYPE
	SYNTAX	INTEGER {
		systemControlled (1),
		forceOn (2),
		forceOff (3)
		}
	ACCESS  read-only
	STATUS  mandatory
	DESCRIPTION
	  "NAME = ;
	   DESC = The value of this object selects the voice \
		  channel busy out control type. (Configuration);
	   HELP = ;
	   CAPABILITIES = ;"
	DEFVAL { systemControlled }
	::= { nvmVNETProfileCfgEntry 6 }

nvmVNETProfileCfgBandwidth OBJECT-TYPE
	SYNTAX	INTEGER {
		voiceActivated (1),
		continuous (2)
		}
	ACCESS  read-only
	STATUS  mandatory
	DESCRIPTION
	  "NAME = ;
	   DESC = The value of this object selects the voice \
		  channel link bandwidth reservation style. \
		  (Configuration);
	   HELP = 2 is used for forced connects or PVCs only. \
		  1 is used for switched connects.;
	   CAPABILITIES = ;"
	DEFVAL { voiceActivated }
	::= { nvmVNETProfileCfgEntry 7 }

nvmVNETProfileCfgBackground OBJECT-TYPE
	SYNTAX	INTEGER {
		regenerated (1),
		silence (2)
		}
	ACCESS  read-only
	STATUS  mandatory
	DESCRIPTION
	  "NAME = ;
	   DESC = The value of this object selects the voice \
		  channel background noise generation type. \
		  (Configuration);
	   HELP = The ability of passing background noise or \ 
		  silencing the channel during idle periods. \
		  First option allows the background noise to be \
		  regenerated during the periods, whereas the \
		  second option suppresses background noise during \ 
		  idle periods.;
	   CAPABILITIES = ;"
	DEFVAL { regenerated }
	::= { nvmVNETProfileCfgEntry 8 }

nvmVNETProfileCfgBRIPulseRate OBJECT-TYPE
	SYNTAX	INTEGER {
		pulses10PerSec (1),
		pulses20PerSec (2),
		pulses125PerSec (3)
		}
	ACCESS  read-only
	STATUS  obsolete
	DESCRIPTION
	  "NAME = ;
	   DESC = The value of this object selects the voice \
		  channel pulse rate in pulses per second. \
		  (Configuration);
	   HELP = NOTE: This object is used by the Partner Card, \
                  not by the ISDN BRI voice card.;
	   CAPABILITIES = ;"
	DEFVAL { pulses10PerSec }
	::= { nvmVNETProfileCfgEntry 9 }

nvmVNETProfileCfgEMSigFormat OBJECT-TYPE
	SYNTAX	INTEGER {
		dc (1),
		tone2280 (2),
		pulsedDC (3),
		winkStart (4)
		}
	ACCESS  read-only
	STATUS  mandatory
	DESCRIPTION
	  "NAME = ;
	   DESC = The value of this object specifies the voice \
		  channel E&M signaling format. (Configuration);
	   HELP = 2 and 3 are used for force connects only. \
		  1 (DC) is used for switched connects.;
	   CAPABILITIES = ;"
	DEFVAL { dc }
	::= { nvmVNETProfileCfgEntry 10 }

nvmVNETProfileCfgFXSSigFormat OBJECT-TYPE
	SYNTAX	INTEGER {
		repeatedRing (1),
		interruptedRing (2)
		}
	ACCESS  read-only
	STATUS  mandatory
	DESCRIPTION
	  "NAME = ;
	   DESC = The value of this object specifies the voice \
		  channel FXS signaling format. (Configuration);
	   HELP = 1 is used for force connects only. \
		  2 is used for switched connects.;
	   CAPABILITIES = ;"
	DEFVAL { interruptedRing }
	::= { nvmVNETProfileCfgEntry 11 }

nvmVNETProfileCfgDVMSigFormat OBJECT-TYPE
	SYNTAX	INTEGER {
		tieTrunk (1),
		tieInvert (2),
 		tone2280 (3),
		clearChannel (4),
		dC5B (5),
		dC5BInvert (6),
		r2PUNCOM (7),
		r2Q421 (8),
                dC5RonTron (9),
		israelCAS (10),
		spainCAS (11),
                winkStart (12) 
		}
	ACCESS  read-only
	STATUS  mandatory
	DESCRIPTION
	  "NAME = ;
	   DESC = The value of this object specifies the voice \
		  channel DVM signaling format. (Configuration);
	   HELP = 3 and 4 are used for force connects only. \
		  1 is used for switched connects.;
	   CAPABILITIES = ;"
	DEFVAL { tieTrunk }
	::= { nvmVNETProfileCfgEntry 12 }

nvmVNETProfileCfgNumberOfRings OBJECT-TYPE
	SYNTAX	INTEGER (1..9)
	ACCESS  read-only
	STATUS  mandatory
	DESCRIPTION
	  "NAME = ;
	   DESC = The value of this object specifies when the \
		  voice channel (FXO or 3-port) will answer \
		  the call request. (Configuration);
	   HELP = ;
	   CAPABILITIES = ;"
	DEFVAL { 1 }
	::= { nvmVNETProfileCfgEntry 13 }

nvmVNETProfileCfgEMAnalOper OBJECT-TYPE
	SYNTAX	INTEGER {
		twoWire (1),
		fourWire (2)
		}
	ACCESS  read-only
	STATUS  mandatory
	DESCRIPTION
	  "NAME = ;
	   DESC = The value of this object specifies the E&M \
		  voice channel operation as either 2 or 4 wire \
		  operation. (Configuration);
	   HELP = ;
	   CAPABILITIES = ;"
	DEFVAL { fourWire }
	::= { nvmVNETProfileCfgEntry 14 }

nvmVNETProfileCfgRingingFreq OBJECT-TYPE
	SYNTAX	INTEGER {
		freq25Hz (1),
		freq50Hz (2)
		}
	ACCESS  read-only
	STATUS  mandatory
	DESCRIPTION
	  "NAME = ;
	   DESC = The value of this object specifies the voice \
		  channel (FXS or 3-port) ringing frequency. \
		  (Configuration);
	   HELP = ;
	   CAPABILITIES = ;"
	DEFVAL { freq25Hz }
	::= { nvmVNETProfileCfgEntry 15 }

nvmVNETProfileCfgFaxDigRate OBJECT-TYPE
	SYNTAX	INTEGER {
		voiceRate (1),
		rate2400 (2),
		rate4800 (3),
		rate7200 (4),
		rate9600 (5)
		}
	ACCESS  read-only
	STATUS  mandatory
	DESCRIPTION
	  "NAME = ;
	   DESC = The value of this object selects the voice \
		  channel Fax digitizing rate in bits per second. \
		  (Configuration);
	   HELP = ;
	   CAPABILITIES = ;"
	DEFVAL { voiceRate }
	::= { nvmVNETProfileCfgEntry 16 }

nvmVNETProfileCfgDiscSupervision OBJECT-TYPE
	SYNTAX	INTEGER {
		tone (1),
		powerInterrupt (2)
		}
	ACCESS  read-only
	STATUS  mandatory
	DESCRIPTION
	  "NAME = ;
	   DESC = The value of this object selects the voice \
		  channel method to detect the line disconnect. \
		  (Configuration);
	   HELP = ;
	   CAPABILITIES = ;"
	DEFVAL { tone }
	::= { nvmVNETProfileCfgEntry 17 }

nvmVNETProfileCfgLineImpedance OBJECT-TYPE
	SYNTAX	INTEGER {
		impedance600Ohms (1),
		complex (2)
		}
	ACCESS  read-only
	STATUS  mandatory
	DESCRIPTION
	  "NAME = ;
	   DESC = The value of this object selects the voice \
		  channel type of line impedance. (Configuration);
	   HELP = ;
	   CAPABILITIES = ;"
	DEFVAL { impedance600Ohms }
	::= { nvmVNETProfileCfgEntry 18 }

nvmVNETProfileCfgMaxOutputLevel OBJECT-TYPE
	SYNTAX	INTEGER {
		zerodBMNominal (1),
		plus7dBM (2)
		}
	ACCESS  read-only
	STATUS  mandatory
	DESCRIPTION
	  "NAME = ;
	   DESC = The value of this object specifies the voice \
		  channel maximum output level. (Configuration);
	   HELP = ;
	   CAPABILITIES = ;"
	DEFVAL { zerodBMNominal }
	::= { nvmVNETProfileCfgEntry 19 }

nvmVNETProfileCfgRegenDelay OBJECT-TYPE
	SYNTAX	INTEGER (1..15)
	ACCESS  read-only
	STATUS  mandatory
	DESCRIPTION
	  "NAME = ;
	   DESC = The value of this object specifies the voice \
		  channel time (in seconds) to delay before dialing \
		  out the number (i.e., time to wait for dial tone). \
		  (Configuration);
	   HELP = NOTE : This object is not used for the ISDN BRI \
                  voice card.;
	   CAPABILITIES = ;"
	DEFVAL { 1 }
	::= { nvmVNETProfileCfgEntry 20 }

nvmVNETProfileCfgDialDigTimeLimit OBJECT-TYPE
	SYNTAX	INTEGER (1..15)
	ACCESS  read-only
	STATUS  mandatory
	DESCRIPTION
	  "NAME = ;
	   DESC = The value of this object specifies the voice \
		  channel inter-digit time-out time (in seconds). \
		  (Configuration);
	   HELP = ;
	   CAPABILITIES = ;"
	DEFVAL { 10 }
	::= { nvmVNETProfileCfgEntry 21 }

nvmVNETProfileCfgMaxNumForDig OBJECT-TYPE
	SYNTAX	INTEGER (0..40)
	ACCESS  read-only
	STATUS  mandatory
	DESCRIPTION
	  "NAME = ;
	   DESC = The value of this object specifies the voice \
		  channel maximum number of digits that can \
		  be dialed. (Configuration);
	   HELP = 0 is used for auto-call functionality.;
	   CAPABILITIES = ;"
	DEFVAL { 7 }
	::= { nvmVNETProfileCfgEntry 22 }

nvmVNETProfileCfgRegenFormat OBJECT-TYPE
	SYNTAX	INTEGER {
		dialPulse (1),
		dtmf (2)
		}
	ACCESS  read-only
	STATUS  mandatory
	DESCRIPTION
	  "NAME = ;
	   DESC = The value of this object specifies the voice \
		  channel dial digit regeneration format. \
		  (Configuration);
	   HELP = NOTE: THIS object is not used for the ISDN \
                  BRI voice card.;
	   CAPABILITIES = ;"
	DEFVAL { dtmf }
	::= { nvmVNETProfileCfgEntry 23 }

nvmVNETProfileCfgCallProgTone OBJECT-TYPE
	SYNTAX	INTEGER {
		northAmerica (1),
		japan (2),
		unitedKingdom (3),
		europe-germany (4),
		france (5),
		centralAmerica (6),
		chile (7),
		australia (8)
		}
	ACCESS  read-only
	STATUS  mandatory
	DESCRIPTION
	  "NAME = ;
	   DESC = The value of this object specifies the voice \
		  channel call progress tone required for different \
		  countries or areas. (Configuration);
	   HELP = ;
	   CAPABILITIES = ;"
	DEFVAL { northAmerica }
	::= { nvmVNETProfileCfgEntry 24 }

nvmVNETProfileCfgDTMFDetector OBJECT-TYPE
	SYNTAX	INTEGER {
		disable (1),
		enable (2)
		}
	ACCESS  read-only
	STATUS  mandatory
	DESCRIPTION
	  "NAME = ;
	   DESC = The value of this object specifies to the voice \
		  channel whether to turn on or off the DTMF \
		  detector. (Configuration);
	   HELP = ;
	   CAPABILITIES = ;"
	DEFVAL { enable }
	::= { nvmVNETProfileCfgEntry 25 }

nvmVNETProfileCfgJitters OBJECT-TYPE
	SYNTAX	INTEGER (0..200)
	ACCESS  read-only
	STATUS  mandatory
	DESCRIPTION
	  "NAME = ;
	   DESC = The value of this object specifies the voice \
		  channel maximum jitters delay (in milliseconds). \
		  (Configuration);
	   HELP = ;
	   CAPABILITIES = ;"
	DEFVAL { 50 }
	::= { nvmVNETProfileCfgEntry 26 }

nvmVNETProfileCfgEchoCanceller OBJECT-TYPE
	SYNTAX	INTEGER {
		disable (1),
		enable (2)
		}
	ACCESS  read-only
	STATUS  mandatory
	DESCRIPTION
	  "NAME = ;
	   DESC = The value of this object specifies to the voice \
		  channel whether to turn on or off the echo \
		  canceller. (Configuration);
	   HELP = ;
	   CAPABILITIES = ;"
	DEFVAL { enable }
	::= { nvmVNETProfileCfgEntry 27 }

nvmVNETProfileCfgAutoGainControl OBJECT-TYPE
	SYNTAX	INTEGER {
		disable (1),
		enable (2)
		}
	ACCESS  read-only
	STATUS  mandatory
	DESCRIPTION
	  "NAME = ;
	   DESC = The value of this object specifies to the voice \
		  channel whether to automatically set the input \
		  signal level. (Configuration);
	   HELP = ;
	   CAPABILITIES = ;"
	DEFVAL { disable }
	::= { nvmVNETProfileCfgEntry 28 }

nvmVNETProfileCfgCompanderFormat OBJECT-TYPE
	SYNTAX	INTEGER {
		uLaw (1),
		aLaw (2)
		}
	ACCESS  read-only
	STATUS  mandatory
	DESCRIPTION
	  "NAME = ;
	   DESC = The value of this object specifies the voice \
		  channel (DVM or BRI) compander type. \
		  (Configuration);
	   HELP = ;
	   CAPABILITIES = ;"
	DEFVAL { uLaw }
	::= { nvmVNETProfileCfgEntry 29 }

nvmVNETProfileCfgPremiumVoice OBJECT-TYPE
	SYNTAX	INTEGER {
		disable-compress (1),
		enable-notcompress (2)
		}
	ACCESS  read-only
	STATUS  mandatory
	DESCRIPTION
	  "NAME = ;
	   DESC = The value of this object specifies to the voice \
		  channel (DVM) whether to enable or disable the \
		  transparent voice (no compression) algorithm. \
		  (Configuration);
	   HELP = This object is also used by the ISDN BRI voice \
                  card to enable/disable Digital Lossless Switching \
                  Pattern Generation and Pattern Search.;
	   CAPABILITIES = ;"
	DEFVAL { disable-compress }
	::= { nvmVNETProfileCfgEntry 30 }

nvmVNETProfileCfgEndOfDialChar OBJECT-TYPE
	SYNTAX	INTEGER {
		disable (1),
		enable (2)
		}
	ACCESS  read-only
	STATUS  mandatory
	DESCRIPTION
	  "NAME = ;
	   DESC = The value of this object specifies to the voice \
		  channel whether '#' is used to end a dialing input. \
		  (Configuration);
	   HELP = ;
	   CAPABILITIES = ;"
	DEFVAL { disable }
	::= { nvmVNETProfileCfgEntry 31 }

nvmVNETProfileCfgBckGrndNoiseLevel OBJECT-TYPE
	SYNTAX	INTEGER {
		neg25dbm0 (1),
		neg30dbm0 (2),
                neg35dbm0 (3),
                neg40dbm0 (4),
                neg45dbm0 (5)
		}
	ACCESS  read-only
	STATUS  mandatory
	DESCRIPTION
	  "NAME = ;
	   DESC = Signal input above this level is considered\
                  a voiced signal, below this level, the \
                  Voice Activity Detector (VAD), will  \
                  determine if it is a voiced signal or \
                  background noise.
		  (Configuration);
	   HELP = Refer to the International \
                  Telecommunication Union(ITU-T) G.711 \
                  document for more information;
	   CAPABILITIES = ;"
	DEFVAL { neg30dbm0 }
	::= { nvmVNETProfileCfgEntry 32 }

nvmVNETProfileCfgSilenceHngOvrTime OBJECT-TYPE
	SYNTAX	INTEGER {
		msec100 (1),
		msec200 (2),
                msec300 (3),
                msec400 (4),
                msec500 (5),
                msec600 (6),
                msec700 (7),
                msec800 (8)
		}
	ACCESS  read-only
	STATUS  mandatory
	DESCRIPTION
	  "NAME = ;
	   DESC = Indicates the time delay to switch \
                  from voice to silence.\
		  (Configuration);
	   HELP = ;
	   CAPABILITIES = ;"
	DEFVAL { msec300 }
	::= { nvmVNETProfileCfgEntry 33 }

nvmVNETProfileCfgIdlePattern OBJECT-TYPE
	SYNTAX	INTEGER ( 0..255 )
	ACCESS  read-only
	STATUS  mandatory
	DESCRIPTION
	  "NAME = ;
	   DESC = The value of this object represents the \
                  Idle pattern on the line when no call is up.\
                  Specific to a PBX. This is a permanent DSP \
                  configuration parameter;
	   HELP = This value can be used to detect that a call \
                  has finished and that the echo canceller should \
                  be reset and that fax mode should be terminated.;
	   CAPABILITIES = ;"
	DEFVAL { 255 }
	::= { nvmVNETProfileCfgEntry 34 }


nvmVNETProfileCfgEcanFilterLength OBJECT-TYPE
	SYNTAX	INTEGER {
				length128 (1),
				length256 (2)
				}
	ACCESS  read-only
	STATUS  mandatory
	DESCRIPTION
	  "NAME = ;
	   DESC = The value of this object specifies the filter \
                  length for echo canceller.  This is a permanent \
                  DSP configuration parameter.;
	   HELP = A length of 128 is equal to 16ms.\
                  A length of 256 is equal to 32ms.; 
----                  NOTE: The ISDN BRI voice card supports 32ms only;
	   CAPABILITIES = ;"
	DEFVAL { 256 }
	::= { nvmVNETProfileCfgEntry  35 }

nvmVNETProfileCfgEcanErlImprovement OBJECT-TYPE
	SYNTAX	INTEGER ( -18..0 )
	ACCESS  read-only
	STATUS  mandatory
	DESCRIPTION
	  "NAME = ;
	   DESC =  The value of this object is used for echo \
                  canceller Er1 improvement. This is a DSP \
                  Dynamic configuration parameter.  \
                   A signal will be attenuated by this dB \
                  amount before being passed through the \
                  echo canceller. After the echo canceller, \
                  it will be amplified by this same dB amount, \
                  for a net gain of 0 dB. \
                   This attenuation amplicfication cycle reduces \
                  the resolution of the signal ( -18 ..0 ).;
	   HELP = ;
	   CAPABILITIES = ;"
	DEFVAL { 0 } 
	::= { nvmVNETProfileCfgEntry 36 }

nvmVNETProfileCfgNoiseFloorOffset OBJECT-TYPE
	SYNTAX	INTEGER ( 0..255 )
	ACCESS  read-only
	STATUS  mandatory
	DESCRIPTION
	  "NAME = ;
	   DESC = The value of this object will suppress the \
                  impulsive backround noise in order to achieve \
                  silence suppression savings.
	   HELP = ;
	   CAPABILITIES = ;"
	DEFVAL { 0 }
	::= { nvmVNETProfileCfgEntry 37 }

nvmVNETProfileCfgDtmfGenBurstLength OBJECT-TYPE
	SYNTAX	INTEGER {
                time50msec  (1),
                time60msec  (2),
                time70msec  (3),
                time100msec (4)
                }
	ACCESS  read-only
	STATUS  mandatory
	DESCRIPTION
	  "NAME = ;
	   DESC = DTMF burst generation in milliseconds.; 
	   HELP = ;
	   CAPABILITIES = ;"
	DEFVAL { 100 }
	::= { nvmVNETProfileCfgEntry 38 }

nvmVNETProfileCfgDtmRegenBurstLength OBJECT-TYPE
	SYNTAX	INTEGER {
                time50msec  (1),
                time60msec  (2),
                time70msec  (3),
                time100msec (4)
                }
	ACCESS  read-only
	STATUS  mandatory
	DESCRIPTION
	  "NAME = ;
	   DESC = DTMF burst Regeneration length in milliseconds.;
	   HELP = ;
	   CAPABILITIES = ;"
	DEFVAL { 100 }
	::= { nvmVNETProfileCfgEntry 39 }

--  the VNET Voice Switching Profile Configuration Table 
--  (Configuration Parameters)

--  This table provides the VNET voice switching profile configuration parameters.
--  This table is used to view a profile of voice channel switching configuration
--  characteristics; of which, a subset may be used for a particular voice channel
--  (of a specific interface type) to define its switching configuration. (Configuration)

nvmVNETSwProfCfgTable OBJECT-TYPE
	SYNTAX  SEQUENCE OF NvmVNETSwProfCfgEntry
	ACCESS  not-accessible
	STATUS  mandatory
	DESCRIPTION
	  "NAME = ; 
	   DESC = The VNET Voice Switching Profile Configuration \
		  table.(Configuration);
	   HELP = ;
	   CAPABILITIES = NET_CFG, VPN_CFG;"
	::= { vnet-configuration 8 }

nvmVNETSwProfCfgEntry OBJECT-TYPE
	SYNTAX  NvmVNETSwProfCfgEntry
	ACCESS  not-accessible
	STATUS  mandatory
	DESCRIPTION
	  "NAME = ; 
	   DESC = An entry in the VNET Voice Switching Profile \
		  Configuration table. (Configuration);
	   HELP = ;
	   CAPABILITIES = ;"
	INDEX   { nvmVNETSwProfCfgProfileNum }
	::= { nvmVNETSwProfCfgTable 1 }

NvmVNETSwProfCfgEntry ::= SEQUENCE {
	nvmVNETSwProfCfgProfileNum		INTEGER,
	nvmVNETSwProfCfgOutCallRestrict		INTEGER,
	nvmVNETSwProfCfgInCallRestrict		INTEGER,
	nvmVNETSwProfCfgCUGID			INTEGER,
	nvmVNETSwProfCfgRestrictClassCd		INTEGER,
	nvmVNETSwProfCfgAutoCallEntNum		INTEGER,
	nvmVNETSwProfCfgCallNegStrategy		INTEGER,
	nvmVNETSwProfCfgTransmitPriority	INTEGER,
	nvmVNETSwProfCfgAutoCallType		INTEGER,
    nvmVNETSwProfCfgAddServerSelect     INTEGER,
    nvmVNETSwProfCfgOutCallMode         INTEGER
	}

nvmVNETSwProfCfgProfileNum OBJECT-TYPE
	SYNTAX	INTEGER (1..32)
	ACCESS  read-only
	STATUS  mandatory
	DESCRIPTION
	  "NAME = ;
	   DESC = The value of this object indicates the profile \
		  number.  Used as an index to the VNET Voice \
		  Switching Profile Configuration table. \
		  (Configuration);
	   HELP = ;
	   CAPABILITIES = ;"
	::= { nvmVNETSwProfCfgEntry 1 }

nvmVNETSwProfCfgOutCallRestrict OBJECT-TYPE
	SYNTAX	INTEGER {
		noRestriction (1),
		closedUserGroupCall (2),
		restrictionClassCall (3),
		bothCUGandRCCall (4),
		inhibitAll (5)
		}
	ACCESS  read-only
	STATUS  mandatory
	DESCRIPTION
	  "NAME = ;
	   DESC = The value of this object specifies how to \
		  handle outgoing calls for voice channel \
		  switching. (Configuration);
	   HELP = 2: include CUG ID in outgoing call. \
		  3: include restriction class in outgoing call. \
		  4: include both CUG ID and restriction \
		  class in outgoing call. \
		  5: outgoing call is not allowed.;
	   CAPABILITIES = ;"
	DEFVAL { noRestriction }
	::= { nvmVNETSwProfCfgEntry 2 }

nvmVNETSwProfCfgInCallRestrict OBJECT-TYPE
	SYNTAX	INTEGER {
		noRestriction (1),
		checkCUGID (2),
		checkRestrictionClassCode (3),
		cUGandPublicClassInhibit (4),
		inhibitAll (5)
		}
	ACCESS  read-only
	STATUS  mandatory
	DESCRIPTION
	  "NAME = ;
	   DESC = The value of this object specifies how to \
		  handle incoming calls for voice channel \
		  switching. (Configuration);
	   HELP = 2: check CUG ID in incoming call.  (Must \
		  match our CUG ID for call acceptance. \
		  3: check RCC in incoming call.  (Must be \
		  greater than or equal to our RCC for call \
		  acceptance. \
		  4: check both CUG and RCC in incoming \
		  call. \
		  5: incoming call is not allowed.;
	   CAPABILITIES = ;"
	DEFVAL { noRestriction }
	::= { nvmVNETSwProfCfgEntry 3 }

nvmVNETSwProfCfgCUGID OBJECT-TYPE
	SYNTAX	INTEGER (0..255)
	ACCESS  read-only
	STATUS  mandatory
	DESCRIPTION
	  "NAME = ;
	   DESC = The value of this object assigns the Closed \
		  User Group ID for a voice channel. (Configuration);
	   HELP = ;
	   CAPABILITIES = ;"
	DEFVAL { 0 }
	::= { nvmVNETSwProfCfgEntry 4 }

nvmVNETSwProfCfgRestrictClassCd OBJECT-TYPE
	SYNTAX	INTEGER (0..255)
	ACCESS  read-only
	STATUS  mandatory
	DESCRIPTION
	  "NAME = ;
	   DESC = The value of this object assigns the Restriction \
		  Class Code for a voice channel. (Configuration);
	   HELP = ;
	   CAPABILITIES = ;"
	DEFVAL { 0 }
	::= { nvmVNETSwProfCfgEntry 5 }

nvmVNETSwProfCfgAutoCallEntNum OBJECT-TYPE
	SYNTAX	INTEGER (0..32)
	ACCESS  read-only
	STATUS  mandatory
	DESCRIPTION
	  "NAME = ;
	   DESC = The value of this object provides a voice \
		  channel Auto Call destination number by \
		  specifying an index into the ingress table. \
		  (Configuration);
	   HELP = 0: auto call disabled. \
		  1-32: index to the ingress table entry where \
		  the dial number is specified. \
                  The auto call for the ISDN BRI voice card is always \
                  disabled.;
	   CAPABILITIES = ;"
	DEFVAL { 0 }
	::= { nvmVNETSwProfCfgEntry 6 }

nvmVNETSwProfCfgCallNegStrategy OBJECT-TYPE
	SYNTAX	INTEGER {
		specific (1),
		bandwidth (2),
		delay (3)
		}
	ACCESS  read-only
	STATUS  mandatory
	DESCRIPTION
	  "NAME = ;
	   DESC = The value of this object specifies the preference \
		  for the voice algorithm when an outgoing call is \
		  made. (Configuration);
	   HELP = specific: whatever is configured. \
		  bandwidth: bigger block size. \
		  delay: shorter block size.;
	   CAPABILITIES = ;"
	DEFVAL { specific }
	::= { nvmVNETSwProfCfgEntry 7 }

nvmVNETSwProfCfgTransmitPriority OBJECT-TYPE
	SYNTAX	INTEGER (0..15)
	ACCESS  read-only
	STATUS  mandatory
	DESCRIPTION
	  "NAME = ;
	   DESC = The value of this object assigns the priority \
		  of the voice data to be transmitted. (Configuration);
	   HELP = 0: lowest priority. \
		  15: highest priority.;
	   CAPABILITIES = ;"
	DEFVAL { 11 }
	::= { nvmVNETSwProfCfgEntry 8 }

nvmVNETSwProfCfgAutoCallType OBJECT-TYPE
	SYNTAX	INTEGER {
                normal             (1),
                masterHootnHoller  (2),
                slaveHootnHoller   (3)
                }
	ACCESS  read-only
	STATUS  mandatory
	DESCRIPTION
	  "NAME = ;
	   DESC = Indicates the type of auto-call \
                  switching to be performed by the \
                  voice channel.;
	   HELP = ;
	   CAPABILITIES = ;"
	DEFVAL { normal }
	::= { nvmVNETSwProfCfgEntry 9 }

nvmVNETSwProfCfgAddServerSelect OBJECT-TYPE
	SYNTAX	INTEGER {
                nas      (1),
                vncs     (2)
                }
	ACCESS  read-only
	STATUS  mandatory
	DESCRIPTION
	  "NAME = ;
	   DESC = Indicates which DNA server is used.;
	   HELP = ;
	   CAPABILITIES = ;"
	::= { nvmVNETSwProfCfgEntry 10 }

nvmVNETSwProfCfgOutCallMode OBJECT-TYPE
	SYNTAX	INTEGER {
                enblock-only (1),
                dynamic      (2)
                }
	ACCESS  read-only
	STATUS  mandatory
	DESCRIPTION
	  "NAME = ;
	   DESC = Indicates the type of call being made.;
	   HELP = ;
	   CAPABILITIES = ;"
	::= { nvmVNETSwProfCfgEntry 11 }


--  the VNET Voice Ingress Digit Filtering Configuration Table 
--  (Configuration Parameters)

--  This table provides the VNET voice ingress digit filtering configuration 
--  parameters. (Configuration)

nvmVNETIngressDigFilterTable OBJECT-TYPE
	SYNTAX  SEQUENCE OF NvmVNETIngressDigFilterEntry
	ACCESS  not-accessible
	STATUS  mandatory
	DESCRIPTION
	  "NAME = ; 
	   DESC = The VNET Voice Ingress Digit Filtering \
		  Configuration table. (Configuration);
	   HELP = ;
	   CAPABILITIES = NET_CFG, VPN_CFG;"
	::= { vnet-configuration 9 }

nvmVNETIngressDigFilterEntry OBJECT-TYPE
	SYNTAX  NvmVNETIngressDigFilterEntry
	ACCESS  not-accessible
	STATUS  mandatory
	DESCRIPTION
	  "NAME = ; 
	   DESC = An entry in the VNET Voice Ingress Digit \
		  Filtering Configuration table. (Configuration);
	   HELP = ;
	   CAPABILITIES = ;"
	INDEX   { nvmVNETIngressDigFilterIndex }
	::= { nvmVNETIngressDigFilterTable 1 }

NvmVNETIngressDigFilterEntry ::= SEQUENCE {
	nvmVNETIngressDigFilterIndex		INTEGER,
	nvmVNETIngressDigFilterIngressNum	DisplayString,
	nvmVNETIngressDigFilterManipString	DisplayString
	}

nvmVNETIngressDigFilterIndex OBJECT-TYPE
	SYNTAX	INTEGER (1..32)
	ACCESS  read-only
	STATUS  mandatory
	DESCRIPTION
	  "NAME = ;
	   DESC = The value of this object indicates the index to \
		  the ingress table.  Used as an index to the VNET \
		  Voice Ingress Digit Filtering Configuration table. \
		  Configuration);
	   HELP = ;
	   CAPABILITIES = ;"
	::= { nvmVNETIngressDigFilterEntry 1 }

nvmVNETIngressDigFilterIngressNum OBJECT-TYPE
	SYNTAX	DisplayString (SIZE (0..40))
	ACCESS  read-only
	STATUS  mandatory
	DESCRIPTION
	  "NAME = ;
	   DESC = The value of this object selects the digit \
		  pattern to be matched.  (Null terminated \
		  character string.) (Configuration);
	   HELP = Valid characters are decimal digits, '#', \
		  '*', '+', '[' and ']' .;
	   CAPABILITIES = ;"
	DEFVAL { "" }
	::= { nvmVNETIngressDigFilterEntry 2 }

nvmVNETIngressDigFilterManipString OBJECT-TYPE
	SYNTAX	DisplayString (SIZE (0..40))
	ACCESS  read-only
	STATUS  mandatory
	DESCRIPTION
	  "NAME = ;
	   DESC = The value of this object selects commands \
		  to produce the ingress digits for speed dial, \
		  call redirect, and source ID insertion features. \
		  (Configuration);
	   HELP = Valid characters are decimal digits, '#', \
		  '*', 'D', and 'I'.;
	   CAPABILITIES = ;"
	DEFVAL { "#" }
	::= { nvmVNETIngressDigFilterEntry 3 }


--  the VNET Voice Egress Digit Manipulation Configuration Table 
--  (Configuration Parameters)

--  This table provides the VNET voice egress digit manipulation configuration 
--  parameters. (Configuration)

nvmVNETEgressDigManipTable OBJECT-TYPE
	SYNTAX  SEQUENCE OF NvmVNETEgressDigManipEntry
	ACCESS  not-accessible
	STATUS  mandatory
	DESCRIPTION
	  "NAME = ; 
	   DESC = The VNET Voice Egress Digit Manipulation \
		  Configuration table. (Configuration);
	   HELP = ;
	   CAPABILITIES = NET_CFG, VPN_CFG;"
	::= { vnet-configuration 10 }

nvmVNETEgressDigManipEntry OBJECT-TYPE
	SYNTAX  NvmVNETEgressDigManipEntry
	ACCESS  not-accessible
	STATUS  mandatory
	DESCRIPTION
	  "NAME = ; 
	   DESC = An entry in the VNET Voice Egress Digit \
		  Manipulation Configuration table. (Configuration);
	   HELP = ;
	   CAPABILITIES = ;"
	INDEX   { nvmVNETEgressDigManipIndex }
	::= { nvmVNETEgressDigManipTable 1 }

NvmVNETEgressDigManipEntry ::= SEQUENCE {
	nvmVNETEgressDigManipIndex		INTEGER,
	nvmVNETEgressDigManipPhoneNum		DisplayString,
	nvmVNETEgressDigManipString		DisplayString,
	nvmVNETEgressDigManipChIDList		DisplayString
	}

nvmVNETEgressDigManipIndex OBJECT-TYPE
	SYNTAX	INTEGER (1..32)
	ACCESS  read-only
	STATUS  mandatory
	DESCRIPTION
	  "NAME = ;
	   DESC = The value of this object indicates the index to \
		  the egress table.  Used as an index to the VNET \
		  Voice Egress Digit Manipulation Configuration \
		  table. Configuration);
	   HELP = ;
	   CAPABILITIES = ;"
	::= { nvmVNETEgressDigManipEntry 1 }

nvmVNETEgressDigManipPhoneNum OBJECT-TYPE
	SYNTAX	DisplayString (SIZE (0..40))
	ACCESS  read-only
	STATUS  mandatory
	DESCRIPTION
	  "NAME = ;
	   DESC = The value of this object selects the phone \
		  number that voice channels are associated with. \
		  This is the number to be registered to the Address \
		  Server (RSA). (Configuration);
	   HELP = Valid characters are decimal digits, '#', and '*'.;
	   CAPABILITIES = ;"
	DEFVAL { "" }
	::= { nvmVNETEgressDigManipEntry 2 }

nvmVNETEgressDigManipString OBJECT-TYPE
	SYNTAX	DisplayString (SIZE (0..40))
	ACCESS  read-only
	STATUS  mandatory
	DESCRIPTION
	  "NAME = ;
	   DESC = The value of this object selects commands \
		  to produce the egress digits for FXO, E&M, \
		  or FXS 3-Port interface.  The result is the \
		  number to be sent to the connected phone \
		  device. (Configuration);
	   HELP = Valid characters are decimal digits, '#', '*', \
		  '+', 'D', 'H', and 'I'.  The character 'H' is \
		  used to trigger immediate dial handling by the PBX.;  
	   CAPABILITIES = ;"
	DEFVAL { "" }
	::= { nvmVNETEgressDigManipEntry 3 }

nvmVNETEgressDigManipChIDList OBJECT-TYPE
	SYNTAX	DisplayString (SIZE (0..70))
	ACCESS  read-only
	STATUS  mandatory
	DESCRIPTION
	  "NAME = ;
	   DESC = The value of this object selects voice channels \
		  associated with the phone number.  The valid \
		  string consists of the substring 'B1'~'B6', \
		  'C1'~'C12', 'D1'~'D12', and 'E1'~'E2'. \
		  (Configuration);
	   HELP = Valid characters are decimal digits, 'B', 'C', \
		  'D', and 'E'.;
	   CAPABILITIES = ;"
	DEFVAL { "" }
	::= { nvmVNETEgressDigManipEntry 4 }



-- *** STATUS groups/tables ***

--  Operational Parameter ("mcm") Groups/Tables (note: no parallel "nvm" objects
--  are defined for STATUS parameters.)


--  the VNET Voice Channel Status Display Table 

--  This table provides the VNET voice channel status display parameters.

mcmVNETChStatusTable OBJECT-TYPE
	SYNTAX  SEQUENCE OF McmVNETChStatusEntry
	ACCESS  not-accessible
	STATUS  mandatory
	DESCRIPTION
	  "NAME = ; 
	   DESC = The VNET Voice Channel Status Display table. \
	   HELP = ;
	   CAPABILITIES = NET_CFG, VPN_CFG;"
	::= { vnet-status 1 }

mcmVNETChStatusEntry OBJECT-TYPE
	SYNTAX  McmVNETChStatusEntry
	ACCESS  not-accessible
	STATUS  mandatory
	DESCRIPTION
	  "NAME = ; 
	   DESC = An entry in the VNET Voice Channel Status Display \
		  table.;
	   HELP = ;
	   CAPABILITIES = ;"
	INDEX   { mcmVNETChStatusLimID, mcmVNETChStatusChannelID }
	::= { mcmVNETChStatusTable 1 }

McmVNETChStatusEntry ::= SEQUENCE {
	mcmVNETChStatusLimID		INTEGER,
	mcmVNETChStatusChannelID		INTEGER,
	mcmVNETChStatusInterfaceType		INTEGER,
	mcmVNETChStatusInterfaceSwID		INTEGER,
	mcmVNETChStatusEMType			INTEGER,
	mcmVNETChStatusModelID			INTEGER,
	mcmVNETChStatusDSPOperation		INTEGER,
	mcmVNETChStatusNetworkConnect		INTEGER,
	mcmVNETChStatusRemoteChHwType		DisplayString,
	mcmVNETChStatusRemoteChNodeName		DisplayString,
	mcmVNETChStatusRemoteChNum		DisplayString,
	mcmVNETChStatusRemoteChIfType		DisplayString,
	mcmVNETChStatusRemoteFrameIfVer		INTEGER,
	mcmVNETChStatusRemoteChVoiceAlg		DisplayString,
	mcmVNETChStatusRemoteChFaxAlg		DisplayString,
	mcmVNETChStatusRemoteChModemAlg		DisplayString,
	mcmVNETChStatusSelfTestResult		INTEGER,
	mcmVNETChStatusFlashEPROM		INTEGER,
	mcmVNETChStatusEPROM			INTEGER,
	mcmVNETChStatusDspPROMVer		DisplayString,
	mcmVNETChStatusPROMID			DisplayString,
	mcmVNETChStatusInputLevel		INTEGER
	}

mcmVNETChStatusLimID OBJECT-TYPE
	SYNTAX	INTEGER {
		lim1 (2),
		lim2 (3),
		lim3 (4),
		lim4 (5),
		limB (6),
		limC (7),
		limD (8),
		limE (9)
		}
	ACCESS  read-only
	STATUS  mandatory
	DESCRIPTION
	  "NAME = ;
	   DESC = The card lim (logical interface module) number of \
		  a particular voice channel.  Used as an index to \
		  the VNET Voice Channel Status Display table.;
	   HELP = ;
	   CAPABILITIES = ;"
	::= { mcmVNETChStatusEntry 1 }

mcmVNETChStatusChannelID OBJECT-TYPE
	SYNTAX	INTEGER (1..12)
	ACCESS  read-only
	STATUS  mandatory
	DESCRIPTION
	  "NAME = ;
	   DESC = The position of the voice channel in the lim. \
		  Used as an index to the VNET Voice \
		  Channel Status Display table.;
	   HELP = ;
	   CAPABILITIES = ;"
	::= { mcmVNETChStatusEntry 2 }

mcmVNETChStatusInterfaceType OBJECT-TYPE
	SYNTAX	INTEGER {
		not-available (1),
		enhanced-loop-start-FXS (2),
		enhanced-EandM (3),
		enhanced-loop-start-FXO (4),
		low-cost-loop-start-FXS (5),
		low-cost-EandM (6),
		low-cost-loop-start-FXO (7),
		ground-start-FXS (8),
		ground-start-FXO (9),
		three-port (10),
		dvm (11),
		bri (12)
		}
	ACCESS  read-only
	STATUS  mandatory
	DESCRIPTION
	  "NAME = ; 
	   DESC = The value of this object indicates the interface \
		  type of the specified voice channel.;
	   HELP = Upon powerup, the interface type will not be \
		  available until the DSP software is loaded and its \
		  status is reported.;
	   CAPABILITIES = ;"
	::= { mcmVNETChStatusEntry 3 }

mcmVNETChStatusInterfaceSwID OBJECT-TYPE
	SYNTAX	INTEGER (0..255)
	ACCESS  read-only
	STATUS  mandatory
	DESCRIPTION
	  "NAME = ; 
	   DESC = The value of this object indicates the command \
		  interface version ID (CIVID) of the specified voice \
		  channel.  (Note: CIVID is 20 or above.);
	   HELP = ;
	   CAPABILITIES = ;"
	::= { mcmVNETChStatusEntry 4 }

mcmVNETChStatusEMType OBJECT-TYPE
	SYNTAX	INTEGER {
		typeI (1),
		typeII (2),
		typeIII (3),
		typeIV (4),
		typeV (5),
		notApplicable (6)
		}
	ACCESS  read-only
	STATUS  mandatory
	DESCRIPTION
	  "NAME = ;
	   DESC = The value of this object indicates the E&M \
		  type of the specified voice channel.;
	   HELP = This is for E&M interface channels only.  Other \
		  interface types will show notApplicable.;
	   CAPABILITIES = ;"
	::= { mcmVNETChStatusEntry 5 }

mcmVNETChStatusModelID OBJECT-TYPE
	SYNTAX	INTEGER {
		t1 (1),
		e1 (2),
		notApplicable (3)
		}
	ACCESS  read-only
	STATUS  mandatory
	DESCRIPTION
	  "NAME = ;
	   DESC = The value of this object indicates the hardware \
		  module type for the specified DVM voice channel.;
	   HELP = This is for DVM voice channels only.  Analog \
		  voice channels will show notApplicable.;
	   CAPABILITIES = ;"
	::= { mcmVNETChStatusEntry 6 }

mcmVNETChStatusDSPOperation OBJECT-TYPE
	SYNTAX	INTEGER {
		dead (1),
		notReady (2),
		downloadFailure (3),
		forceConnected (4),
		forceConnected-TimedOut (5),
		idle (6),
		switchConnectInProgress (7),
		switchConnected (8),
		switchDisconnectInProgress (9),
		busyOut (10),
		codeDownloadInProgress (11),
		pcmChannelNotInstalled (12)
		}
	ACCESS  read-only
	STATUS  mandatory
	DESCRIPTION
	  "NAME = ;
	   DESC = The value of this object indicates the current \
		  DSP status of the specified voice channel.;
	   HELP = ;
	   CAPABILITIES = ;"
	::= { mcmVNETChStatusEntry 7 }

mcmVNETChStatusNetworkConnect OBJECT-TYPE
	SYNTAX	INTEGER {
		idle (1),
		callInProgress (2),
		locallyConnected (3),
		remotelyConnected (4),
		disconnectInProgress (5)
		}
	ACCESS  read-only
	STATUS  mandatory
	DESCRIPTION
	  "NAME = ;
	   DESC = The value of this object indicates the current \
		  channel network connect status of the specified \
		  voice channel.;
	   HELP = ;
	   CAPABILITIES = ;"
	::= { mcmVNETChStatusEntry 8 }

mcmVNETChStatusRemoteChHwType OBJECT-TYPE
	SYNTAX	DisplayString (SIZE (0..15))
	ACCESS  read-only
	STATUS  mandatory
	DESCRIPTION
	  "NAME = ;
	   DESC = The value of this object indicates the remote \
		  voice channel hardware type (corresponding to \
		  the specified voice channel).;
	   HELP = This will be the NULL string if the specified \
		  voice channel is not connected.;
	   CAPABILITIES = ;"
	::= { mcmVNETChStatusEntry 9 }

mcmVNETChStatusRemoteChNodeName OBJECT-TYPE
	SYNTAX	DisplayString (SIZE (0..32))
	ACCESS  read-only
	STATUS  mandatory
	DESCRIPTION
	  "NAME = ;
	   DESC = The value of this object indicates the remote \
		  voice channel node name (corresponding to \
		  the specified voice channel).;
	   HELP = This will be the NULL string if the specified \
		  voice channel is not connected.;
	   CAPABILITIES = ;"
	::= { mcmVNETChStatusEntry 10 }

mcmVNETChStatusRemoteChNum OBJECT-TYPE
	SYNTAX	DisplayString (SIZE (0..7))
	ACCESS  read-only
	STATUS  mandatory
	DESCRIPTION
	  "NAME = ;
	   DESC = The value of this object indicates the remote \
		  voice channel number (corresponding to \
		  the specified voice channel).;
	   HELP = This will be the NULL string if the specified \
		  voice channel is not connected.;
	   CAPABILITIES = ;"
	::= { mcmVNETChStatusEntry 11 }

mcmVNETChStatusRemoteChIfType OBJECT-TYPE
	SYNTAX	DisplayString (SIZE (0..31))
	ACCESS  read-only
	STATUS  mandatory
	DESCRIPTION
	  "NAME = ;
	   DESC = The value of this object indicates the remote \
		  voice channel interface type (corresponding to \
		  the specified voice channel).;
	   HELP = This will be the NULL string if the specified \
		  voice channel is not connected.;
	   CAPABILITIES = ;"
	::= { mcmVNETChStatusEntry 12 }

mcmVNETChStatusRemoteFrameIfVer OBJECT-TYPE
	SYNTAX	INTEGER (0..255)
	ACCESS  read-only
	STATUS  mandatory
	DESCRIPTION
	  "NAME = ;
	   DESC = The value of this object indicates the final \
		  negotiated software version to be run on both \
		  sides of a voice channel connection.;
	   HELP = This will be 0 if the specified \
		  voice channel is not connected.;
	   CAPABILITIES = ;"
	::= { mcmVNETChStatusEntry 13 }

mcmVNETChStatusRemoteChVoiceAlg OBJECT-TYPE
	SYNTAX	DisplayString (SIZE (0..23))
	ACCESS  read-only
	STATUS  mandatory
	DESCRIPTION
	  "NAME = ;
	   DESC = The value of this object indicates the final \
		  negotiated voice algorithm running on both \
		  sides of a voice channel connection.;
	   HELP = This will be the NULL string if the specified \
		  voice channel is not connected.;
	   CAPABILITIES = ;"
	::= { mcmVNETChStatusEntry 14 }

mcmVNETChStatusRemoteChFaxAlg OBJECT-TYPE
	SYNTAX	DisplayString (SIZE (0..15))
	ACCESS  read-only
	STATUS  mandatory
	DESCRIPTION
	  "NAME = ;
	   DESC = The value of this object indicates the final \
		  negotiated voice fax algorithm and maximum \
		  speed running on both sides of a voice fax \
		  channel connection.;
	   HELP = This will be the NULL string if the specified \
		  voice fax channel is not connected.;
	   CAPABILITIES = ;"
	::= { mcmVNETChStatusEntry 15 }

mcmVNETChStatusRemoteChModemAlg OBJECT-TYPE
	SYNTAX	DisplayString (SIZE (0..15))
	ACCESS  read-only
	STATUS  mandatory
	DESCRIPTION
	  "NAME = ;
	   DESC = The value of this object indicates the final \
		  negotiated voice modem algorithm and maximum \
		  speed running on both sides of a voice modem \
		  channel connection.;
	   HELP = This will be the NULL string if the specified \
		  voice fax channel is not connected.;
	   CAPABILITIES = ;"
	::= { mcmVNETChStatusEntry 16 }

mcmVNETChStatusSelfTestResult OBJECT-TYPE
	SYNTAX	INTEGER {
		testPassed (1),
		testFailed (2)
		}
	ACCESS  read-only
	STATUS  mandatory
	DESCRIPTION
	  "NAME = ;
	   DESC = The value of this object indicates the results \
		  of a self test performed on the specified voice \
		  channel.;
	   HELP = ;
	   CAPABILITIES = ;"
	::= { mcmVNETChStatusEntry 17 }

mcmVNETChStatusFlashEPROM OBJECT-TYPE
	SYNTAX	INTEGER {
		notInstalled (1),
		valid (2),
		erased (3),
		invalidChecksum (4),
		noAnalogInterfaceDriver (5),
		securityViolation (6)
		}
	ACCESS  read-only
	STATUS  mandatory
	DESCRIPTION
	  "NAME = ;
	   DESC = The value of this object indicates the current \
		  flash EPROM status in the DSP of the specified \
		  voice channel.;
	   HELP = ;
	   CAPABILITIES = ;"
	::= { mcmVNETChStatusEntry 18 }

mcmVNETChStatusEPROM OBJECT-TYPE
	SYNTAX	INTEGER {
		notInstalled (1),
		currentlyOperating (2),
		presentButNotOperating (3)
		}
	ACCESS  read-only
	STATUS  mandatory
	DESCRIPTION
	  "NAME = ;
	   DESC = The value of this object indicates the current \
		  EPROM status in the DSP of the specified voice \
		  channel.;
	   HELP = ;
	   CAPABILITIES = ;"
	::= { mcmVNETChStatusEntry 19 }

mcmVNETChStatusDspPROMVer OBJECT-TYPE
	SYNTAX	DisplayString (SIZE (0..7))
	ACCESS  read-only
	STATUS  mandatory
	DESCRIPTION
	  "NAME = ;
	   DESC = The value of this object indicates the DSP PROM \
		  version of the specified voice channel.;
	   HELP = ;
	   CAPABILITIES = ;"
	::= { mcmVNETChStatusEntry 20 }

mcmVNETChStatusPROMID OBJECT-TYPE
	SYNTAX	DisplayString (SIZE (0..15))
	ACCESS  read-only
	STATUS  mandatory
	DESCRIPTION
	  "NAME = ;
	   DESC = The value of this object indicates the PROM \
		  ID of the specified voice channel.;
	   HELP = ;
	   CAPABILITIES = ;"
	::= { mcmVNETChStatusEntry 21 }

mcmVNETChStatusInputLevel OBJECT-TYPE
	SYNTAX	INTEGER {
		lessThanNeg25dBm (1),
		neg24dBm (2),
		neg21dBm (3),
		neg18dBm (4),
		neg15dBm (5),
		neg12dBm (6),
		neg10dBm (7),
		neg8dBm (8),
		neg6dBm (9),
		neg5dBm (10),
		neg4dBm (11),
		neg3dBm (12),
		neg2dBm (13),
		neg1dBm (14),
		zerodBm (15),
		greaterThan0dBm (16),
                notApplicable (17)
		}
	ACCESS  read-only
	STATUS  mandatory
	DESCRIPTION
	  "NAME = ;
	   DESC = The value of this object indicates the input \
		  level of the specified voice channel.;
	   HELP = ;
	   CAPABILITIES = ;"
	::= { mcmVNETChStatusEntry 22 }


-- VOICE SYSTEM STATUS

voiceSysStatusGroup    OBJECT IDENTIFIER ::= {vnet-status 2}

voiceSysStatusPhoneRegistrationStatus OBJECT-TYPE
    SYNTAX  INTEGER {
            registrationComplete (1),
            registrationInProgress (2),
            nasAddressNotConfigured (3),
            lostCommunicationWithNAS (4),
            noResponseFromNAS (5),
            registrationFailed (6)
            }
    ACCESS  read-only
    STATUS  mandatory
    DESCRIPTION
      "NAME = PhoneRegistrationStatus;
       DESC = Indicates current communications \
          status with NAS;
       HELP = ;
       CAPABILITIES = NET_CFG, VPN_CFG;"
    ::= { voiceSysStatusGroup 1}


-- *** STATISTICS groups/tables ***

--  Operational Parameter ("mcm") Groups/Tables (note: no parallel "nvm" objects
--  are defined for STATISTICS parameters.)


--  the VNET Voice Channel Statistics Counters Display Table 

--  This table provides the VNET voice channel statistics counters display parameters.

mcmVNETChStatsTable OBJECT-TYPE
	SYNTAX  SEQUENCE OF McmVNETChStatsEntry
	ACCESS  not-accessible
	STATUS  mandatory
	DESCRIPTION
	  "NAME = ; 
	   DESC = The VNET Voice Channel Statistics Display table. \
	   HELP = ;
	   CAPABILITIES = NET_CFG, VPN_CFG;"
	::= { vnet-statistics 1 }

mcmVNETChStatsEntry OBJECT-TYPE
	SYNTAX  McmVNETChStatsEntry
	ACCESS  not-accessible
	STATUS  mandatory
	DESCRIPTION
	  "NAME = ; 
	   DESC = An entry in the VNET Voice Channel Statistics \
		  Display table.;
	   HELP = ;
	   CAPABILITIES = ;"
	INDEX   { mcmVNETChStatsLimID, mcmVNETChStatsChannelID }
	::= { mcmVNETChStatsTable 1 }

McmVNETChStatsEntry ::= SEQUENCE {
	mcmVNETChStatsLimID		INTEGER,
	mcmVNETChStatsChannelID			INTEGER,
	mcmVNETChStatsOutCallConnTime		Counter,
	mcmVNETChStatsInCallConnTime		Counter,
	mcmVNETChStatsOutCallsSucceded		Counter,
	mcmVNETChStatsOutCallsFailed		Counter,
	mcmVNETChStatsInCallsAccepted		Counter,
	mcmVNETChStatsInCallsRejected		Counter,
	mcmVNETChStatsNumberOfResets		Counter,
	mcmVNETChStatsNumberOfRetries		Counter,
	mcmVNETChStatsBBCFramesRcvd		Counter,
	mcmVNETChStatsBEOFFramesRcvd		Counter,
	mcmVNETChStatsLostSpeechFrames		Counter,
	mcmVNETChStatsLostControlFrames		Counter,
	mcmVNETChStatsInvalPayloadFrRcvd	Counter,
	mcmVNETChStatsInvalPUMPMsgRcvd		Counter
	}

mcmVNETChStatsLimID OBJECT-TYPE
	SYNTAX	INTEGER {
		lim1 (2),
		lim2 (3),
		lim3 (4),
		lim4 (5),
		limB (6),
		limC (7),
		limD (8),
		limE (9)
		}
	ACCESS  read-only
	STATUS  mandatory
	DESCRIPTION
	  "NAME = ;
	   DESC = The card lim (logical interface module) number of a \
		  particular voice channel.  Used as an index to the \
		  VNET Voice Channel Statistics Display table.;
	   HELP = ;
	   CAPABILITIES = ;"
	::= { mcmVNETChStatsEntry 1 }

mcmVNETChStatsChannelID OBJECT-TYPE
	SYNTAX	INTEGER (1..12)
	ACCESS  read-only
	STATUS  mandatory
	DESCRIPTION
	  "NAME = ;
	   DESC = The position of the voice channel in the lim. \
		  Used as an index to the VNET Voice \
		  Channel Statistics Display table.;
	   HELP = ;
	   CAPABILITIES = ;"
	::= { mcmVNETChStatsEntry 2 }

mcmVNETChStatsOutCallConnTime OBJECT-TYPE
	SYNTAX	Counter
	ACCESS  read-only
	STATUS  mandatory
	DESCRIPTION
	  "NAME = ; 
	   DESC = The value of this object indicates the total \
		  connection time (in sec) since the last statistics \
		  reset for the specified voice channel outgoing \
		  calls.  (Excludes call setup time and local calls.) ;
	   HELP = ;
	   CAPABILITIES = ;"
	::= { mcmVNETChStatsEntry 3 }

mcmVNETChStatsInCallConnTime OBJECT-TYPE
	SYNTAX	Counter
	ACCESS  read-only
	STATUS  mandatory
	DESCRIPTION
	  "NAME = ; 
	   DESC = The value of this object indicates the total \
		  connection time (in sec) since the last statistics \
		  reset for the specified voice channel incoming \
		  calls.  (Excludes local calls.) ;
	   HELP = ;
	   CAPABILITIES = ;"
	::= { mcmVNETChStatsEntry 4 }

mcmVNETChStatsOutCallsSucceded OBJECT-TYPE
	SYNTAX	Counter
	ACCESS  read-only
	STATUS  mandatory
	DESCRIPTION
	  "NAME = ; 
	   DESC = The value of this object indicates the total \
		  number of positive call responses sent from the \
		  remote DSP since the last statistics reset \
		  for the specified voice channel.  (Excludes \
		  local calls.) ;
	   HELP = ;
	   CAPABILITIES = ;"
	::= { mcmVNETChStatsEntry 5 }

mcmVNETChStatsOutCallsFailed OBJECT-TYPE
	SYNTAX	Counter
	ACCESS  read-only
	STATUS  mandatory
	DESCRIPTION
	  "NAME = ; 
	   DESC = The value of this object indicates the total \
		  number of negative call responses sent from the \
		  remote DSP since the last statistics reset \
		  for the specified voice channel.  (Excludes \
		  local calls.) ;
	   HELP = ;
	   CAPABILITIES = ;"
	::= { mcmVNETChStatsEntry 6 }

mcmVNETChStatsInCallsAccepted OBJECT-TYPE
	SYNTAX	Counter
	ACCESS  read-only
	STATUS  mandatory
	DESCRIPTION
	  "NAME = ; 
	   DESC = The value of this object indicates the total \
		  number of positive call responses sent to the \
		  remote DSP since the last statistics reset \
		  for the specified voice channel.  (Excludes \
		  local calls.) ;
	   HELP = ;
	   CAPABILITIES = ;"
	::= { mcmVNETChStatsEntry 7 }

mcmVNETChStatsInCallsRejected OBJECT-TYPE
	SYNTAX	Counter
	ACCESS  read-only
	STATUS  mandatory
	DESCRIPTION
	  "NAME = ; 
	   DESC = The value of this object indicates the total \
		  number of negative call responses sent to the \
		  remote DSP since the last statistics reset \
		  for the specified voice channel.  (Excludes \
		  local calls.) ;
	   HELP = ;
	   CAPABILITIES = ;"
	::= { mcmVNETChStatsEntry 8 }

mcmVNETChStatsNumberOfResets OBJECT-TYPE
	SYNTAX	Counter
	ACCESS  read-only
	STATUS  mandatory
	DESCRIPTION
	  "NAME = ;
	   DESC = The value of this object indicates the total \
		  number of resets sent to the DSP corresponding \
		  to the specified voice channel.;
	   HELP = ;
	   CAPABILITIES = ;"
	::= { mcmVNETChStatsEntry 9 }

mcmVNETChStatsNumberOfRetries OBJECT-TYPE
	SYNTAX	Counter
	ACCESS  read-only
	STATUS  mandatory
	DESCRIPTION
	  "NAME = ;
	   DESC = The value of this object indicates the total \
		  number of no responses sent from the DSP \
		  since the last DSP reset corresponding \
		  to the specified voice channel.;
	   HELP = ;
	   CAPABILITIES = ;"
	::= { mcmVNETChStatsEntry 10 }

mcmVNETChStatsBBCFramesRcvd OBJECT-TYPE
	SYNTAX	Counter
	ACCESS  read-only
	STATUS  mandatory
	DESCRIPTION
	  "NAME = ;
	   DESC = The value of this object indicates the total \
		  number of frames with Bad Byte Count received \
		  from the DSP corresponding to the specified \
		  voice channel.;
	   HELP = ;
	   CAPABILITIES = ;"
	::= { mcmVNETChStatsEntry 11 }

mcmVNETChStatsBEOFFramesRcvd OBJECT-TYPE
	SYNTAX	Counter
	ACCESS  read-only
	STATUS  mandatory
	DESCRIPTION
	  "NAME = ;
	   DESC = The value of this object indicates the total \
		  number of frames with Bad End Of Frame \
		  character received from the DSP corresponding \
		  to the specified voice channel.;
	   HELP = ;
	   CAPABILITIES = ;"
	::= { mcmVNETChStatsEntry 12 }

mcmVNETChStatsLostSpeechFrames OBJECT-TYPE
	SYNTAX	Counter
	ACCESS  read-only
	STATUS  mandatory
	DESCRIPTION
	  "NAME = ;
	   DESC = The value of this object indicates the total \
		  number of speech frames sent by the remote \
		  that were lost since power up corresponding \
		  to the specified voice channel.;
	   HELP = Always 0 if sequence number in speech frame \
		  is not used.;
	   CAPABILITIES = ;"
	::= { mcmVNETChStatsEntry 13 }

mcmVNETChStatsLostControlFrames OBJECT-TYPE
	SYNTAX	Counter
	ACCESS  read-only
	STATUS  mandatory
	DESCRIPTION
	  "NAME = ;
	   DESC = The value of this object indicates the total \
		  number of control frames sent by the remote \
		  that were lost corresponding to the specified \
		  voice channel.;
	   HELP = ;
	   CAPABILITIES = ;"
	::= { mcmVNETChStatsEntry 14 }

mcmVNETChStatsInvalPayloadFrRcvd OBJECT-TYPE
	SYNTAX	Counter
	ACCESS  read-only
	STATUS  mandatory
	DESCRIPTION
	  "NAME = ;
	   DESC = The value of this object indicates the total \
		  number of payload frames received from the \
		  remote with bad length or frame type \
		  corresponding to the specified voice channel.;
	   HELP = ;
	   CAPABILITIES = ;"
	::= { mcmVNETChStatsEntry 15 }

mcmVNETChStatsInvalPUMPMsgRcvd OBJECT-TYPE
	SYNTAX	Counter
	ACCESS  read-only
	STATUS  mandatory
	DESCRIPTION
	  "NAME = ;
	   DESC = The value of this object indicates the total \
		  number of PUMP messages received from the \
		  remote with unknown message type, IEs, or \
		  invalid length corresponding to the specified \
		  voice channel.;
	   HELP = ;
	   CAPABILITIES = ;"
	::= { mcmVNETChStatsEntry 16 }


--  the VNET Voice Network Statistics Counters Display Group 

--  This group provides the VNET voice network statistics counters display parameters.

mcmVNETNetStatsGroup  OBJECT IDENTIFIER  ::= { vnet-statistics 2 }

mcmVNETNetStatsSucceedOutSVCCalls OBJECT-TYPE
	SYNTAX	Counter
	ACCESS  read-only
	STATUS  mandatory
	DESCRIPTION
	  "NAME = ; 
	   DESC = The value of this object indicates the total \
		  number of successful SVC calls since the \
		  last network statistics reset.;
	   HELP = ;
	   CAPABILITIES = NET_CFG, VPN_CFG ;"
	::= { mcmVNETNetStatsGroup 1 }

mcmVNETNetStatsFailedOutSVCCalls OBJECT-TYPE
	SYNTAX	Counter
	ACCESS  read-only
	STATUS  mandatory
	DESCRIPTION
	  "NAME = ; 
	   DESC = The value of this object indicates the total \
		  number of unsuccessful SVC calls since the \
		  last network statistics reset.;
	   HELP = ;
	   CAPABILITIES = NET_CFG, VPN_CFG ;"
	::= { mcmVNETNetStatsGroup 2 }

mcmVNETNetStatsAcceptedInCalls OBJECT-TYPE
	SYNTAX	Counter
	ACCESS  read-only
	STATUS  mandatory
	DESCRIPTION
	  "NAME = ; 
	   DESC = The value of this object indicates the total \
		  number of SVC calls accepted by this access device \
		  since the last network statistics reset.;
	   HELP = ;
	   CAPABILITIES = NET_CFG, VPN_CFG ;"
	::= { mcmVNETNetStatsGroup 3 }

mcmVNETNetStatsRejectedInCalls OBJECT-TYPE
	SYNTAX	Counter
	ACCESS  read-only
	STATUS  mandatory
	DESCRIPTION
	  "NAME = ; 
	   DESC = The value of this object indicates the total \
		  number of SVC calls rejected by this access device \
		  since the last network statistics reset.;
	   HELP = ;
	   CAPABILITIES = NET_CFG, VPN_CFG ;"
	::= { mcmVNETNetStatsGroup 4 }

mcmVNETNetStatsSucceedDNARequests OBJECT-TYPE
	SYNTAX	Counter
	ACCESS  read-only
	STATUS  mandatory
	DESCRIPTION
	  "NAME = ; 
	   DESC = The value of this object indicates the total \
		  number of successful DNA requests received \
		  by this access device since the last network \
		  statistics reset.;
	   HELP = ;
	   CAPABILITIES = NET_CFG, VPN_CFG ;"
	::= { mcmVNETNetStatsGroup 5 }

mcmVNETNetStatsFailedDNARequests OBJECT-TYPE
	SYNTAX	Counter
	ACCESS  read-only
	STATUS  mandatory
	DESCRIPTION
	  "NAME = ; 
	   DESC = The value of this object indicates the total \
		  number of unsuccessful DNA requests received \
		  by this access device since the last network \
		  statistics reset.;
	   HELP = ;
	   CAPABILITIES = NET_CFG, VPN_CFG ;"
	::= { mcmVNETNetStatsGroup 6 }

mcmVNETNetStatsFailedBuffAllocations OBJECT-TYPE
	SYNTAX	Counter
	ACCESS  read-only
	STATUS  mandatory
	DESCRIPTION
	  "NAME = ; 
	   DESC = The value of this object indicates the total \
		  number of streams buffers not available \
		  to this access device.;
	   HELP = ;
	   CAPABILITIES = NET_CFG, VPN_CFG ;"
	::= { mcmVNETNetStatsGroup 7 }

mcmVNETNetStatsNumActiveCalls OBJECT-TYPE
	SYNTAX	Counter
	ACCESS  read-only
	STATUS  mandatory
	DESCRIPTION
	  "NAME = ; 
	   DESC = The value of this object indicates the total \
		  number of calls in progress or connected \
		  in this access device.;
	   HELP = ;
	   CAPABILITIES = NET_CFG, VPN_CFG ;"
	::= { mcmVNETNetStatsGroup 8 }



-- *** CONTROL groups/tables ***

--  Operational Parameter ("mcm") Groups/Tables (note: no parallel "nvm" objects
--  are defined for CONTROL parameters.)


--  the VNET Voice Channel Control Table 

--  This table provides the VNET voice channel control/action commands.

mcmVNETChControlTable OBJECT-TYPE
	SYNTAX  SEQUENCE OF McmVNETChControlEntry
	ACCESS  not-accessible
	STATUS  mandatory
	DESCRIPTION
	  "NAME = ; 
	   DESC = The VNET Voice Channel Control table. \
	   HELP = ;
	   CAPABILITIES = NET_OPER, VPN_OPER ;"
	::= { vnet-control 1 }

mcmVNETChControlEntry OBJECT-TYPE
	SYNTAX  McmVNETChControlEntry
	ACCESS  not-accessible
	STATUS  mandatory
	DESCRIPTION
	  "NAME = ; 
	   DESC = An entry in the VNET Voice Channel Control \
		  table.;
	   HELP = ;
	   CAPABILITIES = ;"
	INDEX   { mcmVNETChControlLimID, mcmVNETChControlChannelID }
	::= { mcmVNETChControlTable 1 }

McmVNETChControlEntry ::= SEQUENCE {
	mcmVNETChControlLimID		INTEGER,
	mcmVNETChControlChannelID		INTEGER,
	mcmVNETChControlActionCmd		INTEGER
	}

mcmVNETChControlLimID OBJECT-TYPE
	SYNTAX	INTEGER {
		lim1 (2),
		lim2 (3),
		lim3 (4),
		lim4 (5),
		limB (6),
		limC (7),
		limD (8),
		limE (9)
		}
	ACCESS  read-only
	STATUS  mandatory
	DESCRIPTION
	  "NAME = ;
	   DESC = The card lim (logical interface module) number of a \
		  particular voice channel.  Used as an index to the \
		  VNET Voice Channel Control table.;
	   HELP = ;
	   CAPABILITIES = ;"
	::= { mcmVNETChControlEntry 1 }

mcmVNETChControlChannelID OBJECT-TYPE
	SYNTAX	INTEGER (1..12)
	ACCESS  read-only
	STATUS  mandatory
	DESCRIPTION
	  "NAME = ;
	   DESC = The position of the voice channel in the lim. \
		  Used as an index to the VNET Voice \
		  Channel Control table.;
	   HELP = ;
	   CAPABILITIES = ;"
	::= { mcmVNETChControlEntry 2 }

mcmVNETChControlActionCmd OBJECT-TYPE
	SYNTAX	INTEGER {
		resetChannel (1),
		clearChannelCounters (2),
		codeDownload (3),
		disconnect (4),
		loopbackTest (5),
		terminateTests (6),
		forceConnect (7)
		}
	ACCESS  write-only
	STATUS  mandatory
	DESCRIPTION
	  "NAME = ; 
	   DESC = Setting this object will perform various \
		  actions on the specified voice channel. \
		  Note: Starting with software release 3.0, \
		  the enumeration clearChannelCounters (2) is \
		  not supported. The enumeration is included \
		  here only to support backwards compatibility \
		  for software versions prior to release 3.0.; 
	   HELP = 1: perform hardware reset to DSP. \
		  2: clear statistics counter. \
		  3: download code to DSP. \
		  4: disconnect call. \
		  5: set DSP to loopback mode. \
		  6: terminate test. \
		  7: force connect channel by using the \
		  auto call number. NOTE: This option is not \
                  supported by the ISDN BRI voice card.;
	   CAPABILITIES = ;"
	::= { mcmVNETChControlEntry 3 }


--  the VNET Voice System Control Group 

--  This object provides the VNET voice system control/action commands.

mcmVNETSysControlActionCmd OBJECT-TYPE
	SYNTAX	INTEGER {
		clearNetworkCounters (1),
		resetChannels (2),
		clearChannelCounters (3),
		download (4),
		disconnect (5),
		loopbackTests (6),
		terminateTests (7),
		forceConnects (8),
                reRegisterPhoneNum (9)
		}
	ACCESS  write-only
	STATUS  mandatory
	DESCRIPTION
	  "NAME = ; 
	   DESC = Setting this object will perform various \
		  actions on the VNET voice system. \
		  Note: Starting with software release 3.0, \
		  the enumerations clearNetworkCounters (1) and \
		  clearChannelCounters (3) are not supported. \
		  The enumeration is included here only to support \
		  backwards compatibility for software versions \
		  prior to release 3.0.; 
	   HELP = 1: clear network statistics counters. \
		  2: perform hardware reset to all channels. \
		  3: clear all channel statistics counters. \
		  4: download code to all channels. \
		  5: disconnect all channel's calls. \
		  6: set all channels to loopback mode. \
		  7: terminate all channel's tests. \
		  8: force connect all channels by using the 
		  auto call numbers. NOTE: This option is not \
                  supported by the ISDN BRI voice card.; \
                  9: re-register phone number.;
	   CAPABILITIES = NET_OPER, VPN_OPER ;"
	::= { vnet-control 2 }

-- Trap Messages 

mcmVNETDownloadFail TRAP-TYPE
	ENTERPRISE	micom-2vnet
	VARIABLES	{mcmSysAsciiTimeOfDay, mcmVNETChCfgLimID, mcmVNETChCfgChannelID}
	DESCRIPTION
	  "NAME = ;
	   DESC = Indicates that a failure occurred while \
		  downloading the voice image.\
                  Severity Level: MAJOR.;
	   HELP = Downloading the voice image failed. Retry again, and if problem \
                  persists, please contact system admin., or field \
                  Personnel.;"
	::= 1

mcmVNETOutOfOrder TRAP-TYPE
	ENTERPRISE	micom-2vnet
	VARIABLES	{mcmSysAsciiTimeOfDay, mcmVNETChCfgLimID, mcmVNETChCfgChannelID}
	DESCRIPTION
	  "NAME = ;
	   DESC = Indicates that the DSP is not running. \
		  A channel reset may be required.;
	   HELP = DSP is not running. Reset voice channel(s). If problem still exist, \
                  contact sys admin. or Field Personnel.;"
	::= 2

mcmVNETOutOfOrderRecovered TRAP-TYPE
	ENTERPRISE	micom-2vnet
	VARIABLES	{mcmSysAsciiTimeOfDay, mcmVNETChCfgLimID, mcmVNETChCfgChannelID}
	DESCRIPTION
	  "NAME = ;
	   DESC = Indicates recovery from the out of order condition.\
                  Severity Level: CRITICAL.;
	   HELP = DSP is running. Normal status indication.;"
	::= 3

mcmVNETFailedToSyncUp TRAP-TYPE
	ENTERPRISE	micom-2vnet
	VARIABLES	{mcmSysAsciiTimeOfDay, mcmVNETChCfgLimID, mcmVNETChCfgChannelID}
	DESCRIPTION
	  "NAME = ;
	   DESC = Indicates that the DSP is running, \
		  but unable to sync up. A channel reset \
		  may be required.\
                  Severity Level: MAJOR.;
	   HELP = Reset channel(s). If Synchronization is not acquired, \
                  contact sys admin., or Field Personnel.;"
	::= 4

mcmVNETFailedToSyncUpRecovered TRAP-TYPE
	ENTERPRISE	micom-2vnet
	VARIABLES	{mcmSysAsciiTimeOfDay, mcmVNETChCfgLimID, mcmVNETChCfgChannelID}
	DESCRIPTION
	  "NAME = ;
	   DESC = Indicates recovery from the failure to \
		  sync up condition.\
                  Severity Level: INFORMATIVE. ;
	   HELP = Synchronization is acquired. Normal Status Indicator.;"
	::= 5

mcmVNETNoCVMCodeImage TRAP-TYPE
	ENTERPRISE	micom-2vnet
	VARIABLES	{mcmSysAsciiTimeOfDay}
	DESCRIPTION
	  "NAME = ;
	   DESC = Indicates that the built image doesn't \
		  contain CVM code\
                  Severity Level: MAJOR.;
	   HELP = Access device code does not contain image for CVM module. \
                  Please contact Sys Admin., or Field Personnel. ;"
	::= 6

mcmVNETNoTUVMCodeImage TRAP-TYPE
	ENTERPRISE	micom-2vnet
	VARIABLES	{mcmSysAsciiTimeOfDay}
	DESCRIPTION
	  "NAME = ;
	   DESC = Indicates that the built image doesn't \
		  contain TUVM code.\
		  Severity Level: MAJOR.;
	   HELP = Access device code does not contain image for TUVM module. \
                  Please contact Sys Admin., or Field Personnel. ;"
	::= 7

mcmVNETNoDVMCodeImage TRAP-TYPE
	ENTERPRISE	micom-2vnet
	VARIABLES	{mcmSysAsciiTimeOfDay}
	DESCRIPTION
	  "NAME = ;
	   DESC = Indicates that the built image doesn't \
	          contain DVM code.\
                  Severity Level: MAJOR.;
	   HELP = Access device code does not contain image for DVM module. \
                  Please contact Sys Admin., or Field Personnel. ;"
	::= 8

-- End of Trap Messages

END
