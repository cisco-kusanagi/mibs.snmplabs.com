XEDIA-AUTHENTICATION-MIB DEFINITIONS ::= BEGIN

IMPORTS 
    RowStatus, DisplayString
        FROM SNMPv2-TC

    MODULE-IDENTITY, OBJECT-TYPE,  
    Integer32, Counter32, Gauge32, TimeTicks
        FROM SNMPv2-SMI

    MODULE-COMPLIANCE, OBJECT-GROUP
        FROM SNMPv2-CONF

    xediaMibs
        FROM XEDIA-REG
    ;    

xediaAuthenticationMIB MODULE-IDENTITY
    LAST-UPDATED "9804142200Z" -- April 14, 1998   
    ORGANIZATION "Xedia Corp."
    CONTACT-INFO
        "support@xedia.com"
    DESCRIPTION
        "This module defines objects for the management of the
	User Authentication mechanism in Xedia devices."
    ::= { xediaMibs 17 }

-- Top-level organization of the MIB

xAuthenticationObjects          OBJECT IDENTIFIER ::= { xediaAuthenticationMIB 1 }
xAuthenticationConformance      OBJECT IDENTIFIER ::= { xediaAuthenticationMIB 2 }

-- Operational Objects, and User Table...

xAuthConfigObjects      OBJECT IDENTIFIER ::= { xAuthenticationObjects 1 } 
xAuthOperObjects        OBJECT IDENTIFIER ::= { xAuthenticationObjects 2 } 
xAuthUsers              OBJECT IDENTIFIER ::= { xAuthenticationObjects 3 }
xAuthDebugUserObjects   OBJECT IDENTIFIER ::= { xAuthenticationObjects 4 } 
xAuthUserStats          OBJECT IDENTIFIER ::= { xAuthUsers 1 }

--
-- Authentication Configuration Objects
--
xauthCfgUserActgSize OBJECT-TYPE
    SYNTAX      Integer32
    MAX-ACCESS  read-write
    STATUS      current
    DESCRIPTION
        "The configured size of the user accounting list.  Changes to this
         parameter require a node boot to take affect."
    DEFVAL      { 200 }
    ::= { xAuthConfigObjects 1 }

xauthCfgUserActgLogControl OBJECT-TYPE
    SYNTAX      BIT STRING {
                    logStart(0),
                    logStop(1),
                    logUpdate(2)
                }
    MAX-ACCESS  read-write
    STATUS      current
    DESCRIPTION
         "The preference determining which types of accounting messages will
         be recorded.  The 'logStart' will record all user session 'start'
         messages.  The 'logStop' will record all user session 'stop' messages.
         And 'logUpdate' will record any update messages that may be sent
         during a session."
    -- DEFVAL      { { logStart, logStop } }
    ::= { xAuthConfigObjects 2 }

xauthCfgEnableUserPasswordAuth OBJECT-TYPE
    SYNTAX      BIT STRING {
                    ipsec(0),
                    ppp(1)
                }
    MAX-ACCESS  read-write
    STATUS      current
    DESCRIPTION
         "The subsystems expected to perform username-password authentiation
          for dial-in users."
    -- DEFVAL      { { ipsec, ppp } }
    ::= { xAuthConfigObjects 3 }

--
-- Authentication Operational Stats
--
xauthOperUserActgSize OBJECT-TYPE
    SYNTAX      Integer32
    MAX-ACCESS  read-only
    STATUS      current
    DESCRIPTION
        "The operational size of the user accounting list."
    ::= { xAuthOperObjects 1 }

xauthOperUserActgIndexCurr OBJECT-TYPE
    SYNTAX      Gauge32
    MAX-ACCESS  read-only
    STATUS      current
    DESCRIPTION
        "The current index of the accounting list.  A zero is used to 
         represent an empty list."
    ::= { xAuthOperObjects 2 }

xauthOperAuthQCurr OBJECT-TYPE
    SYNTAX      Integer32
    MAX-ACCESS  read-only
    STATUS      current
    DESCRIPTION
        "The current number of elements in the Authentication queue."
    ::= { xAuthOperObjects 3 }

xauthOperAuthQMax OBJECT-TYPE
    SYNTAX      Gauge32
    MAX-ACCESS  read-only
    STATUS      current
    DESCRIPTION
        "The maximum number of elements in the Authentication queue
	 at one time."
    ::= { xAuthOperObjects 4 }

xauthOperAuthExpected OBJECT-TYPE
    SYNTAX      Integer32
    MAX-ACCESS  read-only
    STATUS      current
    DESCRIPTION
        "The expected number of elements in the Authentication queue by
	 monitoring the enqueue/dequeue operations."
    ::= { xAuthOperObjects 5 }

xauthOperAuthEnqueued OBJECT-TYPE
    SYNTAX      Counter32
    MAX-ACCESS  read-only
    STATUS      current
    DESCRIPTION
        "The number of requested posted to the Authentication queue."
    ::= { xAuthOperObjects 6 }

xauthOperAuthDequeued OBJECT-TYPE
    SYNTAX      Counter32
    MAX-ACCESS  read-only
    STATUS      current
    DESCRIPTION
        "The number of requested removed from the Authentication queue."
    ::= { xAuthOperObjects 7 }

xauthOperActgQCurr OBJECT-TYPE
    SYNTAX      Integer32
    MAX-ACCESS  read-only
    STATUS      current
    DESCRIPTION
        "The current number of elements in the Accounting queue."
    ::= { xAuthOperObjects 8 }

xauthOperActgQMax OBJECT-TYPE
    SYNTAX      Gauge32
    MAX-ACCESS  read-only
    STATUS      current
    DESCRIPTION
        "The maximum number of elements in the Accounting queue
	 at one time."
    ::= { xAuthOperObjects 9 }

xauthOperActgExpected OBJECT-TYPE
    SYNTAX      Integer32
    MAX-ACCESS  read-only
    STATUS      current
    DESCRIPTION
        "The expected number of elements in the Accounting queue by
	 monitoring the enqueue/dequeue operations."
    ::= { xAuthOperObjects 10 }

xauthOperActgEnqueued OBJECT-TYPE
    SYNTAX      Counter32
    MAX-ACCESS  read-only
    STATUS      current
    DESCRIPTION
        "The number of requested posted to the Accounting queue."
    ::= { xAuthOperObjects 11 }

xauthOperActgDequeued OBJECT-TYPE
    SYNTAX      Counter32
    MAX-ACCESS  read-only
    STATUS      current
    DESCRIPTION
        "The number of requested removed from the Accounting queue."
    ::= { xAuthOperObjects 12 }

xauthOperRespQCurr OBJECT-TYPE
    SYNTAX      Integer32
    MAX-ACCESS  read-only
    STATUS      current
    DESCRIPTION
        "The current number of elements in the Response queue."
    ::= { xAuthOperObjects 13 }

xauthOperRespQMax OBJECT-TYPE
    SYNTAX      Gauge32
    MAX-ACCESS  read-only
    STATUS      current
    DESCRIPTION
        "The maximum number of elements in the Response queue
	 at one time."
    ::= { xAuthOperObjects 14 }

xauthOperRespExpected OBJECT-TYPE
    SYNTAX      Integer32
    MAX-ACCESS  read-only
    STATUS      current
    DESCRIPTION
        "The expected number of elements in the Response queue by
	 monitoring the enqueue/dequeue operations."
    ::= { xAuthOperObjects 15 }

xauthOperRespEnqueued OBJECT-TYPE
    SYNTAX      Counter32
    MAX-ACCESS  read-only
    STATUS      current
    DESCRIPTION
        "The number of requested posted to the Response queue."
    ::= { xAuthOperObjects 16 }

xauthOperRespDequeued OBJECT-TYPE
    SYNTAX      Counter32
    MAX-ACCESS  read-only
    STATUS      current
    DESCRIPTION
        "The number of requested removed from the Response queue."
    ::= { xAuthOperObjects 17 }

xauthOperDeleteListCurr OBJECT-TYPE
    SYNTAX      Integer32
    MAX-ACCESS  read-only
    STATUS      current
    DESCRIPTION
        "The current number of elements in the Delete List."
    ::= { xAuthOperObjects 18 }

xauthOperDeleteListMax OBJECT-TYPE
    SYNTAX      Gauge32
    MAX-ACCESS  read-only
    STATUS      current
    DESCRIPTION
        "The maximum number of elements in the Delete List
	 at one time."
    ::= { xAuthOperObjects 19 }

xauthOperDeleteExpected OBJECT-TYPE
    SYNTAX      Integer32
    MAX-ACCESS  read-only
    STATUS      current
    DESCRIPTION
        "The expected number of elements in the Delete list by
	 monitoring the enqueue/dequeue operations."
    ::= { xAuthOperObjects 20 }

xauthOperDeleteEnqueued OBJECT-TYPE
    SYNTAX      Counter32
    MAX-ACCESS  read-only
    STATUS      current
    DESCRIPTION
        "The number of requested posted to the Delete list."
    ::= { xAuthOperObjects 21 }

xauthOperDeleteDequeued OBJECT-TYPE
    SYNTAX      Counter32
    MAX-ACCESS  read-only
    STATUS      current
    DESCRIPTION
        "The number of requested removed from the Delete list."
    ::= { xAuthOperObjects 22 }

xauthOperAuthReqTotal OBJECT-TYPE
    SYNTAX      Counter32
    MAX-ACCESS  read-only
    STATUS      current
    DESCRIPTION
        "The count of total authentication requests."
    ::= { xAuthOperObjects 23 }

xauthOperAuthReqPass OBJECT-TYPE
    SYNTAX      Counter32
    MAX-ACCESS  read-only
    STATUS      current
    DESCRIPTION
        "The count of authentication requests that were authenticated."
    ::= { xAuthOperObjects 24 }

xauthOperAuthReqFail OBJECT-TYPE
    SYNTAX      Counter32
    MAX-ACCESS  read-only
    STATUS      current
    DESCRIPTION
        "The count of total authentication requests that were
	 not authenticated due to timeouts, or rejects."
    ::= { xAuthOperObjects 25 }

xauthOperActgReqTotal OBJECT-TYPE
    SYNTAX      Counter32
    MAX-ACCESS  read-only
    STATUS      current
    DESCRIPTION
        "The count of total authentication requests."
    ::= { xAuthOperObjects 26 }

xauthOperActgResponse OBJECT-TYPE
    SYNTAX      Counter32
    MAX-ACCESS  read-only
    STATUS      current
    DESCRIPTION
        "The count of successful accounting responses."
    ::= { xAuthOperObjects 27 }

xauthOperActgFail OBJECT-TYPE
    SYNTAX      Counter32
    MAX-ACCESS  read-only
    STATUS      current
    DESCRIPTION
        "The count of accounting responses that were not successful."
    ::= { xAuthOperObjects 28 }

xauthOperBadRequests OBJECT-TYPE
    SYNTAX      Counter32
    MAX-ACCESS  read-only
    STATUS      current
    DESCRIPTION
        "The count of invalid requests from calling applications."
    ::= { xAuthOperObjects 29 }

--
-- Authentication/User Operational Stats
--
xauthUserUserCount OBJECT-TYPE
    SYNTAX      Integer32
    MAX-ACCESS  read-only
    STATUS      current
    DESCRIPTION
        "The current number of user entries defined."
    ::= { xAuthUserStats 1 }

-- ************************************************************
-- Authentication User Table
-- ************************************************************
xAuthUserTable        OBJECT-TYPE
    SYNTAX      SEQUENCE OF XAuthUserEntry
    MAX-ACCESS  not-accessible
    STATUS      current
    DESCRIPTION
        "The Authentication User table. Remote dial-in clients can be
        authenticated: locally using an internal database, or externally 
        using a Radius server server.  Clients are defined internally
        in this table. This table can have a special '<default>' entry
        that defines the default user authentication method and
        default client group name. The table lookup is always done first.
      
        If the client's name is not found a 'default' entry defines
        an alternative authentication methanism. If the 'default' entry
        is not defined, and the client is not found in the table, the
        client is denied access to the network, i.e. IPsec security
        associations will not be created. If the client's name is
        found in the table, the xauthUserAuthenProtocol
        defines which authenication mechanism is to be used.
      
        Specific users CAN be excluded by specifying 'always reject'
        in the authentication protocol.  The 'default' user can be
	set to 'always accept' to allow ALL undefined users to
        be automatically authenticated.

	For 'internal authentication', whether through a specific
        entry, or the default entry, the requested password must
        match the configured password. '

        Remote client example:
                xauthUserName           = xyz@company.com, 
                xauthUserPassword       = abc, 
                xauthUserClientGroup    = Engineering, 
                xauthUserAuthenProtocol = internalAuthentication."

    ::= { xAuthUsers 2 }
 
xAuthUserEntry     OBJECT-TYPE
    SYNTAX      XAuthUserEntry
    MAX-ACCESS  not-accessible
    STATUS      current
    DESCRIPTION
            "An entry containing information applicable to a
	     particular User."
    INDEX   { xauthUserName }
    ::= { xAuthUserTable 1 }

XAuthUserEntry ::=
    SEQUENCE {
      xauthUserName            DisplayString,
      xauthUserPassword        DisplayString,
      xauthUserClientGroup     DisplayString,
      xauthUserAuthenProtocol  INTEGER,
      xauthUserRowStatus       RowStatus
    }

xauthUserName OBJECT-TYPE
      SYNTAX      DisplayString (SIZE (1..32))
      MAX-ACCESS  not-accessible
      STATUS      current
      DESCRIPTION
        "The name of the remote client (like a user name). The name
        may be of the form User-Name or User-Name@company.com."
    ::= { xAuthUserEntry 1 }

xauthUserPassword OBJECT-TYPE
      SYNTAX      DisplayString (SIZE (0..32))
      MAX-ACCESS  read-create
      STATUS      current
      DESCRIPTION
        "The client's password, an ASCII string.  The password is used
         during 'internal authentication' by comparing it to the 
         password specified by the user."
      ::= { xAuthUserEntry 2 }

xauthUserClientGroup OBJECT-TYPE
      SYNTAX      DisplayString (SIZE (1..32))
      MAX-ACCESS  read-create
      STATUS      current
      DESCRIPTION
        "The client group name in clientGroupTable.

         For IPSec client connections, this object identifies the 
         IPSec client group tunnel or transport with which the
         client will be associated."
      ::= { xAuthUserEntry 3 }

xauthUserAuthenProtocol OBJECT-TYPE
      SYNTAX      INTEGER { alwaysReject(1),
			    internalAuthentication(2), 
			    radiusAuthentication(3),
			    alwaysAccept(4) }
      MAX-ACCESS  read-create
      STATUS      current
      DESCRIPTION
        "Defines the method of authentication.  Either individual
         users, or the <default> entry can accomodate various methods
         of authentication.  The 'always reject' will prohibit the
         corresponding user (specific or default) from ever being
         authenticated.  The use of 'always accept' will always 
         authenticate the corresponding user, regardless of which
         password was used.  'Internal Authentication' performs 
         password validation for a specific user.  'Radius Authentication'
         attempts to use a configured Radius server to determine whether
         or not a user is authenticated."
      DEFVAL      { internalAuthentication }
      ::= { xAuthUserEntry 4 }

xauthUserRowStatus OBJECT-TYPE
      SYNTAX      RowStatus
      MAX-ACCESS  read-create
      STATUS      current
      DESCRIPTION
        "This object allows entries to be created and deleted in this
         table."
    ::= { xAuthUserEntry 5 }


--
-- Authentication Debug User Objects
--
xauthDebugUserName OBJECT-TYPE
    SYNTAX      DisplayString
    MAX-ACCESS  read-write
    STATUS      current
    DESCRIPTION
        "The user name identifying which user is being debugged."
    ::= { xAuthDebugUserObjects 1 }

xAuthDebugUserTable        OBJECT-TYPE
    SYNTAX      SEQUENCE OF XAuthDebugUserEntry
    MAX-ACCESS  not-accessible
    STATUS      current
    DESCRIPTION
        "The Authentication Debug User table."
    ::= { xAuthDebugUserObjects 2 }
 
xAuthDebugUserEntry     OBJECT-TYPE
    SYNTAX      XAuthDebugUserEntry
    MAX-ACCESS  not-accessible
    STATUS      current
    DESCRIPTION
            "An entry containing debug information applicable to a
	     particular User."
    INDEX   { xauthDebugUserIndex }
    ::= { xAuthDebugUserTable 1 }

XAuthDebugUserEntry ::=
    SEQUENCE {
      xauthDebugUserIndex      Integer32,
      xauthDebugUserRequest    DisplayString,
      xauthDebugUserResponse   DisplayString,
      xauthDebugUserAppRequest DisplayString
    }

xauthDebugUserIndex OBJECT-TYPE
      SYNTAX      Integer32
      MAX-ACCESS  not-accessible
      STATUS      current
      DESCRIPTION
        "The index into the display table of debug information."
      ::= { xAuthDebugUserEntry 1 }

xauthDebugUserRequest OBJECT-TYPE
      SYNTAX      DisplayString 
      MAX-ACCESS  read-only 
      STATUS      current
      DESCRIPTION
        "Debug information related to the last request of the user 
	 currently being debugged."
    ::= { xAuthDebugUserEntry 2 }

xauthDebugUserResponse OBJECT-TYPE
      SYNTAX      DisplayString 
      MAX-ACCESS  read-only 
      STATUS      current
      DESCRIPTION
        "Debug information related to the last response of the user 
	 currently being debugged."
    ::= { xAuthDebugUserEntry 3 }

xauthDebugUserAppRequest OBJECT-TYPE
      SYNTAX      DisplayString 
      MAX-ACCESS  read-only 
      STATUS      current
      DESCRIPTION
        "Debug information related to the application's view of the
	 request (prior to it being issued) of the user currently 
	 being debugged."
    ::= { xAuthDebugUserEntry 4 }

-- ************************************************************
-- Additional Objects to track User Accounting stats
-- ************************************************************
xAuthUserActgTable        OBJECT-TYPE
    SYNTAX      SEQUENCE OF XAuthUserActgEntry
    MAX-ACCESS  not-accessible
    STATUS      current
    DESCRIPTION
            ""
    ::= { xAuthUsers 3 }
 
xAuthUserActgEntry     OBJECT-TYPE
    SYNTAX      XAuthUserActgEntry
    MAX-ACCESS  not-accessible
    STATUS      current
    DESCRIPTION
            "An entry containing additional management information"
    INDEX   { xauthUserActgIndex }
    ::= { xAuthUserActgTable 1 }

XAuthUserActgEntry ::=
    SEQUENCE {
      -- 
      -- Identification info
      --
      xauthUserActgIndex       Integer32,
      xauthUserActgName        DisplayString,
      xauthUserActgRecordType  INTEGER,
      xauthUserActgTunnelInfo  DisplayString,
      xauthUserActgSessionID   DisplayString,
      -- 
      -- Stats
      -- 
      xauthUserActgStartTime   TimeTicks,
      xauthUserActgEndTime     TimeTicks,
      xauthUserActgSessionTime Counter32,
      xauthUserActgRxBytes     Counter32,
      xauthUserActgTxBytes     Counter32,
      xauthUserActgRxPkts      Counter32,
      xauthUserActgTxPkts      Counter32
    }

xauthUserActgIndex OBJECT-TYPE
    SYNTAX      Integer32
    MAX-ACCESS  not-accessible
    STATUS      current
    DESCRIPTION
        "The numeric index into the circular list which represents 
	 the tunnel entries in the order inwhich they were created.
	 The list is of a limited length, as configured by the 
	 object 'xauthCfgUserActgSize', and the list wraps with the
	 oldest entries being replaced with the newest entries."
    ::= { xAuthUserActgEntry 1 }

xauthUserActgName OBJECT-TYPE
    SYNTAX      DisplayString
    MAX-ACCESS  read-only 
    STATUS      current
    DESCRIPTION
        "The username associated with the particular accounting record."
    ::= { xAuthUserActgEntry 2 }

xauthUserActgRecordType OBJECT-TYPE
    SYNTAX      INTEGER { start(1), stop(2), update(3) }
    MAX-ACCESS  read-only 
    STATUS      current
    DESCRIPTION
        "The record type of the recorded accounting entry.  The start/stop
        messages mark the beginning and ending of a user session.  The update
        messages are periodic statistics update messages that MAY be used by
        some of the internal application.  These update messages are optional."
	::= { xAuthUserActgEntry 3 }

xauthUserActgTunnelInfo OBJECT-TYPE
    SYNTAX      DisplayString
    MAX-ACCESS  read-only 
    STATUS      current
    DESCRIPTION
        "The additional tunnel and interface information associated with the
	 particular accounting record."
    ::= { xAuthUserActgEntry 4 }

xauthUserActgSessionID OBJECT-TYPE
    SYNTAX      DisplayString
    MAX-ACCESS  read-only 
    STATUS      current
    DESCRIPTION
        "The unique identification string of the session."
    ::= { xAuthUserActgEntry 5 }

xauthUserActgStartTime OBJECT-TYPE
    SYNTAX      TimeTicks
    MAX-ACCESS  read-only 
    STATUS      current
    DESCRIPTION
        "The value of sysUpTime (rounded to the full second value) at the 
	 creation of the session."
    ::= { xAuthUserActgEntry 6 }

xauthUserActgEndTime OBJECT-TYPE
    SYNTAX      TimeTicks
    MAX-ACCESS  read-only 
    STATUS      current
    DESCRIPTION
        "The value of sysUpTime (rounded to the full second value) at the 
	 termination of the session."
    ::= { xAuthUserActgEntry 7 }

xauthUserActgSessionTime OBJECT-TYPE
    SYNTAX      Counter32 
    MAX-ACCESS  read-only 
    STATUS      current
    DESCRIPTION
        "The number of seconds representing the duration of the session."
    ::= { xAuthUserActgEntry 8 }

xauthUserActgRxBytes OBJECT-TYPE
    SYNTAX      Counter32 
    MAX-ACCESS  read-only 
    STATUS      current
    DESCRIPTION
        "The number of bytes received during the particular session."
    ::= { xAuthUserActgEntry 9 }

xauthUserActgTxBytes OBJECT-TYPE
    SYNTAX      Counter32 
    MAX-ACCESS  read-only 
    STATUS      current
    DESCRIPTION
        "The number of bytes transmitted during the particular session."
    ::= { xAuthUserActgEntry 10 }

xauthUserActgRxPkts OBJECT-TYPE
    SYNTAX      Counter32 
    MAX-ACCESS  read-only 
    STATUS      current
    DESCRIPTION
        "The number of packets received during the particular session."
    ::= { xAuthUserActgEntry 11 }

xauthUserActgTxPkts OBJECT-TYPE
    SYNTAX      Counter32 
    MAX-ACCESS  read-only 
    STATUS      current
    DESCRIPTION
        "The number of packets transmitted during the particular session."
    ::= { xAuthUserActgEntry 12 }
 
-- ****************************************************************
-- Conformance Information
-- ****************************************************************
xauthCompliances OBJECT IDENTIFIER ::= { xAuthenticationConformance 1 }
xauthGroups      OBJECT IDENTIFIER ::= { xAuthenticationConformance 2 }

--
-- Compliance Statements
--
xauthCompliance MODULE-COMPLIANCE
    STATUS      current
    DESCRIPTION
        "The compliance statement for all agents that support this
        MIB. A compliant agent implements all objects defined in this
        MIB."
    MODULE 
    MANDATORY-GROUPS {
        xauthAllGroup
    }
    ::= { xauthCompliances 1 }

--
-- All Object Groups
--
xauthAllGroup OBJECT-GROUP
    OBJECTS {
      --
      -- Configured objects
      --
      xauthCfgUserActgSize,
      xauthCfgUserActgLogControl, 
      --
      -- Operational stats
      --
      xauthOperUserActgSize, 
      xauthOperUserActgIndexCurr,
      xauthOperAuthQCurr, 
      xauthOperAuthQMax,
      xauthOperAuthExpected,
      xauthOperAuthEnqueued,
      xauthOperAuthDequeued,
      xauthOperActgQCurr,
      xauthOperActgQMax,
      xauthOperActgExpected,
      xauthOperActgEnqueued,
      xauthOperActgDequeued,
      xauthOperRespQCurr,
      xauthOperRespQMax,
      xauthOperRespExpected,
      xauthOperRespEnqueued,
      xauthOperRespDequeued,
      xauthOperDeleteListCurr,
      xauthOperDeleteListMax,
      xauthOperDeleteExpected,
      xauthOperDeleteEnqueued,
      xauthOperDeleteDequeued,

      xauthOperAuthReqTotal,
      xauthOperAuthReqPass,
      xauthOperAuthReqFail,
      xauthOperActgReqTotal,
      xauthOperActgResponse,
      xauthOperActgFail,
      xauthOperBadRequests,
      --
      -- User stats
      --
      xauthUserUserCount,
      --
      -- User Table
      --
      xauthUserPassword,
      xauthUserClientGroup,
      xauthUserAuthenProtocol,
      xauthUserRowStatus,
      --
      -- Debug User Objects
      --
      xauthDebugUserName,
      xauthDebugUserRequest,
      xauthDebugUserResponse,
      xauthDebugUserAppRequest,
      --
      -- User Accounting Objects
      --
      xauthUserActgName,
      xauthUserActgRecordType,
      xauthUserActgTunnelInfo,
      xauthUserActgSessionID,
      xauthUserActgStartTime,
      xauthUserActgEndTime,
      xauthUserActgSessionTime,
      xauthUserActgRxBytes,
      xauthUserActgTxBytes,
      xauthUserActgRxPkts,
      xauthUserActgTxPkts
    }
    STATUS      current
    DESCRIPTION
        "The set of all accessible objects in this MIB."
    ::= { xauthGroups 1 }

END
