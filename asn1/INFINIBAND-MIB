-- extracted from draft-ietf-ipoib-ibif-mib-00.txt
-- at Fri Oct 12 06:06:33 2001

INFINIBAND-MIB DEFINITIONS ::= BEGIN

IMPORTS
       experimental, MODULE-IDENTITY,
       Integer32                                   FROM SNMPv2-SMI
       TEXTUAL-CONVENTION                          FROM SNMPv2-TC  
       ;

infinibandMIB MODULE-IDENTITY
    LAST-UPDATED "200110031200Z"  -- 3 October 2001 12:00:00
    ORGANIZATION
                 "IETF IP over IB Working Group 
         Email:   ipoverib@ietf.org"
    CONTACT-INFO
                 "Bill Anderson
          Postal: InfiniSwitch Corporation
                  134 Flanders Road
                  Westborough, MA 01581
                  United States
          Tel:    +1 508 599 6300
          Email:  banderson@infiniswitch.com
                  Bill Strahm
          Postal: Sanera Systems Inc
                  1925 NW Amberglen Parkway
                  Suite 155
                  Beaverton, OR   97006
                  United States
          Tel:    +1 503 601-0263
          Email:  bill@sanera.net"
    DESCRIPTION
       "This MIB contains managed object definitions and textual
        conventions for managing Infiniband devices."
    -- Revision history.
    REVISION    "200110031200Z"  -- 3 October 2001 12:00:00
    DESCRIPTION  "Initial version of this MIB."
::= { experimental  xxx } -- To be assigned by IANA


   -- Textual Conventions
   -- Note that the IBA Port TCs are one based.
   -- Making the port TCs be 1 based allows for IBA port numbers to
   -- possibly parallel ifIndex which is defined to start at 1. 
   -- The SNMP responder must make appropriate conversions to 
   -- IBA numbering scheme.

VLIdTC ::= TEXTUAL-CONVENTION
    DISPLAY-HINT "d"
    STATUS      current
    DESCRIPTION
       "Identifies a Virtual Lane instance on a given interface. This
        includes both the management and data Virtual Lanes. "
    SYNTAX       Integer32(0..15)

DataVLIdTC ::= TEXTUAL-CONVENTION
    DISPLAY-HINT "d"
    STATUS      current
    DESCRIPTION
       "Identifies a Data Virtual Lane instance on a given interface.
        This index exludes the management Virtual Lane."
    SYNTAX       Integer32(0..14)

IBPortTC ::= TEXTUAL-CONVENTION
    DISPLAY-HINT "d"
    STATUS      current
    DESCRIPTION
       "Identifies a IBA Port. Including the management and invalid
        port identifier."
    SYNTAX       Integer32(1..256)                                                                                  
IBPhyPortTC ::= TEXTUAL-CONVENTION
    DISPLAY-HINT "d"
    STATUS      current
    DESCRIPTION
       "Identifies a non management IBA Port. Including the invalid
        port identifier.
       "
    SYNTAX       Integer32(2..256)                                                                                  
IBValidPhyPortTC ::= TEXTUAL-CONVENTION
    STATUS      current
    DESCRIPTION
       "Identifies a valid non management IBA Port.
       "
    SYNTAX       Integer32(2..255)                                                                                  
LIdTC ::= TEXTUAL-CONVENTION
    DISPLAY-HINT "d"
    STATUS      current
    DESCRIPTION
       "Identifies the LID of a Desitination Port. LID value
        of 0x0 is considered invalid.
       "
    SYNTAX       Integer32 (1..65535)  

GUIDTC::= TEXTUAL-CONVENTION
    DISPLAY-HINT "1x:"
    STATUS      current
    DESCRIPTION
       "A locally  scoped EUI-64 identifier of channel adapters,
        routers, and switch management port."
    SYNTAX       OCTET STRING (SIZE(8))   

   --
   --  Object Identifier Assignments
   --  MIB writes must coordinate their use of this OID space.
END

--  
--    Copyright (C) The Internet Society (2000).  All Rights Reserved.
--  
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--  
--    The limited permissions granted above are perpetual and will not be
--    revoked by the Internet Society or its successors or assigns.
--  
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.            
-- 6.0  Intellectual Property
--  
--    The IETF takes no position regarding the validity or scope of any
--    intellectual property or other rights that might be claimed to
--    pertain to the implementation or use of the technology described in
--    this document or the extent to which any license under such rights
--    might or might not be available; neither does it represent that it
--    has made any effort to identify any such rights.  Information on the
--    IETF's procedures with respect to rights in standards-track and
--    standards- related documentation can be found in BCP-11.  Copies of
--    claims of rights made available for publication and any assurances of
--    licenses to be made available, or the result of an attempt made to
--    obtain a general license or permission for the use of such
--    proprietary rights by implementors or users of this specification can
--    be obtained from the IETF Secretariat. 
-- 
--    The IETF invites any interested party to bring to its attention any
--    copyrights, patents or patent applications, or other proprietary
--    rights which may cover technology that may be required to practice
--    this standard.  Please address the information to the IETF Executive
--    Director. 
--  
-- 7.0  Author's Address
--  
--    Name:    Bill Anderson
--    Company: Infiniswitch Corporation
--    Address: 134 Flanders Road
--             Westborough, MA 01581
--    Phone:   978-599-6336
--    EMail:   banderson@infiniswitch.com
-- 
-- 7.1  Known Issues
--      
-- 1)  Need REFERENCE clauses on object definitions to point to
--    definitions in InfiniBand docs.
--  
-- 8.0  References
-- 
-- [RFC2571]   Harrington, D., Presuhn, R., and B. Wijnen, "An Architecture
--             for Describing SNMP Management Frameworks", RFC 2571, April
--             1999.
-- 
-- [RFC1155]   Rose, M., and K. McCloghrie, "Structure and Identification
--             of Management Information for TCP/IP-based Internets", STD
--             16, RFC 1155, May 1990.
-- 
-- [RFC1212]   Rose, M., and K. McCloghrie, "Concise MIB Definitions", STD
--             16, RFC 1212, March 1991.
-- 
-- [RFC1215]   M. Rose, "A Convention for Defining Traps for use with the
--             SNMP", RFC 1215, March 1991.
-- 
-- [RFC2578]   McCloghrie, K., Perkins, D., Schoenwaelder, J., Case, J.,
--             Rose, M., and S. Waldbusser, "Structure of Management
--             Information Version 2 (SMIv2)", STD 58, RFC 2578, April 1999
-- [RFC2579]   McCloghrie, K., Perkins, D., Schoenwaelder, J., Case, J.,
--             Rose, M., and S. Waldbusser, "Textual Conventions for
--             SMIv2", STD 58, RFC 2579, April 1999.
-- 
-- [RFC2580]   McCloghrie, K., Perkins, D., Schoenwaelder, J., Case, J.,
--             Rose, M., and S. Waldbusser, "Conformance Statements for
--             SMIv2", STD 58, RFC 2580, April 1999.
-- 
-- [RFC1157]   Case, J., Fedor, M., Schoffstall, M., and J. Davin, "Simple
--             Network Management Protocol", STD 15, RFC 1157, May 1990.
-- 
-- [RFC1901]   Case, J., McCloghrie, K., Rose, M., and S. Waldbusser,
--             "Introduction to Community-based SNMPv2", RFC 1901, January
--             1996.
-- 
-- [RFC1906]   Case, J., McCloghrie, K., Rose, M., and S. Waldbusser,
--             "Transport Mappings for Version 2 of the Simple Network
--             Management Protocol (SNMPv2)", RFC 1906, January 1996.
-- 
-- [RFC2572]   Case, J., Harrington D., Presuhn R., and B. Wijnen, "Message
--             Processing and Dispatching for the Simple Network Management
--             Protocol (SNMP)", RFC 2572, April 1999.
-- 
-- [RFC2574]   Blumenthal, U., and B. Wijnen, "User-based Security Model
--             (USM) for version 3 of the Simple Network Management
--             Protocol (SNMPv3)", RFC 2574, April 1999.
-- 
-- [RFC1905]   Case, J., McCloghrie, K., Rose, M., and S. Waldbusser,
--             "Protocol Operations for Version 2 of the Simple Network
--             Management Protocol (SNMPv2)", RFC 1905, January 1996.
-- 
-- [RFC2573]   Levi, D., Meyer, P., and B. Stewart, "SNMPv3 Applications",
--             RFC 2573, April 1999.
-- 
-- [RFC2575]   Wijnen, B., Presuhn, R., and K. McCloghrie, "View-based
--             Access Control Model (VACM) for the Simple Network
--             Management Protocol (SNMP)", RFC 2575, April 1999.
-- 
-- [RFC2570]   Case, J., Mundy, R., Partain, D., and B. Stewart,
--             "Introduction to Version 3 of the Internet-standard Network
--             Management Framework", RFC 2570, April 1999.
-- --- end of Framework references
-- [RFC2863]   McCloghrie, K., and Kasenholz F.,
--             "The Interfaces Group MIB", RFC 2863, June 2000
-- 
-- [RFC2665]   Flick J.,and Johnson J.,
--             "Definitions of Managed Objects for the Ethernet-like
--             Interface Types", RFC 2863, August 1999
-- 
-- [Infini v1.0a] InfiniBand Architecture Specification, 
--                Volume 1.0 Version 1.0a
-- 
-- This Internet draft has an expiration date  of April 12, 2002
