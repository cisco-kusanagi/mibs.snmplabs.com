-- This MIB was created by extracting information from 
-- Sun Mangement Center 3.5 for use in other applications
-- to help determine what is actually listed in the SMC snmp 
-- agent. Sun has/will not release their MIBS for this 
-- information, so I created them from all information that
-- they have released.
--
-- Most all the information should be correct, but
-- if you find a discrepency please let me know. I do not
-- have all available Sun hardware to test with, so not 
-- not all types of support hardware has been tested.
-- These MIBs have only been tested using the utilities
-- from net-snmp. They may or may not work with other
-- applications.
-- 
-- The MIBs are not detailed, they only are useful in 
-- mapping OIDs to names. At some point in time 
-- descriptions may be given.
--
-- Author: Brian T. O'Neill (btoneill@misplaced.net)
-- Date: 7-30-2003 
-- Version: 0.9
--
-- No guarantees are given regarding the accuracy of this
-- data.
--
-- Note: The naming was done in line with the published
-- MIBS from Sun Microsystems.
--
--
READER4UDT-SUNMANAGEMENTCENTER-MIB DEFINITIONS ::= BEGIN

  IMPORTS
        enterprises, NOTIFICATION-TYPE, OBJECT-TYPE, MODULE-IDENTITY
                FROM SNMPv2-SMI;

sun             OBJECT IDENTIFIER ::= { enterprises 42 }
prod            OBJECT IDENTIFIER ::= { sun 2 }
sunsymon        OBJECT IDENTIFIER ::= { prod 12 }
agent           OBJECT IDENTIFIER ::= { sunsymon 2 }
base            OBJECT IDENTIFIER ::= { agent 1 }
modules         OBJECT IDENTIFIER ::= { agent 2 }
hardware        OBJECT IDENTIFIER ::= { modules 1 }
--
--
config          OBJECT IDENTIFIER ::= { hardware 1 }
reader4u        OBJECT IDENTIFIER ::= { config 1 }
reader4udt      OBJECT IDENTIFIER ::= { config 2 }
reader4uwg      OBJECT IDENTIFIER ::= { config 3 }
reader4u1P      OBJECT IDENTIFIER ::= { config 4 }
reader4u1D      OBJECT IDENTIFIER ::= { config 5 }
reader4unt      OBJECT IDENTIFIER ::= { config 6 }
readerSerengeti OBJECT IDENTIFIER ::= { config 7 }
reader4uvh      OBJECT IDENTIFIER ::= { config 8 }
readerECP       OBJECT IDENTIFIER ::= { config 9 }
readerELP       OBJECT IDENTIFIER ::= { config 10 }


sunwafb-entry	OBJECT IDENTIFIER ::= { sunwafbTbl 1 }
sunSmTreeProp	OBJECT IDENTIFIER ::= { ppm-entry 1 }
sunSmNodeName	OBJECT IDENTIFIER ::= { ppm-entry 2 }
entry-no	OBJECT IDENTIFIER ::= { ppm-entry 3 }
pathname-element	OBJECT IDENTIFIER ::= { ppm-entry 4 }
sunSmTreeProp	OBJECT IDENTIFIER ::= { networkEntry 1 }
sunSmNodeName	OBJECT IDENTIFIER ::= { networkEntry 2 }
entry-no	OBJECT IDENTIFIER ::= { networkEntry 3 }
device-type	OBJECT IDENTIFIER ::= { networkEntry 4 }
ether	OBJECT IDENTIFIER ::= { networkEntry 5 }
inet	OBJECT IDENTIFIER ::= { networkEntry 6 }
interface-name	OBJECT IDENTIFIER ::= { networkEntry 7 }
node-hierarchy	OBJECT IDENTIFIER ::= { networkEntry 8 }
symbolic-name	OBJECT IDENTIFIER ::= { networkEntry 9 }
reg	OBJECT IDENTIFIER ::= { networkEntry 10 }
cpu-unitTbl	OBJECT IDENTIFIER ::= { cpu-unit 1 }
sunSmTreeProp	OBJECT IDENTIFIER ::= { pci108e5043-entry 1 }
sunSmNodeName	OBJECT IDENTIFIER ::= { pci108e5043-entry 2 }
entry-no	OBJECT IDENTIFIER ::= { pci108e5043-entry 3 }
pathname-element	OBJECT IDENTIFIER ::= { pci108e5043-entry 4 }
power-supplyTbl	OBJECT IDENTIFIER ::= { power-supply 1 }
sunSmTreeProp	OBJECT IDENTIFIER ::= { power-supply-entry 1 }
sunSmNodeName	OBJECT IDENTIFIER ::= { power-supply-entry 2 }
entry-no	OBJECT IDENTIFIER ::= { power-supply-entry 3 }
fru	OBJECT IDENTIFIER ::= { power-supply-entry 4 }
state	OBJECT IDENTIFIER ::= { power-supply-entry 5 }
counter-timer-entry	OBJECT IDENTIFIER ::= { counter-timerTbl 1 }
sysctrlTbl	OBJECT IDENTIFIER ::= { sysctrl 1 }
sunSmTreeProp	OBJECT IDENTIFIER ::= { simm-entry 1 }
sunSmNodeName	OBJECT IDENTIFIER ::= { simm-entry 2 }
entry-no	OBJECT IDENTIFIER ::= { simm-entry 3 }
board-reference-number	OBJECT IDENTIFIER ::= { simm-entry 4 }
fru	OBJECT IDENTIFIER ::= { simm-entry 5 }
size	OBJECT IDENTIFIER ::= { simm-entry 6 }
slot	OBJECT IDENTIFIER ::= { simm-entry 7 }
type	OBJECT IDENTIFIER ::= { simm-entry 8 }
counter-timerTbl	OBJECT IDENTIFIER ::= { counter-timer 1 }
eepromTbl	OBJECT IDENTIFIER ::= { eeprom 1 }
ps-fan-entry	OBJECT IDENTIFIER ::= { power-supply-fansTbl 1 }
sunSmTreeProp	OBJECT IDENTIFIER ::= { memory-controller-entry 1 }
sunSmNodeName	OBJECT IDENTIFIER ::= { memory-controller-entry 2 }
entry-no	OBJECT IDENTIFIER ::= { memory-controller-entry 3 }
pathname-element	OBJECT IDENTIFIER ::= { memory-controller-entry 4 }
flashprom-entry	OBJECT IDENTIFIER ::= { flashpromTbl 1 }
sunSmTreeProp	OBJECT IDENTIFIER ::= { sunwUltra-10 1 }
sunSmNodeName	OBJECT IDENTIFIER ::= { sunwUltra-10 2 }
slotTbl	OBJECT IDENTIFIER ::= { slot 1 }
sunSmTreeProp	OBJECT IDENTIFIER ::= { ps-fan-entry 1 }
sunSmNodeName	OBJECT IDENTIFIER ::= { ps-fan-entry 2 }
entry-no	OBJECT IDENTIFIER ::= { ps-fan-entry 3 }
status	OBJECT IDENTIFIER ::= { ps-fan-entry 4 }
sunSmTreeProp	OBJECT IDENTIFIER ::= { io-controllerEntry 1 }
sunSmNodeName	OBJECT IDENTIFIER ::= { io-controllerEntry 2 }
entry-no	OBJECT IDENTIFIER ::= { io-controllerEntry 3 }
board-num	OBJECT IDENTIFIER ::= { io-controllerEntry 4 }
clock-frequency	OBJECT IDENTIFIER ::= { io-controllerEntry 5 }
device-type	OBJECT IDENTIFIER ::= { io-controllerEntry 6 }
instance	OBJECT IDENTIFIER ::= { io-controllerEntry 7 }
model	OBJECT IDENTIFIER ::= { io-controllerEntry 8 }
reg	OBJECT IDENTIFIER ::= { io-controllerEntry 9 }
upa-mid	OBJECT IDENTIFIER ::= { io-controllerEntry 10 }
upa-portid	OBJECT IDENTIFIER ::= { io-controllerEntry 11 }
version-no	OBJECT IDENTIFIER ::= { io-controllerEntry 12 }
generic-deviceTbl	OBJECT IDENTIFIER ::= { generic-device 1 }
sunSmTreeProp	OBJECT IDENTIFIER ::= { dimm-entry 1 }
sunSmNodeName	OBJECT IDENTIFIER ::= { dimm-entry 2 }
entry-no	OBJECT IDENTIFIER ::= { dimm-entry 3 }
device-type	OBJECT IDENTIFIER ::= { dimm-entry 4 }
fru	OBJECT IDENTIFIER ::= { dimm-entry 5 }
fru-device	OBJECT IDENTIFIER ::= { dimm-entry 6 }
module-size	OBJECT IDENTIFIER ::= { dimm-entry 7 }
socket-name	OBJECT IDENTIFIER ::= { dimm-entry 8 }
status	OBJECT IDENTIFIER ::= { dimm-entry 9 }
generic-device-entry	OBJECT IDENTIFIER ::= { generic-deviceTbl 1 }
io-controllerEntry	OBJECT IDENTIFIER ::= { io-controllerTbl 1 }
cpu-unit-entry	OBJECT IDENTIFIER ::= { cpu-unitTbl 1 }
sunwffbTbl	OBJECT IDENTIFIER ::= { sunwffb 1 }
sunSmTreeProp	OBJECT IDENTIFIER ::= { sunwafb-entry 1 }
sunSmNodeName	OBJECT IDENTIFIER ::= { sunwafb-entry 2 }
entry-no	OBJECT IDENTIFIER ::= { sunwafb-entry 3 }
dram3	OBJECT IDENTIFIER ::= { sunwafb-entry 4 }
dac	OBJECT IDENTIFIER ::= { sunwafb-entry 5 }
fbc-version	OBJECT IDENTIFIER ::= { sunwafb-entry 6 }
board-type	OBJECT IDENTIFIER ::= { sunwafb-entry 7 }
buffer	OBJECT IDENTIFIER ::= { sunwafb-entry 8 }
device-type	OBJECT IDENTIFIER ::= { sunwafb-entry 9 }
height	OBJECT IDENTIFIER ::= { sunwafb-entry 10 }
model	OBJECT IDENTIFIER ::= { sunwafb-entry 11 }
revision	OBJECT IDENTIFIER ::= { sunwafb-entry 12 }
upa-portid	OBJECT IDENTIFIER ::= { sunwafb-entry 13 }
width	OBJECT IDENTIFIER ::= { sunwafb-entry 14 }
eeprom-entry	OBJECT IDENTIFIER ::= { eepromTbl 1 }
simmTbl	OBJECT IDENTIFIER ::= { simm 1 }
bankTbl	OBJECT IDENTIFIER ::= { bank 1 }
dimmTbl	OBJECT IDENTIFIER ::= { dimm 1 }
power-supply-fansTbl	OBJECT IDENTIFIER ::= { power-supply-fans 1 }
tapeTbl	OBJECT IDENTIFIER ::= { tape 1 }
system	OBJECT IDENTIFIER ::= { reader4udt 1 }
system-board	OBJECT IDENTIFIER ::= { reader4udt 2 }
sunwUltra-1	OBJECT IDENTIFIER ::= { reader4udt 3 }
sunwUltra-2	OBJECT IDENTIFIER ::= { reader4udt 4 }
sunwUltra-4	OBJECT IDENTIFIER ::= { reader4udt 5 }
sunwUltra-30	OBJECT IDENTIFIER ::= { reader4udt 6 }
sunwUltra-60	OBJECT IDENTIFIER ::= { reader4udt 7 }
sunwUltra-80	OBJECT IDENTIFIER ::= { reader4udt 8 }
sunwBlade-100	OBJECT IDENTIFIER ::= { reader4udt 9 }
sunwBlade-1000	OBJECT IDENTIFIER ::= { reader4udt 10 }
sunwUltra-5	OBJECT IDENTIFIER ::= { reader4udt 11 }
sunwUltra-10	OBJECT IDENTIFIER ::= { reader4udt 12 }
sunwUltra-5-10	OBJECT IDENTIFIER ::= { reader4udt 13 }
slot	OBJECT IDENTIFIER ::= { reader4udt 14 }
cpu-unit	OBJECT IDENTIFIER ::= { reader4udt 15 }
mc	OBJECT IDENTIFIER ::= { reader4udt 16 }
bank	OBJECT IDENTIFIER ::= { reader4udt 17 }
dimm	OBJECT IDENTIFIER ::= { reader4udt 18 }
power-supply	OBJECT IDENTIFIER ::= { reader4udt 19 }
cpu-fans	OBJECT IDENTIFIER ::= { reader4udt 20 }
power-supply-fans	OBJECT IDENTIFIER ::= { reader4udt 21 }
simm	OBJECT IDENTIFIER ::= { reader4udt 22 }
flashprom	OBJECT IDENTIFIER ::= { reader4udt 23 }
eeprom	OBJECT IDENTIFIER ::= { reader4udt 24 }
sysctrl	OBJECT IDENTIFIER ::= { reader4udt 25 }
fan	OBJECT IDENTIFIER ::= { reader4udt 26 }
memory	OBJECT IDENTIFIER ::= { reader4udt 27 }
memory-controller	OBJECT IDENTIFIER ::= { reader4udt 28 }
counter-timer	OBJECT IDENTIFIER ::= { reader4udt 29 }
generic-device	OBJECT IDENTIFIER ::= { reader4udt 30 }
pci108e5043	OBJECT IDENTIFIER ::= { reader4udt 31 }
ffb	OBJECT IDENTIFIER ::= { reader4udt 32 }
afb	OBJECT IDENTIFIER ::= { reader4udt 33 }
sunwffb	OBJECT IDENTIFIER ::= { reader4udt 34 }
sunwafb	OBJECT IDENTIFIER ::= { reader4udt 35 }
hardware-rules	OBJECT IDENTIFIER ::= { reader4udt 36 }
io-controller	OBJECT IDENTIFIER ::= { reader4udt 37 }
io-device	OBJECT IDENTIFIER ::= { reader4udt 38 }
disk	OBJECT IDENTIFIER ::= { reader4udt 39 }
tape	OBJECT IDENTIFIER ::= { reader4udt 40 }
network	OBJECT IDENTIFIER ::= { reader4udt 41 }
io-unit	OBJECT IDENTIFIER ::= { reader4udt 42 }
ppm	OBJECT IDENTIFIER ::= { reader4udt 43 }
upa64s	OBJECT IDENTIFIER ::= { reader4udt 44 }
ppmTbl	OBJECT IDENTIFIER ::= { ppm 1 }
bank-entry	OBJECT IDENTIFIER ::= { bankTbl 1 }
sunSmTreeProp	OBJECT IDENTIFIER ::= { eeprom-entry 1 }
sunSmNodeName	OBJECT IDENTIFIER ::= { eeprom-entry 2 }
entry-no	OBJECT IDENTIFIER ::= { eeprom-entry 3 }
model	OBJECT IDENTIFIER ::= { eeprom-entry 4 }
reg	OBJECT IDENTIFIER ::= { eeprom-entry 5 }
sunSmTreeProp	OBJECT IDENTIFIER ::= { io-unitEntry 1 }
sunSmNodeName	OBJECT IDENTIFIER ::= { io-unitEntry 2 }
entry-no	OBJECT IDENTIFIER ::= { io-unitEntry 3 }
board-num	OBJECT IDENTIFIER ::= { io-unitEntry 4 }
device-id	OBJECT IDENTIFIER ::= { io-unitEntry 5 }
instance	OBJECT IDENTIFIER ::= { io-unitEntry 6 }
reg	OBJECT IDENTIFIER ::= { io-unitEntry 7 }
ffb-entry	OBJECT IDENTIFIER ::= { ffbTbl 1 }
mc-entry	OBJECT IDENTIFIER ::= { mcTbl 1 }
sunSmTreeProp	OBJECT IDENTIFIER ::= { ffb-entry 1 }
sunSmNodeName	OBJECT IDENTIFIER ::= { ffb-entry 2 }
entry-no	OBJECT IDENTIFIER ::= { ffb-entry 3 }
buffer	OBJECT IDENTIFIER ::= { ffb-entry 4 }
device-type	OBJECT IDENTIFIER ::= { ffb-entry 5 }
model	OBJECT IDENTIFIER ::= { ffb-entry 6 }
pathname-element	OBJECT IDENTIFIER ::= { ffb-entry 7 }
sunwafbTbl	OBJECT IDENTIFIER ::= { sunwafb 1 }
cpu-fansTbl	OBJECT IDENTIFIER ::= { cpu-fans 1 }
afb-entry	OBJECT IDENTIFIER ::= { afbTbl 1 }
sunSmTreeProp	OBJECT IDENTIFIER ::= { bank-entry 1 }
sunSmNodeName	OBJECT IDENTIFIER ::= { bank-entry 2 }
entry-no	OBJECT IDENTIFIER ::= { bank-entry 3 }
bank-size	OBJECT IDENTIFIER ::= { bank-entry 4 }
device-type	OBJECT IDENTIFIER ::= { bank-entry 5 }
fru-device	OBJECT IDENTIFIER ::= { bank-entry 6 }
status	OBJECT IDENTIFIER ::= { bank-entry 7 }
reader4udt	OBJECT IDENTIFIER ::= { config 2 }
simm-entry	OBJECT IDENTIFIER ::= { simmTbl 1 }
sunSmTreeProp	OBJECT IDENTIFIER ::= { sunwBlade-100 1 }
sunSmNodeName	OBJECT IDENTIFIER ::= { sunwBlade-100 2 }
fan-entry	OBJECT IDENTIFIER ::= { cpu-fansTbl 1 }
flashpromTbl	OBJECT IDENTIFIER ::= { flashprom 1 }
io-deviceEntry	OBJECT IDENTIFIER ::= { io-deviceTbl 1 }
memoryTbl	OBJECT IDENTIFIER ::= { memory 1 }
memory-entry	OBJECT IDENTIFIER ::= { memoryTbl 1 }
sunSmTreeProp	OBJECT IDENTIFIER ::= { sunwUltra-60 1 }
sunSmNodeName	OBJECT IDENTIFIER ::= { sunwUltra-60 2 }
sunSmTreeProp	OBJECT IDENTIFIER ::= { system 1 }
sunSmNodeName	OBJECT IDENTIFIER ::= { system 2 }
os	OBJECT IDENTIFIER ::= { system 3 }
os-version	OBJECT IDENTIFIER ::= { system 4 }
system-clock-frequency	OBJECT IDENTIFIER ::= { system 5 }
architecture	OBJECT IDENTIFIER ::= { system 6 }
hostname	OBJECT IDENTIFIER ::= { system 7 }
machine	OBJECT IDENTIFIER ::= { system 8 }
platform	OBJECT IDENTIFIER ::= { system 9 }
sample	OBJECT IDENTIFIER ::= { system 10 }
serial-number	OBJECT IDENTIFIER ::= { system 11 }
timestamp	OBJECT IDENTIFIER ::= { system 12 }
timestamp-raw	OBJECT IDENTIFIER ::= { system 13 }
total-disks	OBJECT IDENTIFIER ::= { system 14 }
total-memory	OBJECT IDENTIFIER ::= { system 15 }
total-processors	OBJECT IDENTIFIER ::= { system 16 }
total-tape-devices	OBJECT IDENTIFIER ::= { system 17 }
total-model-changes	OBJECT IDENTIFIER ::= { system 18 }
total-config-changes	OBJECT IDENTIFIER ::= { system 19 }
ppm-entry	OBJECT IDENTIFIER ::= { ppmTbl 1 }
sunSmTreeProp	OBJECT IDENTIFIER ::= { sunwffb-entry 1 }
sunSmNodeName	OBJECT IDENTIFIER ::= { sunwffb-entry 2 }
entry-no	OBJECT IDENTIFIER ::= { sunwffb-entry 3 }
dram3	OBJECT IDENTIFIER ::= { sunwffb-entry 4 }
dac	OBJECT IDENTIFIER ::= { sunwffb-entry 5 }
fbc-version	OBJECT IDENTIFIER ::= { sunwffb-entry 6 }
board-type	OBJECT IDENTIFIER ::= { sunwffb-entry 7 }
buffer	OBJECT IDENTIFIER ::= { sunwffb-entry 8 }
device-type	OBJECT IDENTIFIER ::= { sunwffb-entry 9 }
height	OBJECT IDENTIFIER ::= { sunwffb-entry 10 }
model	OBJECT IDENTIFIER ::= { sunwffb-entry 11 }
revision	OBJECT IDENTIFIER ::= { sunwffb-entry 12 }
upa-portid	OBJECT IDENTIFIER ::= { sunwffb-entry 13 }
width	OBJECT IDENTIFIER ::= { sunwffb-entry 14 }
sunSmTreeProp	OBJECT IDENTIFIER ::= { sunwBlade-1000 1 }
sunSmNodeName	OBJECT IDENTIFIER ::= { sunwBlade-1000 2 }
networkEntry	OBJECT IDENTIFIER ::= { networkTbl 1 }
sunSmTreeProp	OBJECT IDENTIFIER ::= { solt-entry 1 }
sunSmNodeName	OBJECT IDENTIFIER ::= { solt-entry 2 }
entry-no	OBJECT IDENTIFIER ::= { solt-entry 3 }
slot-num	OBJECT IDENTIFIER ::= { solt-entry 4 }
sunSmTreeProp	OBJECT IDENTIFIER ::= { counter-timer-entry 1 }
sunSmNodeName	OBJECT IDENTIFIER ::= { counter-timer-entry 2 }
entry-no	OBJECT IDENTIFIER ::= { counter-timer-entry 3 }
pathname-element	OBJECT IDENTIFIER ::= { counter-timer-entry 4 }
sunSmTreeProp	OBJECT IDENTIFIER ::= { io-deviceEntry 1 }
sunSmNodeName	OBJECT IDENTIFIER ::= { io-deviceEntry 2 }
entry-no	OBJECT IDENTIFIER ::= { io-deviceEntry 3 }
device-type	OBJECT IDENTIFIER ::= { io-deviceEntry 4 }
disk-count	OBJECT IDENTIFIER ::= { io-deviceEntry 5 }
instance	OBJECT IDENTIFIER ::= { io-deviceEntry 6 }
model	OBJECT IDENTIFIER ::= { io-deviceEntry 7 }
node-hierarchy	OBJECT IDENTIFIER ::= { io-deviceEntry 8 }
network-count	OBJECT IDENTIFIER ::= { io-deviceEntry 9 }
reg	OBJECT IDENTIFIER ::= { io-deviceEntry 10 }
tape-count	OBJECT IDENTIFIER ::= { io-deviceEntry 11 }
solt-entry	OBJECT IDENTIFIER ::= { slotTbl 1 }
fanTbl	OBJECT IDENTIFIER ::= { fan 1 }
sunSmTreeProp	OBJECT IDENTIFIER ::= { cpu-unit-entry 1 }
sunSmNodeName	OBJECT IDENTIFIER ::= { cpu-unit-entry 2 }
entry-no	OBJECT IDENTIFIER ::= { cpu-unit-entry 3 }
board-hash	OBJECT IDENTIFIER ::= { cpu-unit-entry 4 }
board-num	OBJECT IDENTIFIER ::= { cpu-unit-entry 5 }
clock-frequency	OBJECT IDENTIFIER ::= { cpu-unit-entry 6 }
cpu-type	OBJECT IDENTIFIER ::= { cpu-unit-entry 7 }
dcache-size	OBJECT IDENTIFIER ::= { cpu-unit-entry 8 }
device-type	OBJECT IDENTIFIER ::= { cpu-unit-entry 9 }
ecache-size	OBJECT IDENTIFIER ::= { cpu-unit-entry 10 }
fru	OBJECT IDENTIFIER ::= { cpu-unit-entry 11 }
icache-size	OBJECT IDENTIFIER ::= { cpu-unit-entry 12 }
model	OBJECT IDENTIFIER ::= { cpu-unit-entry 13 }
pathname-element	OBJECT IDENTIFIER ::= { cpu-unit-entry 14 }
processor-id	OBJECT IDENTIFIER ::= { cpu-unit-entry 15 }
reg	OBJECT IDENTIFIER ::= { cpu-unit-entry 16 }
status	OBJECT IDENTIFIER ::= { cpu-unit-entry 17 }
unit	OBJECT IDENTIFIER ::= { cpu-unit-entry 18 }
upa-mid	OBJECT IDENTIFIER ::= { cpu-unit-entry 19 }
upa-portid	OBJECT IDENTIFIER ::= { cpu-unit-entry 20 }
io-deviceTbl	OBJECT IDENTIFIER ::= { io-device 1 }
power-supply-entry	OBJECT IDENTIFIER ::= { power-supplyTbl 1 }
sunSmTreeProp	OBJECT IDENTIFIER ::= { tapeEntry 1 }
sunSmNodeName	OBJECT IDENTIFIER ::= { tapeEntry 2 }
entry-no	OBJECT IDENTIFIER ::= { tapeEntry 3 }
device-type	OBJECT IDENTIFIER ::= { tapeEntry 4 }
fru	OBJECT IDENTIFIER ::= { tapeEntry 5 }
instance	OBJECT IDENTIFIER ::= { tapeEntry 6 }
model	OBJECT IDENTIFIER ::= { tapeEntry 7 }
node-hierarchy	OBJECT IDENTIFIER ::= { tapeEntry 8 }
tape-name	OBJECT IDENTIFIER ::= { tapeEntry 9 }
status	OBJECT IDENTIFIER ::= { tapeEntry 10 }
target	OBJECT IDENTIFIER ::= { tapeEntry 11 }
io-controllerTbl	OBJECT IDENTIFIER ::= { io-controller 1 }
sunSmTreeProp	OBJECT IDENTIFIER ::= { fan-entry 1 }
sunSmNodeName	OBJECT IDENTIFIER ::= { fan-entry 2 }
entry-no	OBJECT IDENTIFIER ::= { fan-entry 3 }
status	OBJECT IDENTIFIER ::= { fan-entry 4 }
sunSmTreeProp	OBJECT IDENTIFIER ::= { sunwUltra-30 1 }
sunSmNodeName	OBJECT IDENTIFIER ::= { sunwUltra-30 2 }
tapeEntry	OBJECT IDENTIFIER ::= { tapeTbl 1 }
io-unitEntry	OBJECT IDENTIFIER ::= { io-unitTbl 1 }
memory-controller-entry	OBJECT IDENTIFIER ::= { memory-controllerTbl 1 }
sunSmTreeProp	OBJECT IDENTIFIER ::= { memory-entry 1 }
sunSmNodeName	OBJECT IDENTIFIER ::= { memory-entry 2 }
entry-no	OBJECT IDENTIFIER ::= { memory-entry 3 }
pathname-element	OBJECT IDENTIFIER ::= { memory-entry 4 }
sunSmTreeProp	OBJECT IDENTIFIER ::= { diskEntry 1 }
sunSmNodeName	OBJECT IDENTIFIER ::= { diskEntry 2 }
entry-no	OBJECT IDENTIFIER ::= { diskEntry 3 }
device-type	OBJECT IDENTIFIER ::= { diskEntry 4 }
disk-name	OBJECT IDENTIFIER ::= { diskEntry 5 }
fru	OBJECT IDENTIFIER ::= { diskEntry 6 }
instance	OBJECT IDENTIFIER ::= { diskEntry 7 }
node-hierarchy	OBJECT IDENTIFIER ::= { diskEntry 8 }
target	OBJECT IDENTIFIER ::= { diskEntry 9 }
sunSmTreeProp	OBJECT IDENTIFIER ::= { generic-device-entry 1 }
sunSmNodeName	OBJECT IDENTIFIER ::= { generic-device-entry 2 }
entry-no	OBJECT IDENTIFIER ::= { generic-device-entry 3 }
pathname-element	OBJECT IDENTIFIER ::= { generic-device-entry 4 }
pci108e5043-entry	OBJECT IDENTIFIER ::= { pci108e5043Tbl 1 }
upa64sTbl	OBJECT IDENTIFIER ::= { upa64s 1 }
mcTbl	OBJECT IDENTIFIER ::= { mc 1 }
memory-controllerTbl	OBJECT IDENTIFIER ::= { memory-controller 1 }
dimm-entry	OBJECT IDENTIFIER ::= { dimmTbl 1 }
diskTbl	OBJECT IDENTIFIER ::= { disk 1 }
sunSmTreeProp	OBJECT IDENTIFIER ::= { flashprom-entry 1 }
sunSmNodeName	OBJECT IDENTIFIER ::= { flashprom-entry 2 }
entry-no	OBJECT IDENTIFIER ::= { flashprom-entry 3 }
model	OBJECT IDENTIFIER ::= { flashprom-entry 4 }
reg	OBJECT IDENTIFIER ::= { flashprom-entry 5 }
sunSmTreeProp	OBJECT IDENTIFIER ::= { sunwUltra-5-10 1 }
sunSmNodeName	OBJECT IDENTIFIER ::= { sunwUltra-5-10 2 }
ffbTbl	OBJECT IDENTIFIER ::= { ffb 1 }
sunSmTreeProp	OBJECT IDENTIFIER ::= { sunwUltra-1 1 }
sunSmNodeName	OBJECT IDENTIFIER ::= { sunwUltra-1 2 }
sunSmTreeProp	OBJECT IDENTIFIER ::= { sunwUltra-2 1 }
sunSmNodeName	OBJECT IDENTIFIER ::= { sunwUltra-2 2 }
sunSmTreeProp	OBJECT IDENTIFIER ::= { sysctrl-entry 1 }
sunSmNodeName	OBJECT IDENTIFIER ::= { sysctrl-entry 2 }
entry-no	OBJECT IDENTIFIER ::= { sysctrl-entry 3 }
instance	OBJECT IDENTIFIER ::= { sysctrl-entry 4 }
reg	OBJECT IDENTIFIER ::= { sysctrl-entry 5 }
rcr4u209	OBJECT IDENTIFIER ::= { hardware-rules 1 }
rcr4u210	OBJECT IDENTIFIER ::= { hardware-rules 2 }
rcr4u211	OBJECT IDENTIFIER ::= { hardware-rules 3 }
rcr4u212	OBJECT IDENTIFIER ::= { hardware-rules 4 }
rcr4u214	OBJECT IDENTIFIER ::= { hardware-rules 5 }
rcr4u216	OBJECT IDENTIFIER ::= { hardware-rules 6 }
rcr4u217	OBJECT IDENTIFIER ::= { hardware-rules 7 }
rcr4u219	OBJECT IDENTIFIER ::= { hardware-rules 8 }
rcr4u220	OBJECT IDENTIFIER ::= { hardware-rules 9 }
rcr4u213	OBJECT IDENTIFIER ::= { hardware-rules 10 }
rcr4u215	OBJECT IDENTIFIER ::= { hardware-rules 11 }
rcr4u224	OBJECT IDENTIFIER ::= { hardware-rules 12 }
rcr4u221	OBJECT IDENTIFIER ::= { hardware-rules 13 }
sunSmTreeProp	OBJECT IDENTIFIER ::= { sunwUltra-4 1 }
sunSmNodeName	OBJECT IDENTIFIER ::= { sunwUltra-4 2 }
sunSmTreeProp	OBJECT IDENTIFIER ::= { mc-entry 1 }
sunSmNodeName	OBJECT IDENTIFIER ::= { mc-entry 2 }
entry-no	OBJECT IDENTIFIER ::= { mc-entry 3 }
device-type	OBJECT IDENTIFIER ::= { mc-entry 4 }
fru-device	OBJECT IDENTIFIER ::= { mc-entry 5 }
sunSmTreeProp	OBJECT IDENTIFIER ::= { sunwUltra-5 1 }
sunSmNodeName	OBJECT IDENTIFIER ::= { sunwUltra-5 2 }
sunSmTreeProp	OBJECT IDENTIFIER ::= { system-board 1 }
sunSmNodeName	OBJECT IDENTIFIER ::= { system-board 2 }
io-unitTbl	OBJECT IDENTIFIER ::= { io-unit 1 }
networkTbl	OBJECT IDENTIFIER ::= { network 1 }
pci108e5043Tbl	OBJECT IDENTIFIER ::= { pci108e5043 1 }
afbTbl	OBJECT IDENTIFIER ::= { afb 1 }
sysctrl-entry	OBJECT IDENTIFIER ::= { sysctrlTbl 1 }
sunSmTreeProp	OBJECT IDENTIFIER ::= { afb-entry 1 }
sunSmNodeName	OBJECT IDENTIFIER ::= { afb-entry 2 }
entry-no	OBJECT IDENTIFIER ::= { afb-entry 3 }
buffer	OBJECT IDENTIFIER ::= { afb-entry 4 }
device-type	OBJECT IDENTIFIER ::= { afb-entry 5 }
model	OBJECT IDENTIFIER ::= { afb-entry 6 }
pathname-element	OBJECT IDENTIFIER ::= { afb-entry 7 }
sunSmTreeProp	OBJECT IDENTIFIER ::= { upa64s-entry 1 }
sunSmNodeName	OBJECT IDENTIFIER ::= { upa64s-entry 2 }
entry-no	OBJECT IDENTIFIER ::= { upa64s-entry 3 }
pathname-element	OBJECT IDENTIFIER ::= { upa64s-entry 4 }
sunwffb-entry	OBJECT IDENTIFIER ::= { sunwffbTbl 1 }
sunSmTreeProp	OBJECT IDENTIFIER ::= { sunwUltra-80 1 }
sunSmNodeName	OBJECT IDENTIFIER ::= { sunwUltra-80 2 }
upa64s-entry	OBJECT IDENTIFIER ::= { upa64sTbl 1 }
fan-entry	OBJECT IDENTIFIER ::= { fanTbl 1 }
diskEntry	OBJECT IDENTIFIER ::= { diskTbl 1 }

END
