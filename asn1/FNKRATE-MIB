-- ****************************************************************************
--
--                 Funk Steel-Belted RADIUS Server Rate Statistics
--         Management Information Base for SNMP Network Management
--
--
--      Copyright 2001, Funk Software Inc.
--      All Rights Reserved.
--
--      This MIB defines attributes that contain rate information about
--      selected standard RADIUS MIB attributes. 
--
--      One attribute describes the time interval used for the rate
--      calculationss.
--
--      The Funk Enterprise number is 1411.
--      The ASN.1 prefix to, and including the Funk Enterprise is:
--           1.3.6.1.4.1.1411
--
-- ****************************************************************************

--
--
--

FNKRATE-MIB DEFINITIONS ::= BEGIN

-- ****************************************************************************
-- The more elegant solution to the Funk Trap and Rate extensions would be to
-- have an intermediate MIB that introduces an SBR extensions node and then
-- have each of the Rate and Trap MIBs derive from that. In the interest of
-- expediency that is not being done at this time. I wonder what the SBR4 folks
-- are doing re: cleaning up MIB maintenance? - Jeff V, Trilogy 2001.11.05
-- ****************************************************************************

    IMPORTS
        enterprises             FROM RFC1155-SMI
        SnmpAdminString         FROM SNMP-FRAMEWORK-MIB
        OBJECT-TYPE             FROM RFC-1212
	funkSbr                 FROM FNKSBRTR-MIB;

    funkSbrExtensions OBJECT IDENTIFIER ::= { funkSbr 2 }
    funkSbrRateVars   OBJECT IDENTIFIER ::= { funkSbrExtensions 1 }

-- ****************************************************************************
--  Variable Definitions
-- ****************************************************************************

-- This is not a rate variable, it indicates how the rate variabless were calculated

    funkSbrRatesSecondsPerInterval OBJECT-TYPE
        SYNTAX INTEGER(0..2147483647)
        MAX-ACCESS read-only
        STATUS current
        DESCRIPTION
                "The time (in seconds) interval used for rate calculations"
        ::= { funkSbrRateVars 1 }

-- The 45 or so rate attributes start here

    funkSbrRatesAuthRequestCurrentRate OBJECT-TYPE
        SYNTAX INTEGER(0..2147483647)
        MAX-ACCESS read-only
        STATUS current
        DESCRIPTION
                "AuthRequest Current Rate"
        ::= { funkSbrRateVars 2 }

    funkSbrRatesAuthRequestAverageRate OBJECT-TYPE
        SYNTAX INTEGER(0..2147483647)
        MAX-ACCESS read-only
        STATUS current
        DESCRIPTION
                "AuthRequest Average Rate"
        ::= { funkSbrRateVars 3 }

    funkSbrRatesAuthRequestPeakRate OBJECT-TYPE
        SYNTAX INTEGER(0..2147483647)
        MAX-ACCESS read-only
        STATUS current
        DESCRIPTION
                "AuthRequest Peak Rate"
        ::= { funkSbrRateVars 4 }

    funkSbrRatesAuthAcceptCurrentRate OBJECT-TYPE
        SYNTAX INTEGER(0..2147483647)
        MAX-ACCESS read-only
        STATUS current
        DESCRIPTION
                "AuthAccept Current Rate"
        ::= { funkSbrRateVars 5 }

    funkSbrRatesAuthAcceptAverageRate OBJECT-TYPE
        SYNTAX INTEGER(0..2147483647)
        MAX-ACCESS read-only
        STATUS current
        DESCRIPTION
                "AuthAccept Average Rate"
        ::= { funkSbrRateVars 6 }

    funkSbrRatesAuthAcceptPeakRate OBJECT-TYPE
        SYNTAX INTEGER(0..2147483647)
        MAX-ACCESS read-only
        STATUS current
        DESCRIPTION
                "AuthAccept Peak Rate"
        ::= { funkSbrRateVars 7 }

    funkSbrRatesAuthRejectCurrentRate OBJECT-TYPE
        SYNTAX INTEGER(0..2147483647)
        MAX-ACCESS read-only
        STATUS current
        DESCRIPTION
                "AuthReject Current Rate"
        ::= { funkSbrRateVars 8 }

    funkSbrRatesAuthRejectAverageRate OBJECT-TYPE
        SYNTAX INTEGER(0..2147483647)
        MAX-ACCESS read-only
        STATUS current
        DESCRIPTION
                "AuthReject Average Rate"
        ::= { funkSbrRateVars 9 }

    funkSbrRatesAuthRejectPeakRate OBJECT-TYPE
        SYNTAX INTEGER(0..2147483647)
        MAX-ACCESS read-only
        STATUS current
        DESCRIPTION
                "AuthReject Peak Rate"
        ::= { funkSbrRateVars 10 }

    funkSbrRatesAcctStartCurrentRate OBJECT-TYPE
        SYNTAX INTEGER(0..2147483647)
        MAX-ACCESS read-only
        STATUS current
        DESCRIPTION
                "AcctStart Current Rate"
        ::= { funkSbrRateVars 11 }

    funkSbrRatesAcctStartAverageRate OBJECT-TYPE
        SYNTAX INTEGER(0..2147483647)
        MAX-ACCESS read-only
        STATUS current
        DESCRIPTION
                "AcctStart Average Rate"
        ::= { funkSbrRateVars 12 }

    funkSbrRatesAcctStartPeakRate OBJECT-TYPE
        SYNTAX INTEGER(0..2147483647)
        MAX-ACCESS read-only
        STATUS current
        DESCRIPTION
                "AcctStart Peak Rate"
        ::= { funkSbrRateVars 13 }

    funkSbrRatesAcctStopCurrentRate OBJECT-TYPE
        SYNTAX INTEGER(0..2147483647)
        MAX-ACCESS read-only
        STATUS current
        DESCRIPTION
                "AcctStop Current Rate"
        ::= { funkSbrRateVars 14 }

    funkSbrRatesAcctStopAverageRate OBJECT-TYPE
        SYNTAX INTEGER(0..2147483647)
        MAX-ACCESS read-only
        STATUS current
        DESCRIPTION
                "AcctStop Average Rate"
        ::= { funkSbrRateVars 15 }

    funkSbrRatesAcctStopPeakRate OBJECT-TYPE
        SYNTAX INTEGER(0..2147483647)
        MAX-ACCESS read-only
        STATUS current
        DESCRIPTION
                "AcctStop Peak Rate"
        ::= { funkSbrRateVars 16 }

    funkSbrRatesProxyAuthRequestCurrentRate OBJECT-TYPE
        SYNTAX INTEGER(0..2147483647)
        MAX-ACCESS read-only
        STATUS current
        DESCRIPTION
                "ProxyAuthRequest Current Rate"
        ::= { funkSbrRateVars 17 }

    funkSbrRatesProxyAuthRequestAverageRate OBJECT-TYPE
        SYNTAX INTEGER(0..2147483647)
        MAX-ACCESS read-only
        STATUS current
        DESCRIPTION
                "ProxyAuthRequest Average Rate"
        ::= { funkSbrRateVars 18 }

    funkSbrRatesProxyAuthRequestPeakRate OBJECT-TYPE
        SYNTAX INTEGER(0..2147483647)
        MAX-ACCESS read-only
        STATUS current
        DESCRIPTION
                "ProxyAuthRequest Peak Rate"
        ::= { funkSbrRateVars 19 }

    funkSbrRatesProxyAcctRequestCurrentRate OBJECT-TYPE
        SYNTAX INTEGER(0..2147483647)
        MAX-ACCESS read-only
        STATUS current
        DESCRIPTION
                "ProxyAcctRequest Current Rate"
        ::= { funkSbrRateVars 20 }

    funkSbrRatesProxyAcctRequestAverageRate OBJECT-TYPE
        SYNTAX INTEGER(0..2147483647)
        MAX-ACCESS read-only
        STATUS current
        DESCRIPTION
                "ProxyAcctRequest Average Rate"
        ::= { funkSbrRateVars 21 }

    funkSbrRatesProxyAcctRequestPeakRate OBJECT-TYPE
        SYNTAX INTEGER(0..2147483647)
        MAX-ACCESS read-only
        STATUS current
        DESCRIPTION
                "ProxyAcctRequest Peak Rate"
        ::= { funkSbrRateVars 22 }

    funkSbrRatesProxyFailTimeoutCurrentRate OBJECT-TYPE
        SYNTAX INTEGER(0..2147483647)
        MAX-ACCESS read-only
        STATUS current
        DESCRIPTION
                "ProxyFailTimeout Current Rate"
        ::= { funkSbrRateVars 23 }

    funkSbrRatesProxyFailTimeoutAverageRate OBJECT-TYPE
        SYNTAX INTEGER(0..2147483647)
        MAX-ACCESS read-only
        STATUS current
        DESCRIPTION
                "ProxyFailTimeout Average Rate"
        ::= { funkSbrRateVars 24 }

    funkSbrRatesProxyFailTimeoutPeakRate OBJECT-TYPE
        SYNTAX INTEGER(0..2147483647)
        MAX-ACCESS read-only
        STATUS current
        DESCRIPTION
                "ProxyFailTimeout Peak Rate"
        ::= { funkSbrRateVars 25 }

    funkSbrRatesProxyFailBadrespCurrentRate OBJECT-TYPE
        SYNTAX INTEGER(0..2147483647)
        MAX-ACCESS read-only
        STATUS current
        DESCRIPTION
                "ProxyFailBadresp Current Rate"
        ::= { funkSbrRateVars 26 }

    funkSbrRatesProxyFailBadrespAverageRate OBJECT-TYPE
        SYNTAX INTEGER(0..2147483647)
        MAX-ACCESS read-only
        STATUS current
        DESCRIPTION
                "ProxyFailBadresp Average Rate"
        ::= { funkSbrRateVars 27 }

    funkSbrRatesProxyFailBadrespPeakRate OBJECT-TYPE
        SYNTAX INTEGER(0..2147483647)
        MAX-ACCESS read-only
        STATUS current
        DESCRIPTION
                "ProxyFailBadresp Peak Rate"
        ::= { funkSbrRateVars 28 }

    funkSbrRatesProxyFailBadsecretCurrentRate OBJECT-TYPE
        SYNTAX INTEGER(0..2147483647)
        MAX-ACCESS read-only
        STATUS current
        DESCRIPTION
                "ProxyFailBadsecret Current Rate"
        ::= { funkSbrRateVars 29 }

    funkSbrRatesProxyFailBadsecretAverageRate OBJECT-TYPE
        SYNTAX INTEGER(0..2147483647)
        MAX-ACCESS read-only
        STATUS current
        DESCRIPTION
                "ProxyFailBadsecret Average Rate"
        ::= { funkSbrRateVars 30 }

    funkSbrRatesProxyFailBadsecretPeakRate OBJECT-TYPE
        SYNTAX INTEGER(0..2147483647)
        MAX-ACCESS read-only
        STATUS current
        DESCRIPTION
                "ProxyFailBadsecret Peak Rate"
        ::= { funkSbrRateVars 31 }

    funkSbrRatesProxyFailMissingresrCurrentRate OBJECT-TYPE
        SYNTAX INTEGER(0..2147483647)
        MAX-ACCESS read-only
        STATUS current
        DESCRIPTION
                "ProxyFailMissingresr Current Rate"
        ::= { funkSbrRateVars 32 }

    funkSbrRatesProxyFailMissingresrAverageRate OBJECT-TYPE
        SYNTAX INTEGER(0..2147483647)
        MAX-ACCESS read-only
        STATUS current
        DESCRIPTION
                "ProxyFailMissingresr Average Rate"
        ::= { funkSbrRateVars 33 }

    funkSbrRatesProxyFailMissingresrPeakRate OBJECT-TYPE
        SYNTAX INTEGER(0..2147483647)
        MAX-ACCESS read-only
        STATUS current
        DESCRIPTION
                "ProxyFailMissingresr Peak Rate"
        ::= { funkSbrRateVars 34 }

    funkSbrRatesProxyRetriesCurrentRate OBJECT-TYPE
        SYNTAX INTEGER(0..2147483647)
        MAX-ACCESS read-only
        STATUS current
        DESCRIPTION
                "ProxyRetries Current Rate"
        ::= { funkSbrRateVars 35 }

    funkSbrRatesProxyRetriesAverageRate OBJECT-TYPE
        SYNTAX INTEGER(0..2147483647)
        MAX-ACCESS read-only
        STATUS current
        DESCRIPTION
                "ProxyRetries Average Rate"
        ::= { funkSbrRateVars 36 }

    funkSbrRatesProxyRetriesPeakRate OBJECT-TYPE
        SYNTAX INTEGER(0..2147483647)
        MAX-ACCESS read-only
        STATUS current
        DESCRIPTION
                "ProxyRetries Peak Rate"
        ::= { funkSbrRateVars 37 }

    funkSbrRatesProxyAuthRejProxyCurrentRate OBJECT-TYPE
        SYNTAX INTEGER(0..2147483647)
        MAX-ACCESS read-only
        STATUS current
        DESCRIPTION
                "ProxyAuthRejProxy Current Rate"
        ::= { funkSbrRateVars 38 }

    funkSbrRatesProxyAuthRejProxyAverageRate OBJECT-TYPE
        SYNTAX INTEGER(0..2147483647)
        MAX-ACCESS read-only
        STATUS current
        DESCRIPTION
                "ProxyAuthRejProxy Average Rate"
        ::= { funkSbrRateVars 39 }

    funkSbrRatesProxyAuthRejProxyPeakRate OBJECT-TYPE
        SYNTAX INTEGER(0..2147483647)
        MAX-ACCESS read-only
        STATUS current
        DESCRIPTION
                "ProxyAuthRejProxy Peak Rate"
        ::= { funkSbrRateVars 40 }

    funkSbrRatesProxyAcctFailProxCurrentRate OBJECT-TYPE
        SYNTAX INTEGER(0..2147483647)
        MAX-ACCESS read-only
        STATUS current
        DESCRIPTION
                "ProxyAcctFailProx Current Rate"
        ::= { funkSbrRateVars 41 }

    funkSbrRatesProxyAcctFailProxAverageRate OBJECT-TYPE
        SYNTAX INTEGER(0..2147483647)
        MAX-ACCESS read-only
        STATUS current
        DESCRIPTION
                "ProxyAcctFailProx Average Rate"
        ::= { funkSbrRateVars 42 }

    funkSbrRatesProxyAcctFailProxPeakRate OBJECT-TYPE
        SYNTAX INTEGER(0..2147483647)
        MAX-ACCESS read-only
        STATUS current
        DESCRIPTION
                "ProxyAcctFailProx Peak Rate"
        ::= { funkSbrRateVars 43 }

    funkSbrRatesProxyAuthRejProxyErrorCurrentRate OBJECT-TYPE
        SYNTAX INTEGER(0..2147483647)
        MAX-ACCESS read-only
        STATUS current
        DESCRIPTION
                "ProxyAuthRejProxyError Current Rate"
        ::= { funkSbrRateVars 44 }

    funkSbrRatesProxyAuthRejProxyErrorAverageRate OBJECT-TYPE
        SYNTAX INTEGER(0..2147483647)
        MAX-ACCESS read-only
        STATUS current
        DESCRIPTION
                "ProxyAuthRejProxyError Average Rate"
        ::= { funkSbrRateVars 45 }

    funkSbrRatesProxyAuthRejProxyErrorPeakRate OBJECT-TYPE
        SYNTAX INTEGER(0..2147483647)
        MAX-ACCESS read-only
        STATUS current
        DESCRIPTION
                "ProxyAuthRejProxyError Peak Rate"
        ::= { funkSbrRateVars 46 }

END
