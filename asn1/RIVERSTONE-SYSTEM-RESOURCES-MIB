RIVERSTONE-SYSTEM-RESOURCES-MIB DEFINITIONS ::= BEGIN

IMPORTS
   MODULE-IDENTITY,OBJECT-IDENTITY, OBJECT-TYPE, Unsigned32
       FROM SNMPv2-SMI
   MODULE-COMPLIANCE, OBJECT-GROUP
       FROM SNMPv2-CONF
   riverstoneMibs
       FROM RIVERSTONE-SMI-MIB
   entPhysicalIndex
      FROM ENTITY-MIB;

rsSystemResourcesMIB MODULE-IDENTITY
   LAST-UPDATED "200409141300Z"  -- Sept 14th 2004
  
        ORGANIZATION "Riverstone Networks, Inc"
        CONTACT-INFO
            "Riverstone Networks, Inc
             5200 Great America Parkway
             Santa Clara CA USA 95054
             PHONE:+1 408.878.6500
             EMAIL: nms-eng@riverstonenet.com
             WEB: http://www.riverstonenet.com"
    DESCRIPTION
    "This module defines a schema to access management information
     pertaining to system resources on Riverstone Device " 

    REVISION     "200409141300Z"
    DESCRIPTION
         "First Version which has objects for CPU and Memory utilization."

      ::= {  riverstoneMibs 281 }   




--System resources are broken down by these function areas

    rsSystemUtilization  OBJECT-IDENTITY
    STATUS current
    DESCRIPTION
	   "System utilization related objects"
    ::= { rsSystemResourcesMIB 5 }

-- Utilization metrics are broken down by these functional areas 
    rsCpuUtl  OBJECT-IDENTITY
    STATUS current
    DESCRIPTION
	   "cpu group"
    ::= { rsSystemUtilization 5 }

    rsMemory  OBJECT-IDENTITY
    STATUS current
    DESCRIPTION
	   "memory group"
    ::= { rsSystemUtilization 10 }

   rsUtlSamplingRate OBJECT-TYPE
       SYNTAX      Unsigned32 (100..60000)
       MAX-ACCESS  read-write
       STATUS      current
       DESCRIPTION
               "Stats are polled at these number of micro seconds interval"

       ::= { rsSystemUtilization 25 }

    rsUtlConformance OBJECT-IDENTITY
    STATUS current
    DESCRIPTION
	   "capacity conformance group "
    ::= { rsSystemUtilization 35 }



-- cpu group : capacity stats for CPU main memory

   rsUtlCPUTable OBJECT-TYPE
       SYNTAX      SEQUENCE OF RsUtlCPUEntry
       MAX-ACCESS  not-accessible
       STATUS      current
       DESCRIPTION
        "Summary of CPU statistics.  It is assumed that there is only 
         one CPU per line card."
       ::= { rsCpuUtl 1 }
 
   rsUtlCPUEntry OBJECT-TYPE
       SYNTAX      RsUtlCPUEntry
       MAX-ACCESS  not-accessible
       STATUS      current
       DESCRIPTION
        "An entry containing CPU utilization information. 
        "
       INDEX { entPhysicalIndex }
       ::= { rsUtlCPUTable 1 }
 
   RsUtlCPUEntry ::=
       SEQUENCE {

           rsUtlCPUSystemUtilization5Sec    Unsigned32,
           rsUtlCPUUserUtilization5Sec      Unsigned32,

           rsUtlCPUSystemUtilization60Sec    Unsigned32,
           rsUtlCPUUserUtilization60Sec      Unsigned32,


           rsUtlCPUSystemUtilization5Min     Unsigned32,
           rsUtlCPUUserUtilization5Min       Unsigned32
       
       }
 

   rsUtlCPUSystemUtilization5Sec OBJECT-TYPE
       SYNTAX      Unsigned32 (0..100)
       MAX-ACCESS  read-only
       STATUS      current
       DESCRIPTION
               "The CPU utilization  expressed as an integer percentage.
                This is calculated over the last 5 seconds at
                rsUtlSamplingRate interval as a simple average.
                This is 'system time'. 
               "
             
       ::= { rsUtlCPUEntry 1 }

   rsUtlCPUUserUtilization5Sec OBJECT-TYPE
       SYNTAX      Unsigned32 (0..100)
       MAX-ACCESS  read-only
       STATUS      current
       DESCRIPTION
               "The CPU utilization  expressed as an integer percentage.
                This is calculated over the last 5 seconds  at
                rsUtlSamplingRate interval as a simple average.
                This is 'user time'. 
               "
             
       ::= { rsUtlCPUEntry 2 }

   rsUtlCPUSystemUtilization60Sec OBJECT-TYPE
       SYNTAX      Unsigned32 (0..100)
       MAX-ACCESS  read-only
       STATUS      current
       DESCRIPTION
               "The CPU utilization  expressed as an integer percentage.
                This is calculated over the last 60 seconds at
                rsUtlSamplingRate interval as a simple average.
                This is 'system time'. 
               "
             
       ::= { rsUtlCPUEntry 3 }

   rsUtlCPUUserUtilization60Sec OBJECT-TYPE
       SYNTAX      Unsigned32 (0..100)
       MAX-ACCESS  read-only
       STATUS      current
       DESCRIPTION
               "The CPU utilization  expressed as an integer percentage.
                This is calculated over the last 60 seconds at
                rsUtlSamplingRate interval as a simple average.
                This is 'user time'. 
               "
             
       ::= { rsUtlCPUEntry 4 }

   rsUtlCPUSystemUtilization5Min OBJECT-TYPE
       SYNTAX      Unsigned32 (0..100)
       MAX-ACCESS  read-only
       STATUS      current
       DESCRIPTION
               "The CPU utilization  expressed as an integer percentage.
                This is calculated over the last 5 Min at
                rsUtlSamplingRate interval as a simple average.
                This is 'system time'. 
               "
             
       ::= { rsUtlCPUEntry 5 }

   rsUtlCPUUserUtilization5Min OBJECT-TYPE
       SYNTAX      Unsigned32 (0..100)
       MAX-ACCESS  read-only
       STATUS      current
       DESCRIPTION
               "The CPU utilization  expressed as an integer percentage.
                This is calculated over the last 5 Min. at
                rsUtlSamplingRate interval as a simple average.
                This is 'user time'. 
               "
             
       ::= { rsUtlCPUEntry 6 }



-- memory group : capacity stats for cpu memory

   rsUtlMemoryTable OBJECT-TYPE
       SYNTAX      SEQUENCE OF RsUtlMemoryEntry
       MAX-ACCESS  not-accessible
       STATUS      current
       DESCRIPTION
        "Summary of Memory statistics."
       ::= { rsMemory 1 }
 
   rsUtlMemoryEntry OBJECT-TYPE
       SYNTAX      RsUtlMemoryEntry
       MAX-ACCESS  not-accessible
       STATUS      current
       DESCRIPTION
        "An entry containing Memory utilization information."
       INDEX   { entPhysicalIndex }
       ::= { rsUtlMemoryTable 1 }
 
   RsUtlMemoryEntry ::=
       SEQUENCE {

           rsUtlMemoryActivePages5Sec   Unsigned32,    
           rsUtlMemoryFreePages5Sec         Unsigned32,

           rsUtlMemoryActivePages60Sec   Unsigned32,
           rsUtlMemoryFreePages60Sec         Unsigned32,


           rsUtlMemoryActivePages5Min    Unsigned32,
           rsUtlMemoryFreePages5Min          Unsigned32
       
       }
 
   rsUtlMemoryActivePages5Sec OBJECT-TYPE
       SYNTAX      Unsigned32 
       MAX-ACCESS  read-only
       STATUS      current
       DESCRIPTION
               "The Memory utilization in terms of active pages of
                size 1024 bytes.This is calculated over the last 5 
                seconds, sampled average at every rsUtlSamplingRate "

       ::= { rsUtlMemoryEntry 1 }

   rsUtlMemoryFreePages5Sec OBJECT-TYPE
       SYNTAX      Unsigned32 
       MAX-ACCESS  read-only
       STATUS      current
       DESCRIPTION
               "The Memory utilization in terms free pages of
                size 1024 bytes.This is calculated over the last 5 
                seconds, sampled average at every rsUtlSamplingRate "

       ::= { rsUtlMemoryEntry 2 }

   rsUtlMemoryActivePages60Sec OBJECT-TYPE
       SYNTAX      Unsigned32 
       MAX-ACCESS  read-only
       STATUS      current
       DESCRIPTION
               "The Memory utilization in terms of active pages of
                size 1024 bytes.This is calculated over the last 60 
                seconds, sampled average at every rsUtlSamplingRate "

       ::= { rsUtlMemoryEntry 3 }

   rsUtlMemoryFreePages60Sec OBJECT-TYPE
       SYNTAX      Unsigned32 
       MAX-ACCESS  read-only
       STATUS      current
       DESCRIPTION
               "The Memory utilization in terms of free pages of
                size 1024 bytes.This is calculated over the last 60 
                seconds, sampled average at every rsUtlSamplingRate "

       ::= { rsUtlMemoryEntry 4 }


   rsUtlMemoryActivePages5Min OBJECT-TYPE
       SYNTAX      Unsigned32 
       MAX-ACCESS  read-only
       STATUS      current
       DESCRIPTION
               "The Memory utilization in terms of active pages of
                size 1024 bytes.This is calculated over the last 5 Min, 
                sampled average at every rsUtlSamplingRate "

       ::= { rsUtlMemoryEntry 5 }

   rsUtlMemoryFreePages5Min OBJECT-TYPE
       SYNTAX      Unsigned32 
       MAX-ACCESS  read-only
       STATUS      current
       DESCRIPTION
               "The Memory utilization in terms free pages of
                size 1024 bytes.This is calculated over the last 5 Min, 
                sampled average at every rsUtlSamplingRate "

       ::= { rsUtlMemoryEntry 6 }

 
-- ### Compliance ###

rsUtlCompliances OBJECT IDENTIFIER ::= { rsUtlConformance 1 }
rsUtlGroups      OBJECT IDENTIFIER ::= { rsUtlConformance 2 }
 
rsUtlComplianceV1  MODULE-COMPLIANCE
    STATUS current
    DESCRIPTION
            "The compliance statement for the RIVERSTONE-SYSTEM-RESOURCES-MIB."
    MODULE  -- this module
    MANDATORY-GROUPS { rsUtlConfGroupV1 }
    ::= { rsUtlCompliances 1 }


rsUtlConfGroupV1  OBJECT-GROUP 
   OBJECTS {

           rsUtlMemoryActivePages5Sec,    
           rsUtlMemoryFreePages5Sec,

           rsUtlCPUSystemUtilization5Sec,    
           rsUtlCPUUserUtilization5Sec,    

          rsUtlCPUSystemUtilization60Sec,    
          rsUtlCPUUserUtilization60Sec,    


          rsUtlCPUSystemUtilization5Min,    
          rsUtlCPUUserUtilization5Min,    

           rsUtlMemoryActivePages60Sec,
           rsUtlMemoryFreePages60Sec,

           rsUtlMemoryActivePages5Min,
           rsUtlMemoryFreePages5Min
}
  STATUS current
  DESCRIPTION
  "A set of managed objects that make up version 1.0 of the Riverstone Utilization mib."
   ::= { rsUtlGroups 1 } 
 
 
END
