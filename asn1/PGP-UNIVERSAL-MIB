-- --------------------------------------------------------------------
-- Copyright (C) 2004 PGP Corporation
-- All rights reserved.
--
-- The PGP Universal MIB
-- --------------------------------------------------------------------

PGP-UNIVERSAL-MIB DEFINITIONS ::= BEGIN

	IMPORTS
		OBJECT-IDENTITY, MODULE-IDENTITY,
		OBJECT-TYPE,
		Integer32
				FROM SNMPv2-SMI
		products
				FROM PGP-SMI;

	pgpuniversal MODULE-IDENTITY
		LAST-UPDATED "200412080000Z"
		ORGANIZATION "PGP Corporation"
		CONTACT-INFO
			"			PGP Corporation
			Internet:	http://www.pgp.com"

		DESCRIPTION
			"A MIB module to describe the statistics provided by
			PGP Universal Server."

		REVISION "200412080000Z"
		DESCRIPTION "Initial version of this MIB module."

		::= { products 1 }

	messaging OBJECT-IDENTITY
		STATUS current
		DESCRIPTION "The PGP Universal messaging statistics."
		::= { pgpuniversal 1 }

	--
	-- messaging statistics
	--
	messagesProcessedToday OBJECT-TYPE
		SYNTAX INTEGER
		MAX-ACCESS read-only
		STATUS current
		DESCRIPTION
			"The number of messages processed today."
		::= { messaging 1 }

	messagesEncryptedToday OBJECT-TYPE
		SYNTAX INTEGER
		MAX-ACCESS read-only
		STATUS current
		DESCRIPTION
			"The number of messages encrypted and/or signed today."
		::= { messaging 2 }

	messagesDecryptedToday OBJECT-TYPE
		SYNTAX INTEGER
		MAX-ACCESS read-only
		STATUS current
		DESCRIPTION
			"The number of messages decrypted today."
		::= { messaging 3 }

	messagesProcessedTotal OBJECT-TYPE
		SYNTAX INTEGER
		MAX-ACCESS read-only
		STATUS current
		DESCRIPTION
			"The number of messages processed total."
		::= { messaging 4 }

	messagesEncryptedTotal OBJECT-TYPE
		SYNTAX INTEGER
		MAX-ACCESS read-only
		STATUS current
		DESCRIPTION
			"The number of messages encrypted and/or signed total."
		::= { messaging 5 }

	messagesDecryptedTotal OBJECT-TYPE
		SYNTAX INTEGER
		MAX-ACCESS read-only
		STATUS current
		DESCRIPTION
			"The number of messages decrypted total."
		::= { messaging 6 }

	virusesFoundToday OBJECT-TYPE
		SYNTAX INTEGER
		MAX-ACCESS read-only
		STATUS current
		DESCRIPTION
			"The number of viruses found today."
		::= { messaging 7 }

	messagesInQueue OBJECT-TYPE
		SYNTAX INTEGER
		MAX-ACCESS read-only
		STATUS current
		DESCRIPTION
			"The number of messages currently in the mail queue."
		::= { messaging 8 }

END
