IPX-RIP-PRIVATE-MIB DEFINITIONS ::= BEGIN

-- Referencing the parent branch.

IMPORTS
    MODULE-IDENTITY, OBJECT-TYPE, Integer32, Counter32
                                                FROM SNMPv2-SMI
    RowStatus                                   FROM SNMPv2-TC
    NetNumber                                   FROM IPX-PRIVATE-MIB
    cjnIpxIfIndex                               FROM IPX-INTERFACE-MANAGEMENT-PRIVATE-MIB
    cjnProtocol                                 FROM Cajun-ROOT;

cjnIpxRip MODULE-IDENTITY
    LAST-UPDATED "9904010000Z" -- Thursday, April 1, 1999"
    ORGANIZATION "Lucent's Concord Technology Center (CTC)"
    CONTACT-INFO
        "Marc Cochran -- mcochran@lucent.com"
    DESCRIPTION
            "Cajun IPX RIP Private MIB"
    ::= { cjnProtocol 20 }


-- Types
--
    FilterPrec ::= Integer32 (0..9999)


-- IPX RIP Global Group
--
    cjnIpxRipGlobalGroup    OBJECT IDENTIFIER ::= { cjnIpxRip 1 }

    cjnIpxRipEnabled OBJECT-TYPE
        SYNTAX      INTEGER { enabled(1), disabled(2) }
        MAX-ACCESS  read-write
        STATUS      current
        DESCRIPTION
                "Enable / Disable IPX RIP on this system."
        ::= { cjnIpxRipGlobalGroup 1 }
        

-- IPX RIP Filter Group
--
    cjnIpxRipFilterGroup  OBJECT IDENTIFIER ::= { cjnIpxRip 2 }

    cjnIpxRipFilterTable OBJECT-TYPE
        SYNTAX      SEQUENCE OF CjnIpxRipFilterEntry
        MAX-ACCESS  not-accessible
        STATUS      current
        DESCRIPTION
                "A list of Cajun IPX RIP filters."
        ::= { cjnIpxRipFilterGroup 1 }
        
    cjnIpxRipFilterEntry OBJECT-TYPE
        SYNTAX      CjnIpxRipFilterEntry
        MAX-ACCESS  not-accessible
        STATUS      current
        DESCRIPTION
                "A Cajun IPX RIP filter instance."
        INDEX       { cjnIpxIfIndex, cjnIpxRipFilterPrec }
        ::= { cjnIpxRipFilterTable 1 }

    CjnIpxRipFilterEntry ::=
        SEQUENCE {
            cjnIpxRipFilterPrec         FilterPrec,
            cjnIpxRipFilterRowStatus    RowStatus,
            cjnIpxRipFilterNetStart     NetNumber,
            cjnIpxRipFilterNetEnd       NetNumber,
            cjnIpxRipFilterDirection    INTEGER,
            cjnIpxRipFilterAction       INTEGER,
            cjnIpxRipFilterTicks        Integer32,
            cjnIpxRipFilterHops         Integer32
        }
        
    cjnIpxRipFilterPrec OBJECT-TYPE
        SYNTAX      FilterPrec
        MAX-ACCESS  read-only
        STATUS      current
        DESCRIPTION
                "The precedence of this RIP filter.  The precedence is
                relative to other RIP filters on the same interface."
        ::= { cjnIpxRipFilterEntry 1 }

    cjnIpxRipFilterRowStatus OBJECT-TYPE
        SYNTAX      RowStatus
        MAX-ACCESS  read-create
        STATUS      current
        DESCRIPTION
                "The status of this row, by which new entries may be
                created, or old entries deleted from this table."
        ::= { cjnIpxRipFilterEntry 2 }

    cjnIpxRipFilterNetStart OBJECT-TYPE
        SYNTAX      NetNumber
        MAX-ACCESS  read-create
        STATUS      current
        DESCRIPTION
                "The first IPX network number in the range which this filter 
                matches."
        ::= { cjnIpxRipFilterEntry 3 }

    cjnIpxRipFilterNetEnd OBJECT-TYPE
        SYNTAX      NetNumber
        MAX-ACCESS  read-create
        STATUS      current
        DESCRIPTION
                "The last IPX network number in the range which this filter 
                matches."
        ::= { cjnIpxRipFilterEntry 4 }

    cjnIpxRipFilterDirection OBJECT-TYPE
        SYNTAX      INTEGER { inbound(1), outbound(2), both(3) }
        MAX-ACCESS  read-create
        STATUS      current
        DESCRIPTION
                "The direction of IPX RIP packets to which this filter 
                applies.  Inbound applies the filter only to RIP packets 
                received on the interface.  Outbound applies the filter 
                only to RIP packets sent on the interface.  Both applies 
                the filter to RIP packets sent and received on the 
                interface."
        ::= { cjnIpxRipFilterEntry 5 }

    cjnIpxRipFilterAction OBJECT-TYPE
        SYNTAX      INTEGER { filter(1), allow(2) }
        MAX-ACCESS  read-create
        STATUS      current
        DESCRIPTION
                "The action to take if this filter matches an IPX RIP entry.
                Filter causes the RIP entry to be ignored in received RIP 
                packets or suppressed in sent RIP packets.  Allow causes 
                the RIP entry to be accepted in received RIP packets or 
                advertised in sent RIP packets."
        ::= { cjnIpxRipFilterEntry 6 }

    cjnIpxRipFilterTicks OBJECT-TYPE
        SYNTAX      Integer32
        MAX-ACCESS  read-create
        STATUS      current
        DESCRIPTION
                "Used to override the delay, in ticks, to reach the IPX 
                network specified in the RIP entry."
        ::= { cjnIpxRipFilterEntry 7 }

    cjnIpxRipFilterHops OBJECT-TYPE
        SYNTAX      Integer32
        MAX-ACCESS  read-create
        STATUS      current
        DESCRIPTION
                "Used to override the hops to reach the IPX network
                specified in the RIP entry."
        ::= { cjnIpxRipFilterEntry 8 }


-- IPX RIP Interface Group
--
    cjnIpxRipIfGroup    OBJECT IDENTIFIER ::= { cjnIpxRip 3 }

    cjnIpxRipIfTable OBJECT-TYPE
        SYNTAX      SEQUENCE OF CjnIpxRipIfEntry
        MAX-ACCESS  not-accessible
        STATUS      current
        DESCRIPTION
                "A list of Cajun IPX RIP interface entries."
        ::= { cjnIpxRipIfGroup 1 }
    
    cjnIpxRipIfEntry OBJECT-TYPE
        SYNTAX      CjnIpxRipIfEntry
        MAX-ACCESS  not-accessible
        STATUS      current
        DESCRIPTION
                "A Cajun IPX RIP interface instance."
        INDEX       { cjnIpxIfIndex }
        ::= { cjnIpxRipIfTable 1 }

        CjnIpxRipIfEntry ::=
            SEQUENCE {
                cjnIpxRipIfRowStatus                    RowStatus,  
                cjnIpxRipIfInterpacketGap               INTEGER,
                cjnIpxRipIfUseMaximumPacketSize         INTEGER,
                cjnIpxRipIfUpdateInterval               Integer32,
                cjnIpxRipIfAgeMultiplier                Integer32,
                cjnIpxRipIfTriggeredUpdates             INTEGER,
                cjnIpxRipIfAdvertiseDefaultRouteOnly    INTEGER,
                cjnIpxRipIfMode                         INTEGER
            }
    
    cjnIpxRipIfRowStatus OBJECT-TYPE
        SYNTAX      RowStatus 
        MAX-ACCESS  read-create
        STATUS      current
        DESCRIPTION
                "The status of this row, by which new entries may be
                created, or old entries deleted from this table."
        ::= { cjnIpxRipIfEntry 1 }

    cjnIpxRipIfInterpacketGap OBJECT-TYPE
        SYNTAX      INTEGER { enable(1), disable(2) }
        MAX-ACCESS  read-create
        STATUS      current
        DESCRIPTION
                "If set to enable(1), IPX RIP packets from periodic 
                advertisements are sent with an interpacket gap of 55 
                milliseconds.  If set to disable(2), no interpacket gap 
                is used."
        DEFVAL      { enable }
        ::= { cjnIpxRipIfEntry 2 }

    cjnIpxRipIfUseMaximumPacketSize OBJECT-TYPE
        SYNTAX      INTEGER { enable(1), disable(2) }
        MAX-ACCESS  read-create
        STATUS      current
        DESCRIPTION
                "If set to enable(1), IPX RIP packets will contain as many 
                entries as will fit in the maximum packet size allowable 
                on the interface given the configured encapsulation type. 
                If set to disable(2), IPX RIP packets will contain at most 
                50 entries."
        DEFVAL      { disable }
        ::= { cjnIpxRipIfEntry 3 }

    cjnIpxRipIfUpdateInterval OBJECT-TYPE
        SYNTAX      Integer32   
        MAX-ACCESS  read-create
        STATUS      current
        DESCRIPTION
                "The RIP periodic update interval, in seconds."
        DEFVAL      { 60 }
        ::= { cjnIpxRipIfEntry 4 }
    
    cjnIpxRipIfAgeMultiplier OBJECT-TYPE
        SYNTAX      Integer32
        MAX-ACCESS  read-create
        STATUS      current
        DESCRIPTION
                "The holding multiplier for information received in RIP 
                updates.  RIP information will be kept for the number of 
                seconds indicated by the cjnIpxRipIfUpdateInterval 
                multiplied by the cjnIpxRipIfAgeMultiplier."
        DEFVAL      { 3 }
        ::= { cjnIpxRipIfEntry 5 }

    cjnIpxRipIfTriggeredUpdates OBJECT-TYPE
        SYNTAX      INTEGER { enable(1), disable(2) }
        MAX-ACCESS  read-create
        STATUS      current
        DESCRIPTION
                "Specified whether or not RIP updates are immediately sent 
                on the interface in response to changes in the routing 
                table."
        DEFVAL      { enable }
        ::= { cjnIpxRipIfEntry 6 }

    cjnIpxRipIfAdvertiseDefaultRouteOnly OBJECT-TYPE
        SYNTAX      INTEGER { enable(1), disable(2) }
        MAX-ACCESS  read-create
        STATUS      current
        DESCRIPTION
                "Specifies whether or not ONLY the default route (FFFFFFFE) 
                is advertised in RIP updates sent on the interface."
        DEFVAL      { disable }
        ::= { cjnIpxRipIfEntry 7 }

    cjnIpxRipIfMode OBJECT-TYPE
        SYNTAX      INTEGER { talk(1), listen(2), both(3) }   
        MAX-ACCESS  read-create
        STATUS      current
        DESCRIPTION
                "The handling of RIP packets on the interface.  If set to 
                talk(1), RIP packets may be sent on the interface but not 
                received.  If set to listen(2), RIP packets may be received 
                but not sent.  If set to both(3), RIP packets may be sent 
                and received."
        DEFVAL      { both }
        ::= { cjnIpxRipIfEntry 8 }
        

-- IPX RIP Interface Statistics Group
--
    cjnIpxRipIfStatGroup    OBJECT IDENTIFIER ::= { cjnIpxRip 4 }

    cjnIpxRipIfStatTable OBJECT-TYPE
        SYNTAX      SEQUENCE OF CjnIpxRipIfStatEntry
        MAX-ACCESS  not-accessible
        STATUS      current
        DESCRIPTION
                "A list of Cajun IPX RIP interface statistics entries."
        ::= { cjnIpxRipIfStatGroup 1 }
    
    cjnIpxRipIfStatEntry OBJECT-TYPE
        SYNTAX      CjnIpxRipIfStatEntry
        MAX-ACCESS  not-accessible
        STATUS      current
        DESCRIPTION
                "A Cajun IPX RIP interface statistics instance."
        INDEX       { cjnIpxIfIndex }
        ::= { cjnIpxRipIfStatTable 1 }

        CjnIpxRipIfStatEntry ::=
            SEQUENCE {
                cjnIpxRipIfStatTriggeredUpdatesSent     Counter32,
                cjnIpxRipIfStatPeriodicUpdatesSent      Counter32,
                cjnIpxRipIfStatUpdatesReceived          Counter32,
                cjnIpxRipIfStatRequestsReceived         Counter32,
                cjnIpxRipIfStatBadPacketsReceived       Counter32
            }
    
    cjnIpxRipIfStatTriggeredUpdatesSent OBJECT-TYPE
        SYNTAX      Counter32   
        MAX-ACCESS  read-only
        STATUS      current
        DESCRIPTION
                "The number of RIP triggered updates sent on the 
                interface."
        ::= { cjnIpxRipIfStatEntry 1 }
    
    cjnIpxRipIfStatPeriodicUpdatesSent OBJECT-TYPE
        SYNTAX      Counter32   
        MAX-ACCESS  read-only
        STATUS      current
        DESCRIPTION
                "The number of periodic RIP updates sent on the interface."
        ::= { cjnIpxRipIfStatEntry 2 }
    
    cjnIpxRipIfStatUpdatesReceived OBJECT-TYPE
        SYNTAX      Counter32   
        MAX-ACCESS  read-only
        STATUS      current
        DESCRIPTION
                "The number of RIP updates received on the interface."
        ::= { cjnIpxRipIfStatEntry 3 }
    
    cjnIpxRipIfStatRequestsReceived OBJECT-TYPE
        SYNTAX      Counter32   
        MAX-ACCESS  read-only
        STATUS      current
        DESCRIPTION
                "The number of RIP requests received on the interface."
        ::= { cjnIpxRipIfStatEntry 4 }
    
    cjnIpxRipIfStatBadPacketsReceived OBJECT-TYPE
        SYNTAX      Counter32   
        MAX-ACCESS  read-only
        STATUS      current
        DESCRIPTION
                "The number of incorrectly formatted RIP packets received 
                on the interface."
        ::= { cjnIpxRipIfStatEntry 5 }

    cjnIpxRipIfStatsReset  OBJECT-TYPE
        SYNTAX      INTEGER { enable(1), disable(2) }
        MAX-ACCESS  read-write
        STATUS      current
        DESCRIPTION
                "When set to the value enable (1) all IPX RIP statistics 
                for this interface are reset to zero after which the value 
                of this MIB object returns to disable(2)."
        ::= { cjnIpxRipIfStatEntry 6 }

END
