--**************************************************************************
--                                                                          
--    Copyright 2004 Broadcom Corporation                                   
--    All Rights Reserved                                                   
--    No portions of this material may be reproduced in any form without the
--    written permission of:                                                
--             Broadcom Corporation                                         
--             16251 Laguna Canyon Road                                     
--             Irvine, California  92618                                    
--    All information contained in this document is Broadcom Corporation    
--    company private, proprietary, and trade secret.                       
--                                                                          
--                                                                          
--                                                                          
--**************************************************************************
--    Filename: brcm-cm-capability.mib
--    Author:   Kevin O'Neal
--    Creation Date: 11-feb-2004 (Happy 2nd Birthday Eric!)
--
--**************************************************************************
--    Description:
--
--		private MIB defining CM agent capability.
--              Note that this MIB does not define an accessible objects
--              and is provided strictly for use in the sysORTable.
--		
--**************************************************************************
--    Revision History:
--
--**************************************************************************

BRCM-CM-CAPABILITY-MIB DEFINITIONS ::= BEGIN

IMPORTS
    MODULE-IDENTITY
        FROM SNMPv2-SMI
    AGENT-CAPABILITIES 
        FROM SNMPv2-CONF
    cableDataAgentCapability 
        FROM BRCM-CABLEDATA-SMI;

brcmCmCapability MODULE-IDENTITY
    LAST-UPDATED       "200402110000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom cabledata management MIB"
    REVISION      "200402110000Z"
    DESCRIPTION
            "Initial version of this MIB module."
    ::= { cableDataAgentCapability 2 }

--
-- AGENT-CAPABILITIES statement for DOCSIS 1.0 CM agent
-- OID (for sysORID purposes) = 1.3.6.1.4.1.4413.2.3.2.1
--
cmDocsis10AgentCapability AGENT-CAPABILITIES
    PRODUCT-RELEASE    
        "BFC DOCSIS 1.0 CM reference design 3.x
         V2 DOCSIS 1.0 CM reference design 2.x"
    STATUS	current
    DESCRIPTION        
        "An agent which supports all MIBs required by the DOCSIS 1.0
         OSS specification."
    -- MIBs required by DOCSIS 1.0 (as of CW28):
    SUPPORTS    DOCS-CABLE-DEVICE-MIB -- RFC-2669
    INCLUDES    { docsDevBaseGroup,
                  docsDevEventGroup,
                  docsDevFilterGroup,
                  docsDevNmAccessGroup,
                  docsDevServerGroup,
                  docsDevSoftwareGroup,
                  docsDevCpeGroup }
    SUPPORTS    DOCS-IF-MIB -- RFC-2670
    INCLUDES    { docsIfBasicGroup,
                  docsIfCmGroup }
    SUPPORTS    DOCS-BPI-MIB -- RFC-3083
    INCLUDES    { docsBpiCmGroup }
 -- SUPPORTS    BRIDGE-MIB - - RFC-1493
 -- INCLUDES    { } - - No conformance section (SNMPv1 syntax), what to do??
    SUPPORTS    EtherLike-MIB -- RFC-2665
    INCLUDES    { etherStatsBaseGroup,
                  etherStatsLowSpeedGroup,
                  etherStatsHighSpeedGroup,
                  etherDuplexGroup }
    SUPPORTS    IP-MIB -- RFC-2011
    INCLUDES    { ipGroup,
                  icmpGroup }
    SUPPORTS    UDP-MIB -- RFC-2013
    INCLUDES    { udpGroup }
    SUPPORTS    USB-MIB -- draft-dolnik-usb-mib-00
    INCLUDES    { usbMibBasicGroup,
                  usbMibCDCGroup,
                  usbMibCDCEtherGroup,
                  usbCDCEtherXmtAddressGroup }
    SUPPORTS    IF-MIB -- RFC-2233
    INCLUDES    { ifGeneralInformationGroup, 
                  ifVHCPacketGroup,
                  ifStackGroup2,
                  ifCounterDiscontinuityGroup }
    SUPPORTS    SNMPv2-MIB -- RFC-3418
    INCLUDES    { snmpGroup,
                  snmpCommunityGroup,
                  snmpSetGroup,
                  systemGroup,
                  snmpObsoleteGroup }
    ::= { brcmCmCapability 1 }
    
--
-- AGENT-CAPABILITIES statement for DOCSIS 1.1 CM agent
-- OID (for sysORID purposes) = 1.3.6.1.4.1.4413.2.3.2.2
--
cmDocsis11AgentCapability AGENT-CAPABILITIES
    PRODUCT-RELEASE    
        "BFC DOCSIS 1.1 CM reference design 3.x
         V2 DOCSIS 1.1 CM reference design 2.x"
    STATUS	current
    DESCRIPTION        
        "An agent which supports all MIBs required by the DOCSIS 1.1
         OSS specification."
    -- MIBs required by DOCSIS 1.1 (as of CW28):
    SUPPORTS    DOCS-CABLE-DEVICE-MIB -- RFC-2669
    INCLUDES    { docsDevBaseGroup,
                  docsDevEventGroup,
                  docsDevFilterGroup,
                  docsDevNmAccessGroup,
                  docsDevServerGroup,
                  docsDevSoftwareGroup,
                  docsDevCpeGroup }
    SUPPORTS    DOCS-IF-MIB -- draft-ietf-ipcdn-docs-rfmibv2-05
    INCLUDES    { docsIfBasicGroup,
                  docsIfCmGroup }
    SUPPORTS    DOCS-BPI-MIB -- RFC-3083
    INCLUDES    { docsBpiCmGroup }
    SUPPORTS    DOCS-BPI2-MIB -- draft-ietf-ipcdn-bpiplus-mib-05
    INCLUDES    { docsBpi2CmGroup,
                  docsBpi2CodeDownloadGroup }
    SUPPORTS    DOCS-QOS-MIB -- draft-ietf-ipcdn-qos-mib-04
    INCLUDES    { docsQosBaseGroup,
                  docsQosParamSetGroup,
                  docsQosSrvClassPolicyGroup }              
    SUPPORTS    DOCS-CABLE-DEVICE-TRAP-MIB -- Appendix 'L' of the 1.1 OSS spec
    INCLUDES    { docsDevCmTrapControlGroup,
                  docsDevCmNotificationGroup }
    SUPPORTS    IF-MIB -- RFC-2863
    INCLUDES    { ifGeneralInformationGroup, 
                  ifVHCPacketGroup,
                  ifStackGroup2,
                  ifCounterDiscontinuityGroup }
 -- SUPPORTS    BRIDGE-MIB - - RFC-1493
 -- INCLUDES    { } - - No conformance section (SNMPv1 syntax), what to do??
    SUPPORTS    EtherLike-MIB -- RFC-2665
    INCLUDES    { etherStatsBaseGroup,
                  etherStatsLowSpeedGroup,
                  etherStatsHighSpeedGroup,
                  etherDuplexGroup }
    SUPPORTS    IP-MIB -- RFC-2011
    INCLUDES    { ipGroup,
                  icmpGroup }
    SUPPORTS    UDP-MIB -- RFC-2013
    INCLUDES    { udpGroup }
    SUPPORTS    USB-MIB -- draft-dolnik-usb-mib-00
    INCLUDES    { usbMibBasicGroup,
                  usbMibCDCGroup,
                  usbMibCDCEtherGroup,
                  usbCDCEtherXmtAddressGroup }
    SUPPORTS    SNMP-TARGET-MIB -- RFC-3413
    INCLUDES    { snmpTargetBasicGroup, 
                  snmpTargetResponseGroup,
                  snmpTargetCommandResponderGroup }
    SUPPORTS    SNMP-NOTIFICATION-MIB -- Also RFC-3413
    INCLUDES    { snmpNotifyGroup, 
                  snmpNotifyFilterGroup }
    SUPPORTS    SNMP-USER-BASED-SM-MIB -- RFC-3414
    INCLUDES    { usmMIBBasicGroup }
    SUPPORTS    SNMP-VIEW-BASED-ACM-MIB -- RFC-3415
    INCLUDES    { vacmBasicGroup }
    SUPPORTS    SNMP-COMMUNITY-MIB -- RFC-2576
    INCLUDES    { snmpCommunityGroup }
    SUPPORTS    SNMP-USM-DH-OBJECTS-MIB -- RFC-2786
    INCLUDES    { usmDHKeyMIBBasicGroup, 
                  usmDHKeyParamGroup,
                  usmDHKeyKickstartGroup }
    SUPPORTS    SNMPv2-MIB -- RFC-3418
    INCLUDES    { snmpGroup,
                  snmpCommunityGroup,
                  snmpSetGroup,
                  systemGroup,
                  snmpObsoleteGroup }
    ::= { brcmCmCapability 2 }
    
--
-- AGENT-CAPABILITIES statement for DOCSIS 2.0 CM agent
-- OID (for sysORID purposes) = 1.3.6.1.4.1.4413.2.3.2.3
--
cmDocsis20AgentCapability AGENT-CAPABILITIES
    PRODUCT-RELEASE    
        "BFC DOCSIS 2.0 CM reference design 3.x
         V2 DOCSIS 2.0 CM reference design 2.x"
    STATUS	current
    DESCRIPTION        
        "An agent which supports all MIBs required by the DOCSIS 2.0
         OSS specification."
    -- MIBs required by DOCSIS 2.0 (as of CW28):
    SUPPORTS    DOCS-CABLE-DEVICE-MIB -- RFC-2669
    INCLUDES    { docsDevBaseGroup,
                  docsDevEventGroup,
                  docsDevFilterGroup,
                  docsDevNmAccessGroup,
                  docsDevServerGroup,
                  docsDevSoftwareGroup,
                  docsDevCpeGroup }
    SUPPORTS    DOCS-IF-MIB -- draft-ietf-ipcdn-docs-rfmibv2-05
    INCLUDES    { docsIfBasicGroup,
                  docsIfCmGroup }
    SUPPORTS    DOCS-BPI-MIB -- RFC-3083
    INCLUDES    { docsBpiCmGroup }
    SUPPORTS    DOCS-BPI2-MIB -- draft-ietf-ipcdn-bpiplus-mib-05
    INCLUDES    { docsBpi2CmGroup,
                  docsBpi2CodeDownloadGroup }
    SUPPORTS    DOCS-QOS-MIB -- draft-ietf-ipcdn-qos-mib-04
    INCLUDES    { docsQosBaseGroup,
                  docsQosParamSetGroup,
                  docsQosSrvClassPolicyGroup }              
    SUPPORTS    DOCS-CABLE-DEVICE-TRAP-MIB -- Annex 'H' of the 2.0 OSS spec
    INCLUDES    { docsDevCmTrapControlGroup,
                  docsDevCmNotificationGroup }
    SUPPORTS    IF-MIB -- RFC-2863
    INCLUDES    { ifGeneralInformationGroup, 
                  ifVHCPacketGroup,
                  ifStackGroup2,
                  ifCounterDiscontinuityGroup }
 -- SUPPORTS    BRIDGE-MIB - - RFC-1493
 -- INCLUDES    { } - - No conformance section (SNMPv1 syntax), what to do??
    SUPPORTS    EtherLike-MIB -- RFC-2665
    INCLUDES    { etherStatsBaseGroup,
                  etherStatsLowSpeedGroup,
                  etherStatsHighSpeedGroup,
                  etherDuplexGroup }
    SUPPORTS    IP-MIB -- RFC-2011
    INCLUDES    { ipGroup,
                  icmpGroup }
    SUPPORTS    UDP-MIB -- RFC-2013
    INCLUDES    { udpGroup }
    SUPPORTS    USB-MIB -- draft-dolnik-usb-mib-00
    INCLUDES    { usbMibBasicGroup,
                  usbMibCDCGroup,
                  usbMibCDCEtherGroup,
                  usbCDCEtherXmtAddressGroup }
    SUPPORTS    SNMP-TARGET-MIB -- RFC-3413
    INCLUDES    { snmpTargetBasicGroup, 
                  snmpTargetResponseGroup,
                  snmpTargetCommandResponderGroup }
    SUPPORTS    SNMP-NOTIFICATION-MIB -- Also RFC-3413
    INCLUDES    { snmpNotifyGroup, 
                  snmpNotifyFilterGroup }
    SUPPORTS    SNMP-USER-BASED-SM-MIB -- RFC-3414
    INCLUDES    { usmMIBBasicGroup }
    SUPPORTS    SNMP-VIEW-BASED-ACM-MIB -- RFC-3415
    INCLUDES    { vacmBasicGroup }
    SUPPORTS    SNMP-COMMUNITY-MIB -- RFC-2576
    INCLUDES    { snmpCommunityGroup }
    SUPPORTS    SNMP-USM-DH-OBJECTS-MIB -- RFC-2786
    INCLUDES    { usmDHKeyMIBBasicGroup, 
                  usmDHKeyParamGroup,
                  usmDHKeyKickstartGroup }
    
    SUPPORTS    SNMPv2-MIB -- RFC-3418
    INCLUDES    { snmpGroup,
                  snmpCommunityGroup,
                  snmpSetGroup,
                  systemGroup,
                  snmpObsoleteGroup }
    ::= { brcmCmCapability 3 }

END
