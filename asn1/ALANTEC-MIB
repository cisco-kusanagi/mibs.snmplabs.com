-- 1. Introduction:

-- The main purpose of this document is to collect all the objects
-- of the different subsystems and map them ( where applicable ) 
-- onto the Standard MIB objects. The objects that do not have any
-- correspondence to the standard MIB objects will be concatenated
-- into the ALANTEC proprietary MIB. This document will be used
-- to derive the ALANTEC proprietary MIB.

-- Let us examine all the subsystems of the PowerHub User Interface
-- one by one.

-- Abbreviations :
  		-- AP - ALANTEC Proprietary

                --{ iso org(3) dod(6) internet(1) private(4)  enterprises(1) 390 }

   ALANTEC-MIB  DEFINITIONS ::= BEGIN

               IMPORTS
                    enterprises, IpAddress, Counter 	FROM RFC1155-SMI
                    DisplayString, PhysAddress                     					FROM RFC1213-MIB
		    OBJECT-TYPE						               FROM RFC-1212;

-- All representations of MAC addresses in this MIB Module use,
-- as a textual convention (i.e. this convention does not affect
-- their encoding), the data type:

MacAddress ::= OCTET STRING (SIZE (6))    -- a 6 octet address in
                                          -- the "canonical" order
-- defined by IEEE 802.1a, i.e., as if it were transmitted least
-- significant bit first, even though 802.5 (in contrast to other
-- 802.x protocols) requires MAC addresses to be transmitted most
-- significant bit first.
--
-- 16-bit addresses, if needed, are represented by setting their
-- upper 4 octets to all 0's, i.e., AAFF would be represented
-- as 00000000AAFF.


		alantec		OBJECT IDENTIFIER ::= { enterprises 390 }

		products	OBJECT IDENTIFIER ::= { alantec 1 }
		common		OBJECT IDENTIFIER ::= { alantec 2 }
	
		powerhub	OBJECT IDENTIFIER ::= { products 1 }
		powerbits	OBJECT IDENTIFIER ::= { products 2 }
		powerhub7000	OBJECT IDENTIFIER ::= { products 3 }
		
		alsystem	OBJECT IDENTIFIER ::= { common 1 }
		albridge	OBJECT IDENTIFIER ::= { common 2 }
		almgmt		OBJECT IDENTIFIER ::= { common 3 }
		alrip		OBJECT IDENTIFIER ::= { common 4 }
		altcp		OBJECT IDENTIFIER ::= { common 5 }
		alip		OBJECT IDENTIFIER ::= { common 6 }
		alat		OBJECT IDENTIFIER ::= { common 7 }
		aldecnet	OBJECT IDENTIFIER ::= { common 8 }
		alipx		OBJECT IDENTIFIER ::= { common 9 }
		alsnmp		OBJECT IDENTIFIER ::= { common 10 }
		
		alchassis	OBJECT IDENTIFIER ::= { powerhub7000 1 }	

                alSlotTable OBJECT-TYPE
                        SYNTAX  SEQUENCE OF AlSlotEntry
                        ACCESS  not-accessible
                        STATUS  mandatory
                        DESCRIPTION
                                "A table that contains information about
				 each slot in the PowerHub 7000 chassis."
                        ::= { alchassis 1 }

                alSlotEntry OBJECT-TYPE
                        SYNTAX  AlSlotEntry
                        ACCESS  not-accessible
                        STATUS  mandatory
                        DESCRIPTION
                                "Information about a specific slot."
                        INDEX   { alSlotNumber }
 
                        ::= { alSlotTable 1 }
 
                AlSlotEntry ::=
                        SEQUENCE {
                                        alSlotNumber
                                                INTEGER,
                                        alSlotCardType
                                                INTEGER,
					alSlotStatus
						INTEGER,
					alSlotModel
						DisplayString,
					alSlotRevision
						DisplayString,
					alSlotIssue
						DisplayString,
					alSlotDeviation
						DisplayString,
					alSlotSerialNumber
						DisplayString,
					alSlotPower5
						INTEGER,
					alSlotPower12
						INTEGER,
					alSlotPower33
						INTEGER,
					alSlotPowerOther
						INTEGER

				}
						
        alSlotNumber OBJECT-TYPE
                   SYNTAX  INTEGER
                   ACCESS  read-only
                   STATUS  mandatory
                   DESCRIPTION
                        "The slot number for which the following 
			 information applies."
 
                ::= { alSlotEntry 1 }

        alSlotCardType OBJECT-TYPE
                   SYNTAX  INTEGER {
-- CVG, LSI					PACKET-ENGINE(0),
					universal-ethernet(1),
					utp-4X4(2),
					utp-4X6(3),
					fddi-dual-das(4),
					fddi-single-das(5),
					utp-16X1(6),
					utp-13X1(7),
					fddi-dual-universal(8),
					fddi-single-universal(9),
					fddi-concentrator(10),
					cddi-concentrator(11),
					fast-thernet(12)
 				    }
					
                   ACCESS  read-only
                   STATUS  mandatory
                   DESCRIPTION
                        "The card type for this slot."
 
                ::= { alSlotEntry 2 }

        alSlotStatus OBJECT-TYPE
                   SYNTAX  INTEGER {
-- CVG, LSI					present-equipped(0),
					not-equipped(1),
					not-present(2)
				   }
                   ACCESS  read-only
                   STATUS  mandatory
                   DESCRIPTION
                        "The status of the card in this slot."

                ::= { alSlotEntry 3 }

        alSlotModel OBJECT-TYPE
                   SYNTAX  DisplayString
                   ACCESS  read-only
                   STATUS  mandatory
                   DESCRIPTION
                        "The model number for this card."

                ::= { alSlotEntry 4 }

        alSlotRevision OBJECT-TYPE
                   SYNTAX  DisplayString
                   ACCESS  read-only
                   STATUS  mandatory
                   DESCRIPTION
                        "The revision number for this card."

                ::= { alSlotEntry 5 }

        alSlotIssue OBJECT-TYPE
                   SYNTAX  DisplayString
                   ACCESS  read-only
                   STATUS  mandatory
                   DESCRIPTION
                        "The issue number for this slot."

                ::= { alSlotEntry 6 }

        alSlotDeviation OBJECT-TYPE
                   SYNTAX  DisplayString
                   ACCESS  read-only
                   STATUS  mandatory
                   DESCRIPTION
                        "The deviation for this slot."

                ::= { alSlotEntry 7 }

        alSlotSerialNumber OBJECT-TYPE
                   SYNTAX  DisplayString
                   ACCESS  read-only
                   STATUS  mandatory
                   DESCRIPTION
                        "The serial number of this card this slot."

                ::= { alSlotEntry 8 }

        alSlotPower5 OBJECT-TYPE
                   SYNTAX  INTEGER
                   ACCESS  read-only
                   STATUS  mandatory
                   DESCRIPTION
                        "The number of milliamps. of current drawn
			 by this slot at 5 Volts."

                ::= { alSlotEntry 9 }

        alSlotPower12 OBJECT-TYPE
                   SYNTAX  INTEGER
                   ACCESS  read-only
                   STATUS  mandatory
                   DESCRIPTION
                        "The number of milliamps. of current drawn
                         by this slot at 12 Volts." 

                ::= { alSlotEntry 10 }

        alSlotPower33 OBJECT-TYPE
                   SYNTAX  INTEGER
                   ACCESS  read-only
                   STATUS  mandatory
                   DESCRIPTION
                        "The number of milliamps. of current drawn 
                         by this slot at 3.3 Volts." 

                ::= { alSlotEntry 11 }

        alSlotPowerOther OBJECT-TYPE
                   SYNTAX  INTEGER
                   ACCESS  read-only
                   STATUS  mandatory
                   DESCRIPTION
                        "The number of milliamps. of current drawn  
                         by this slot at OTHER voltage." 

                ::= { alSlotEntry 12 }



                alVportTable OBJECT-TYPE
                        SYNTAX  SEQUENCE OF AlVportEntry
                        ACCESS  not-accessible
                        STATUS  mandatory
                        DESCRIPTION
                                "A table that contains information about
                                 each virtual port in the PowerHub 7000 
				 chassis."
                        ::= { alchassis 2 }
 
                alVportEntry OBJECT-TYPE
                        SYNTAX  AlVportEntry
                        ACCESS  not-accessible
                        STATUS  mandatory
                        DESCRIPTION
                                "Information about a specific virtual port."
                        INDEX   { alVportNumber }
 
                        ::= { alVportTable 1 }


                AlVportEntry ::=
                        SEQUENCE {
                                        alVportNumber
                                                INTEGER,
                                        alVportSlotNumber
                                                INTEGER,
                                        alVportPortNumber
                                                INTEGER,
					alVportPortType
						INTEGER,
					alVportStatus
						INTEGER,
                                        alVportControllerType
                                                INTEGER
				  }


       alVportNumber OBJECT-TYPE
                   SYNTAX  INTEGER
                   ACCESS  read-only
                   STATUS  mandatory
                   DESCRIPTION
                        "The virtual port number for which the following
                         information applies."

                ::= { alVportEntry 1 }

       alVportSlotNumber OBJECT-TYPE
                   SYNTAX  INTEGER
                   ACCESS  read-only
                   STATUS  mandatory
                   DESCRIPTION
                        "The slot number for the virtual port number 
			 which is identified by the instance of alVportNumber."
 
                ::= { alVportEntry 2 }

       alVportPortNumber OBJECT-TYPE
                   SYNTAX  INTEGER
                   ACCESS  read-only
                   STATUS  mandatory
                   DESCRIPTION
                        "The physical port number on the slot for a 
			 virtual port number which is identified by an
                         instance of alVportNumber."
 
                ::= { alVportEntry 3 }

       alVportPortType OBJECT-TYPE
                   SYNTAX  INTEGER {
-- CVG, LSI					utp(0),
					bnc(1),
					fiber(2),
					aui(3),
					not-stuffed(7)
				   }

                   ACCESS  read-only
                   STATUS  mandatory
                   DESCRIPTION
                        "The port type for the virtual port which is
                         identified by the instance of alVportNumber."
 
                ::= { alVportEntry 4 }

       alVportStatus OBJECT-TYPE
                   SYNTAX  INTEGER {
-- CVG, LSI					good(0),
					bad(1),
					removed(2)
				   }
                   ACCESS  read-only
                   STATUS  mandatory
                   DESCRIPTION
                   "The port status for the virtual port which is
                    identified by the instance of alVportNumber."
 
                ::= { alVportEntry 5 }

       alVportControllerType OBJECT-TYPE
                   SYNTAX  INTEGER
                   ACCESS  read-only
                   STATUS  mandatory
                   DESCRIPTION
                        "The controller type for the virtual port which 
			 is identified by the instance of alVportNumber." 

                ::= { alVportEntry 6 }


                alSlotToVportTable OBJECT-TYPE
                        SYNTAX  SEQUENCE OF AlSlotVportEntry
                        ACCESS  not-accessible
                        STATUS  mandatory
                        DESCRIPTION
                                "A table that contains information about
                                 each virtual port in the PowerHub 7000 
				 chassis."
                        ::= { alchassis 3 }
 
                alSlotVportEntry OBJECT-TYPE
                        SYNTAX  AlSlotVportEntry
                        ACCESS  not-accessible
                        STATUS  mandatory
                        DESCRIPTION
                                "Information about a specific virtual port."
                        INDEX   { alSlotVportSlotNumber, alSlotVportPortNumber }
 
                        ::= { alSlotToVportTable 1 }


                AlSlotVportEntry ::=
                        SEQUENCE {
                                        alSlotVportSlotNumber
                                                INTEGER,
                                        alSlotVportPortNumber
                                                INTEGER,
                                        alSlotVportNumber
                                                INTEGER,
					alSlotVportPortType
						INTEGER,
					alSlotVportStatus
						INTEGER,
                                        alSlotVportControllerType
                                                INTEGER
				  }

       alSlotVportSlotNumber OBJECT-TYPE
                   SYNTAX  INTEGER
                   ACCESS  read-only
                   STATUS  mandatory
                   DESCRIPTION
                        "The slot number for the virtual port number
                         which is identified by the instance of alVportNumber."
 
                ::= { alSlotVportEntry 1 }
 
       alSlotVportPortNumber OBJECT-TYPE 
                   SYNTAX  INTEGER                           
                   ACCESS  read-only
                   STATUS  mandatory
                   DESCRIPTION
                        "The physical port number on the slot for a
                         virtual port number which is identified by an
                         instance of alVportNumber."

                ::= { alSlotVportEntry 2 }

       alSlotVportNumber OBJECT-TYPE
                   SYNTAX  INTEGER
                   ACCESS  read-only
                   STATUS  mandatory
                   DESCRIPTION
                        "The virtual port number for which the following
                         information applies."

                ::= { alSlotVportEntry 3 }


       alSlotVportPortType OBJECT-TYPE
                   SYNTAX  INTEGER
                   ACCESS  read-only
                   STATUS  mandatory
                   DESCRIPTION
                        "The port type for the virtual port which is
                         identified by the instance of alVportNumber."
 
                ::= { alSlotVportEntry 4 }

       alSlotVportStatus OBJECT-TYPE
                   SYNTAX  INTEGER
                   ACCESS  read-only
                   STATUS  mandatory
                   DESCRIPTION
                   "The port status for the virtual port which is
                    identified by the instance of alVportNumber."
 
                ::= { alSlotVportEntry 5 }

       alSlotVportControllerType OBJECT-TYPE
                   SYNTAX  INTEGER
                   ACCESS  read-only
                   STATUS  mandatory
                   DESCRIPTION
                        "The controller type for the virtual port which 
			 is identified by the instance of alVportNumber." 

                ::= { alSlotVportEntry 6 }


                alPSTable OBJECT-TYPE
                        SYNTAX  SEQUENCE OF AlPSEntry
                        ACCESS  not-accessible
                        STATUS  mandatory
                        DESCRIPTION
                                "A table that contains information about
                                 each power supply in the PowerHub 7000
                                 chassis."
                        ::= { alchassis 4 }
 
                alPSEntry OBJECT-TYPE
                        SYNTAX  AlPSEntry
                        ACCESS  not-accessible
                        STATUS  mandatory
                        DESCRIPTION
                                "Information about a specific power supply."
                        INDEX   { alPSNumber }
 
                        ::= { alPSTable 1 }

                AlPSEntry ::=
                        SEQUENCE {
                                        alPSNumber
                                                INTEGER,
                                        alPSStatus
                                                INTEGER
                                  }

       alPSNumber  OBJECT-TYPE
                   SYNTAX  INTEGER
                   ACCESS  read-only
                   STATUS  mandatory
                   DESCRIPTION
                        "The power supply number" 
 
                ::= { alPSEntry 1 }
 
       alPSStatus OBJECT-TYPE
                   SYNTAX  INTEGER
                   ACCESS  read-only
                   STATUS  mandatory
                   DESCRIPTION
                        "The status of the power supply identified by the 
                         instance of alPSNumber."

		::= { alPSEntry 2 }

       alCpuSlot OBJECT-TYPE
                   SYNTAX  INTEGER
                   ACCESS  read-only
                   STATUS  mandatory
                   DESCRIPTION
			"The slot number in which the packet engine
			 resides"

		::= { alchassis 5 }

-- MacAddress ::= OCTET STRING (SIZE (6))

-- 1.1  The "main" subsystem -

--      1.1.1
-- 	. sysuptime - MIB-II.system.sysUpTime

--      1.1.2
-- 	. version   - AP

-- 	  For each of the CPUs, there will be a Runtime version and a 
-- 	  PROM version.

-- 	To find out about the model number of the PowerHub.
-- 	Once the model number is known, this information can be used
--	to draw the chassis picture.

--	Note to CVG : To determine the type of cards and deduce the model
--	number from that info. look at keGetInterfaces() in ifcards.c
--	in kernel directory.

               alChassisType OBJECT-TYPE
                       SYNTAX  INTEGER {
                                        model3100(1),
					model3200(2),
					model3300(3),
					model3500(4),
					model3401(5),
					model3402(6),
					model3403(7),
					model3404(8),
					model3405(9),
					model3406(10),
					model3407(11),
					model3410(12),
					model3411(13),
					model3412(14),
					model3420(15),
					model3421(16),
					model3422(17),
					model3423(18),
					model3424(19),
					model3425(20),
					model5001(21),
					model5002(22),
					model5003(23),
					model5004(24),
					model5005(25),
					model5006(26)
                                }
                        ACCESS  read-only
                        STATUS  mandatory
                        DESCRIPTION
                                "The model type of the PowerHub"

			::= { alsystem 1 }

	alMcpuRtVer OBJECT-TYPE
                   SYNTAX  DisplayString
                   ACCESS  read-only
                   STATUS  mandatory
                   DESCRIPTION
			"Runtime software version of the motherboard CPU;
			 it is an ASCII string that describes the version
			 as well as the date and time the software was
			 released from the factory."

		::= { alsystem 2 }


        alMcpuPromVer OBJECT-TYPE 
                   SYNTAX  DisplayString 
                   ACCESS  read-only 
                   STATUS  mandatory 
                   DESCRIPTION 
                        "PROM software version of the motherboard CPU;
                         it is an ASCII string that describes the version
                         as well as the date and time the software was
                         released from the factory."

             	::= { alsystem 3 } 


        alFcpuOneRtVer OBJECT-TYPE 
                   SYNTAX  DisplayString 
                   ACCESS  read-only 
                   STATUS  mandatory 
                   DESCRIPTION 
                        "Runtime software version of F-bus CPU for the first
		   FDDI board."

             	::= { alsystem 4 } 

        alFcpuTwoRtVer OBJECT-TYPE
                   SYNTAX  DisplayString
                   ACCESS  read-only
                   STATUS  mandatory
                   DESCRIPTION
                        "Runtime software version of F-bus CPU for the second
                   FDDI board." 

             	::= { alsystem 5 } 

        alFcpuOnePromVer OBJECT-TYPE
                   SYNTAX  DisplayString
                   ACCESS  read-only
                   STATUS  mandatory
                   DESCRIPTION
                        "PROM software version of F-bus CPU for the first
                   FDDI board."

             	::= { alsystem 6 } 
 
        alFcpuTwoPromVer OBJECT-TYPE
                   SYNTAX  DisplayString
                   ACCESS  read-only
                   STATUS  mandatory
                   DESCRIPTION
                        "PROM software version of F-bus CPU for the second
                   FDDI board."

                ::= { alsystem 7 }

        alRcpuOneRtVer OBJECT-TYPE
                   SYNTAX  DisplayString
                   ACCESS  read-only
                   STATUS  mandatory
                   DESCRIPTION
                        "Runtime software version of Ring CPU for the first
                   FDDI board."                            

                ::= { alsystem 8 }
 
        alRcpuTwoRtVer OBJECT-TYPE
                   SYNTAX  DisplayString
                   ACCESS  read-only
                   STATUS  mandatory                       
                   DESCRIPTION
                        "Runtime software version of Ring CPU for the second
                   FDDI board."

                ::= { alsystem 9 }

        alRcpuOnePromVer OBJECT-TYPE 
                   SYNTAX  DisplayString 
                   ACCESS  read-only 
                   STATUS  mandatory 
                   DESCRIPTION 
                        "PROM software version of Ring CPU for the first 
                   FDDI board."                             

                ::= { alsystem 10 }
  
        alRcpuTwoPromVer OBJECT-TYPE 
                   SYNTAX  DisplayString 
                   ACCESS  read-only 
                   STATUS  mandatory                        
                   DESCRIPTION 
                        "PROM software version of Ring CPU for the second 
                   FDDI board."

                ::= { alsystem 11 }


--      1.1.3
-- 	. promver   - AP


-- 1.2  The "bridge" subsystem -

-- 	1.2.1   bridge-table

-- 		The bridge table is covered in the dot1dTpFdbTable of the
-- 	dot1dTp group in the Bridge MIB ( RFC 1286 ). However, not all the
-- 	statistics that we display are covered in the Bridge MIB. e.g.
-- 	the link number and the Rule for each Ethernet-address in the Bridge
-- 	table. This part of the table will be added in the Proprietary MIB.

   		alBridgeTable OBJECT-TYPE
       			SYNTAX  SEQUENCE OF AlBridgeEntry
       			ACCESS  not-accessible
       			STATUS  mandatory
       			DESCRIPTION
               			"A table that contains information about 
               		unicast entries for which the bridge has forwarding 
			and/or filtering information.  This information 
			is used by the transparent bridging function in
			determining how to propagate a received frame."

			::= { albridge 1 }

   		alBridgeEntry OBJECT-TYPE
       			SYNTAX  AlBridgeEntry
       			ACCESS  not-accessible
			STATUS  mandatory
       			DESCRIPTION
               			"Information about a specific unicast MAC 
			address for which the bridge has some forwarding
			and/or filtering information."
       			INDEX   { alBridgeEntryAddress }

       			::= { alBridgeTable 1 }

	   	AlBridgeEntry ::=
       			SEQUENCE {
           				alBridgeEntryAddress
               					MacAddress,
           				alBridgeEntryPort
               					INTEGER,
           				alBridgeEntryLink
               					INTEGER,
					alBridgeEntryRule
						INTEGER,	
					alBridgeEntryFlags
						INTEGER
       			}

                alBridgeEntryAddress OBJECT-TYPE
                        SYNTAX  MacAddress
                        ACCESS  read-only
                        STATUS  mandatory
                        DESCRIPTION
                                "The MAC address for which the bridge
			has forwarding and/or filtering information."

			::= { alBridgeEntry 1 }

                alBridgeEntryPort OBJECT-TYPE
                        SYNTAX  INTEGER
                        ACCESS  read-only
                        STATUS  mandatory
                        DESCRIPTION
				"The port number of the port on which a
			frame having a source address equal to the
			value of the corresponding instance of
			alBridgeEntryAddress has been seen."

                        ::= { alBridgeEntry 2 } 

                alBridgeEntryLink OBJECT-TYPE
                        SYNTAX  INTEGER
                        ACCESS  read-only
                        STATUS  mandatory
                        DESCRIPTION
				"The link number on the port on which
			a frame having as ource address equal to the
			value of the corresponding instance of
			alBridgeEntryAddress has been seen. Only applies
			to the UTP port type."

                        ::= { alBridgeEntry 3 } 

                alBridgeEntryRule OBJECT-TYPE
                        SYNTAX  INTEGER
                        ACCESS  read-write
                        STATUS  mandatory
                        DESCRIPTION
				"The rule number that is applied to 
			packets that are forwarded to or from this 
			address."

                        ::= { alBridgeEntry 4 } 

                alBridgeEntryFlags OBJECT-TYPE
                        SYNTAX  INTEGER
                        ACCESS  read-only
                        STATUS  mandatory
                        DESCRIPTION
				"The status of this entry."

                        ::= { alBridgeEntry 5 } 




--         1.2.2   bridge-tableclear 
 
--                 A read-write variable outside the table itself when set, 
--         would clear the bridge table. In the application, sufficient  
--         warning should be given to the user as to the implecations of this 
--         action.

                alBridgeTblClear OBJECT-TYPE
                        SYNTAX  INTEGER
                        ACCESS  read-write
                        STATUS  mandatory
                        DESCRIPTION
                                "When set, clears the Bridge table."

			::= { albridge 2 }

-- 	1.2.3   display-cache

-- 		This will be in AP. Question - How do we return the display
-- 	cache to the manager?? May be, the whole cache can be returned as  
-- 	one huge string??

-- 	1.2.4   flush-cache

-- 		A read-write variable, when set, would clear the display-cache.
-- 		AP.

                alBrFlushCache OBJECT-TYPE
                        SYNTAX  INTEGER
                        ACCESS  read-write
                        STATUS  mandatory
                        DESCRIPTION
                                "When set, flushes the cache."

			::= { albridge 3 }


-- 	1.2.5   port

-- 		A variable in the AP bridge group-> port table. Setting or
-- 	resetting this would enable/disable that port. The port table index
-- 	would be the port number and the port table would have a number of
-- 	attributes listed below.


-- 	1.2.6   stats

-- 	  Name      Description                MIB          Group

-- 	  ---------------------------------------------------------------------
-- 	  pi  -     pkts in			AP
-- 	  po  -     pkts out			AP
-- 	  oi  -     octets in			AP
-- 	  oo  -     octets out			AP
--   	  bpi -	    Multicast packets in	AP
--	  bpo -	    Multicast packets out	AP
--	  pu  -	    Peak Utilization		AP
--        tm  -     Table misses		AP
--	  rbe -	    Receive buffer overruns	AP
--	  xbe -	    Transmit buffer overruns	AP
--	  fcs -	    FCS Errors			Ethernet   dot3StatsFCSErrors
--	  fa  -	    Frame Errors                Ethernet   dot3StatsAlignmentEr
--  	  c   -	    Total collisions		AP
--	  rc  -	    Receive Collisions		AP
--	  tc  -	    Transmit Collisions		AP
--	  q   -     Transmit Queue Length	AP
--	  gp  -	    Giant Packets		Ethernet   dot3StatsFrameTooLong
--	  lc  -	    Loss of Carrier		AP
--	  er  -	    Excessive Retries		AP

--	  The SMI definitions could look like this --

                alPortStatsTable OBJECT-TYPE
                        SYNTAX  SEQUENCE OF PortStatsEntry
                        ACCESS  not-accessible
                        STATUS  mandatory
                        DESCRIPTION
                                " Per port statistics " 

			::= { albridge 4 }

                portStatsEntry OBJECT-TYPE
                        SYNTAX  PortStatsEntry
                        ACCESS  not-accessible
                        STATUS  mandatory
                        DESCRIPTION
                                " "
                        INDEX   { portStatsPort }
			::= { alPortStatsTable 1 }

                PortStatsEntry ::= SEQUENCE {
                                        portStatsPort
                                                INTEGER,
                                        portStatsPktsIn
                                                INTEGER,
                        		portStatsPktsOut 
                                                INTEGER,
					portStatsOctetsIn  
                                                INTEGER,
					portStatsOctetsOut  
                                                INTEGER,
					portStatsMultiCastPktsIn  
                                                INTEGER,
					portStatsMulticastPktsOut  
                                                INTEGER,
					portStatsTableMisses  
                                                INTEGER,
					portStatsRcvBuffErrs  
                                                INTEGER,
					portStatsXmitBuffErrs  
                                                INTEGER,
					portStatsTotalCollisions  
                                                INTEGER,
					portStatsRcvCollisions  
                                                INTEGER,
					portStatsXmitCollisions  
                                                INTEGER,
					portStatsXmitQLen
						INTEGER,
					portStatsPeakUtilization  
                                                INTEGER,  -- ??
					portStatsCurrUtilization  
                                                INTEGER,  -- ??
					portStatsLossOfCarrier  
                                                INTEGER,
					portStatsExcessRetries  
                                                INTEGER

                }

		portStatsPort   OBJECT-TYPE
			SYNTAX	INTEGER
			ACCESS	read-only
			STATUS	mandatory
			DESCRIPTION	
				" "
			::= { portStatsEntry 1 }

                portStatsPktsIn OBJECT-TYPE
                        SYNTAX  INTEGER
                        ACCESS  read-only
                        STATUS  mandatory
                        DESCRIPTION
                                " "
                        ::= { portStatsEntry 2 }
	
                portStatsPktsOut OBJECT-TYPE 
                        SYNTAX  INTEGER 
                        ACCESS  read-only 
                        STATUS  mandatory 
                        DESCRIPTION 
                                " " 
                        ::= { portStatsEntry 3 }

                portStatsOctetsIn OBJECT-TYPE 
                        SYNTAX  INTEGER 
                        ACCESS  read-only 
                        STATUS  mandatory 
                        DESCRIPTION 
                                " " 
                        ::= { portStatsEntry 4 }

                portStatsOctetsOut OBJECT-TYPE
                        SYNTAX  INTEGER
                        ACCESS  read-only
                        STATUS  mandatory
                        DESCRIPTION
                                " "
                        ::= { portStatsEntry 5 }

                portStatsMultiCastPktsIn OBJECT-TYPE 
                        SYNTAX  	 INTEGER 
                        ACCESS  	 read-only 
                        STATUS  	 mandatory 
                        DESCRIPTION 
                                	" " 
                        ::= { portStatsEntry 6 }

                portStatsMulticastPktsOut OBJECT-TYPE 
                        SYNTAX  	 INTEGER 
                        ACCESS  	 read-only 
                        STATUS  	 mandatory 
                        DESCRIPTION 
                                	" " 
                        ::= { portStatsEntry 7 }
			
                portStatsTableMisses 	OBJECT-TYPE 
                        SYNTAX  	INTEGER 
                        ACCESS  	read-only 
                        STATUS  	mandatory 
                        DESCRIPTION 
                                " " 
                        ::= { portStatsEntry 8 }

                portStatsRcvBuffErrs 	OBJECT-TYPE 
                        SYNTAX  	INTEGER 
                        ACCESS  	read-only 
                        STATUS  	mandatory 
                        DESCRIPTION 
                                " " 
                        ::= { portStatsEntry 9 }

                portStatsXmitBuffErrs 	OBJECT-TYPE 
                        SYNTAX  	INTEGER 
                        ACCESS  	read-only 
                        STATUS  	mandatory 
                        DESCRIPTION 
                                " " 
                        ::= { portStatsEntry 10 }

                portStatsTotalCollisions OBJECT-TYPE 
                        SYNTAX  	 INTEGER 
                        ACCESS  	 read-only 
                        STATUS  	 mandatory 
                        DESCRIPTION 
                                " " 
                        ::= { portStatsEntry 11 }
		
                portStatsRcvCollisions 	OBJECT-TYPE 
                        SYNTAX  	INTEGER 
                        ACCESS  	read-only 
                        STATUS  	mandatory 
                        DESCRIPTION 
                                " " 
                        ::= { portStatsEntry 12 }

                portStatsXmitCollisions	OBJECT-TYPE 
                        SYNTAX  	INTEGER 
                        ACCESS  	read-only 
                        STATUS  	mandatory 
                        DESCRIPTION 
                                " " 
                        ::= { portStatsEntry 13 }

                portStatsXmitQLen OBJECT-TYPE 
                        SYNTAX    INTEGER 
                        ACCESS    read-only 
                        STATUS    mandatory 
                        DESCRIPTION 
                                " " 
                        ::= { portStatsEntry 14 }

                portStatsPeakUtilization OBJECT-TYPE 
                        SYNTAX  	 INTEGER 
                        ACCESS  	 read-only 
                        STATUS  	 mandatory 
                        DESCRIPTION 
                                " " 
                        ::= { portStatsEntry 15 }

                portStatsCurrUtilization OBJECT-TYPE  
                        SYNTAX           INTEGER  
                        ACCESS           read-only  
                        STATUS           mandatory  
                        DESCRIPTION  
                                " "  
                        ::= { portStatsEntry 16 }

                portStatsLossOfCarrier   OBJECT-TYPE  
                        SYNTAX           INTEGER  
                        ACCESS           read-only  
                        STATUS           mandatory  
                        DESCRIPTION  
                                " "  
                        ::= { portStatsEntry 17 }

                portStatsExcessRetries   OBJECT-TYPE  
                        SYNTAX           INTEGER  
                        ACCESS           read-only  
                        STATUS           mandatory  
                        DESCRIPTION  
                                " "  
                        ::= { portStatsEntry 18 }


--	1.2.7     stats-clear

--		  A variable outside the stats table to clear the stats. 

                alBridgeStatsClear OBJECT-TYPE
                        SYNTAX  INTEGER
                        ACCESS  read-write
                        STATUS  mandatory
                        DESCRIPTION
                                "When set, clears the statistics for the
			bridge."

			::= { albridge 5 }


--	1.2.8     ppstats  

--	1.2.8.1   pp enl/dis   

--                        The command to enable or disable the port-to-port
--	statistics gathering. It should a read-write variable outside the
--	port-to-port table (see below). This same variable can be used to
--      clear the port-to-port table. Thus this variable will take three
--	values - for enabling, disabling and clearing the table.

		alBridgePPControl OBJECT-TYPE
                        SYNTAX  INTEGER {
						enable(1),
-- CVG, LSI						disable(0),
						clear(2)
					}
                        ACCESS  read-write
                        STATUS  mandatory
                        DESCRIPTION
                                "When set to 0 , disables the port to port 
				 collection of the stats; when set to 1, 
				 enables the port to port stats collection;
				 when set to 2, clears the port to port
				 stats."

                        ::= { albridge 6 }
--	1.2.8.2   pp 

--		  To show the port-to-port statistics in a matrix format.
--	This table should be designed such that the index for the table
--	is a dual index which qualifies the source-destination port pair. 

	alPortToPortTable  OBJECT-TYPE
		SYNTAX	SEQUENCE OF PortToPortEntry
		ACCESS	not-accessible
		STATUS 	mandatory
		DESCRIPTION
			  "Statistics for port to port traffic."

		::= { albridge 7 }

	portToPortEntry	  OBJECT-TYPE
		SYNTAX	PortToPortEntry
		ACCESS	not-accessible
		STATUS	mandatory
		DESCRIPTION
			  " Statistics for port to port traffic"

		INDEX { alPPSourecPort, alPPDestinationPort }
		::= { alPortToPortTable 1 }

	PortToPortEntry ::= SEQUENCE {
				alPPSourecPort
					INTEGER,
				alPPDestinationPort
					INTEGER,
				portToPortPackets
					INTEGER,
				portToPortOctets
					INTEGER
	}

	alPPSourecPort OBJECT-TYPE
		SYNTAX	INTEGER
		ACCESS	read-only
		STATUS	mandatory
		DESCRIPTION
			"Source port number"
		::= { portToPortEntry 1 }
		
        alPPDestinationPort OBJECT-TYPE 
                SYNTAX  INTEGER 
                ACCESS  read-only 
                STATUS  mandatory 
                DESCRIPTION 
                        "Source port number" 
                ::= { portToPortEntry 2 } 

	portToPortPackets OBJECT-TYPE
		SYNTAX	INTEGER
		ACCESS	read-only
		STATUS	mandatory
		DESCRIPTION
			" "
		::= { portToPortEntry 3 }


	portToPortOctets OBJECT-TYPE
                SYNTAX  INTEGER
                ACCESS  read-only
                STATUS  mandatory
                DESCRIPTION
                        " "
                ::= { portToPortEntry 4 }	


--	1.2.10	showcfg

--	 1.2.10.1	 aging-time  
		
--		 This maps to the dot1dTpAgingTime variable in the Bridge MIB.

--	 1.2.10.2	 spanning tree

--		 This corresponds to the dot1dStp group and the 
--		 dot1dStpPortTable of the Bridge MIB.

--	  1.2.10.2.1 	Bridge-wide parameters

--		 Status		       - see 1.2.9 above.
--		 System Priority       - dot1dStpPriority
--		 Spanning Tree Address - ??
--		 My Bridge Address     - dot1dBaseBridgeAddress
--		 Max Age	       - dot1dStpMaxAge
--		 Hello Time 	       - dot1dStpHelloTime
--		 Forward Delay	       - dot1dStpForwardDelay

--	  1.2.10.2.2 	Per port parameters

--		 Port 		       - dot1dStpPort
--		 Priority ( of port )  - dot1dStpPortPriority
--		 Designated Bridge     - dot1dStpPortDesignatedBridge
--		 Designated Port       - dot1dStpPortDesignatedPort
--		 Designated Cost       - dot1dStpPortDesignatedCost

-- 	1.2.10.3 	ports

--		There are 3 parameters shown for this command per port - 
--		Source Rule, Destination Rule and a flag that tells 
--		whether or not to block the learned entries. These can be 
--		constructed in the AP MIB as a Port Configuration Table
--		with port number as the Index. The columns of the table
--		will be the three parameters stated above. e.g this group
--		may look like the following --

		alPortConfigTable OBJECT-TYPE
			SYNTAX	SEQUENCE OF PortConfigEntry
			ACCESS	not-accessible
			STATUS	mandatory
			DESCRIPTION
				" Per port configuration for configuring
			Source and Destination Rules etc."

			::= { albridge 8 }

		portConfigEntry OBJECT-TYPE
			SYNTAX	PortConfigEntry
			ACCESS	not-accessible
			STATUS	mandatory
			DESCRIPTION
				" "				
			INDEX   { portConfigPort }
			::= { alPortConfigTable 1 }

		PortConfigEntry ::= SEQUENCE {
					portConfigPort
						INTEGER,
					portConfigSrcRule
						INTEGER,
					portConfigDstRule
						INTEGER,
					portConfigBlockLearnedEntries
						INTEGER
		}

		portConfigPort OBJECT-TYPE
			SYNTAX	INTEGER
			ACCESS	read-only
			STATUS	mandatory
			DESCRIPTION
				" The port number for this table entry"
			::= { portConfigEntry 1 }
		
		portConfigSrcRule OBJECT-TYPE
			SYNTAX	INTEGER
			ACCESS  read-write
			STATUS	mandatory
			DESCRIPTION
				"Source Rule for the port number identified
			by the instance of portConfigPort"

			::= { portConfigEntry 2 }

		portConfigDstRule OBJECT-TYPE
			SYNTAX	INTEGER
			ACCESS	read-write
			STATUS	mandatory
			DESCRIPTION
				"Destination Rule for the port number 
			identified by the instance of portConfigPort"

			::= { portConfigEntry 3 }

		portConfigBlockLearnedEntries OBJECT-TYPE
			SYNTAX	INTEGER 
-- CVG, LSI                                       { 
-- CVG, LSI						true(1), false(0) }
			ACCESS	read-write
			STATUS	mandatory
			DESCRIPTION
				"When set to True (1), the port identified 
			by the instance of portConfigPort will block the
			learned entries; if set to False (0) the port will
			not block the learned entries"
	
			::= { portConfigEntry 4 }

--	 1.2.10.4  ipbridging
		
--			A read-write variable that when set/reset will
--			enable/disable IP bridging. 

                alBridgeIpBridging OBJECT-TYPE
                        SYNTAX  INTEGER 
-- CVG, LSI				{ enable(1), disable(0) }
                        ACCESS  read-write
                        STATUS  mandatory
                        DESCRIPTION
                                "When set to enable(1), enables the IP
			bridging and if set to disable(0), disables the
			IP bridging."

			::= { albridge 9 }


--	 1.2.10.5  groups  TBD
		
--	1.2.11	set

--		All the commands that are used in this group to set various
--	parameters are covered under previously described groups.

--	  1.2.11.1	aging - dot1dTpAgingTime in the Bridge MIB

--	  1.2.11.2	bridge-priority - dot1dStpPriority
	
--	  1.2.11.3	timer-threshhold
--			     max-age       - dot1dStpMaxAge
--			     hello-time    - dot1dStpHelloTime
--			     forward-delay - dot1dStpForwardDelay


--	  1.2.11.4	source-rule <port-num> <rule-num> 
--			      Refer to portConfigEntry

--	  1.2.11.5	dest-rule <port-num> <rule-num>
--			      Refer to portConfigEntry

--	  1.2.11.6	ipbridging
--			     Refer to 1.2.10.4 above. 
			      
--	  1.2.11.7	port-priority	   - dot1dStpPortPriority

--	  1.2.11.8	block-lentries     - Refer to portConfigEntry.
--	  1.2.11.9	template

                alBrTemplateTable OBJECT-TYPE
                        SYNTAX  SEQUENCE OF BrTemplateEntry
                        ACCESS  not-accessible
                        STATUS  mandatory
                        DESCRIPTION
                                " Per template information"
			::= { albridge 10 } 

                brTemplateEntry OBJECT-TYPE
                        SYNTAX  BrTemplateEntry
                        ACCESS  not-accessible
                        STATUS  mandatory
                        DESCRIPTION
                                " "
                        INDEX   { brTemplateNumber }
                        ::= { alBrTemplateTable 1 }
 
                BrTemplateEntry ::= SEQUENCE {
                                        brTemplateNumber
                                                INTEGER,
                                        brTemplateOffset
						INTEGER,
					brTemplateMask
						Counter,
					brTemplateComparator
						Counter,
					brTemplateOption
						INTEGER
				}


                brTemplateNumber OBJECT-TYPE
                        SYNTAX  INTEGER
                        ACCESS  read-write
                        STATUS  mandatory
                        DESCRIPTION
                                "The number of the template with which it
                        is identified."
 
                        ::= { brTemplateEntry 1 }

                brTemplateOffset OBJECT-TYPE
                        SYNTAX  INTEGER
                        ACCESS  read-write
                        STATUS  mandatory
                        DESCRIPTION
                                "A displacement, in octets, from the 
			beginning of the packet. This must be a multiple of
			4 in the range from 0 to 124 decimal. A value of -1 will 
			delete the entry"
 
                        ::= { brTemplateEntry 2 }

                brTemplateMask OBJECT-TYPE
                        SYNTAX  Counter   -- cvg  ??
                        ACCESS  read-write
                        STATUS  mandatory
                        DESCRIPTION
                                " "   
 
                        ::= { brTemplateEntry 3 }

                brTemplateComparator OBJECT-TYPE
                        SYNTAX  Counter   -- cvg  ??
                        ACCESS  read-write
                        STATUS  mandatory
                        DESCRIPTION
                                " "
 
                        ::= { brTemplateEntry 4 }

                brTemplateOption OBJECT-TYPE
                        SYNTAX  INTEGER   -- cvg  ??
                        ACCESS  read-write
                        STATUS  mandatory
                        DESCRIPTION
                                " "

                        ::= { brTemplateEntry 5 }


-- 1.2.11.10	set rule

                alBrRuleTable OBJECT-TYPE
                        SYNTAX  SEQUENCE OF BrRuleEntry
                        ACCESS  not-accessible
                        STATUS  mandatory
                        DESCRIPTION
                                " Per rule information"

			::= { albridge 11 }
 
                brRuleEntry OBJECT-TYPE
                        SYNTAX  BrRuleEntry
                        ACCESS  not-accessible
                        STATUS  mandatory
                        DESCRIPTION
                                " "
                        INDEX   { brRuleNumber }
                        ::= { alBrRuleTable 1 }
 
                BrRuleEntry ::= SEQUENCE {
                                        brRuleNumber
                                                INTEGER,
                                        brRuleStatement
						DisplayString
				}


                brRuleNumber OBJECT-TYPE
                        SYNTAX  INTEGER
                        ACCESS  read-write
                        STATUS  mandatory
                        DESCRIPTION
                                "The number of the rule with which it is
                        identified."
 
                        ::= { brRuleEntry 1 }


                brRuleStatement OBJECT-TYPE 
                        SYNTAX  DisplayString
                        ACCESS  read-write
                        STATUS  mandatory
                        DESCRIPTION
                                "Rule statement"
 
                        ::= { brRuleEntry 2 }

	
-- 1.2.11.11  set node - Assigning rules to a specific node
--			 An entry is identified by a combination of port
--			 number and MAC address.

                alBrRuleToNodeTable OBJECT-TYPE
                        SYNTAX  SEQUENCE OF AlBrRuleToNodeEntry
                        ACCESS  not-accessible
                        STATUS  mandatory
                        DESCRIPTION
                                " "
			::= { albridge 12 }
 
                alBrRuleToNodeEntry OBJECT-TYPE
                        SYNTAX  AlBrRuleToNodeEntry
                        ACCESS  not-accessible
                        STATUS  mandatory
                        DESCRIPTION
                                " "
                        INDEX   { brRuleToNodePort }

                        ::= { alBrRuleToNodeTable 1 }

                AlBrRuleToNodeEntry ::= SEQUENCE {
                                        brRuleToNodePort
                                                INTEGER,
					brRuleToNodeMacAddr
						PhysAddress,
					brRuleToNodeRule
						INTEGER	
                }

                brRuleToNodePort OBJECT-TYPE
                        SYNTAX  INTEGER
                        ACCESS  read-write
                        STATUS  mandatory
                        DESCRIPTION
                                "The number of the port for which this
			rule applies" 
 
                        ::= { alBrRuleToNodeEntry 1 }


                brRuleToNodeMacAddr OBJECT-TYPE
                        SYNTAX  PhysAddress
                        ACCESS  read-write
                        STATUS  mandatory
                        DESCRIPTION
                                "The source MAC address"

                        ::= { alBrRuleToNodeEntry 2 }

                brRuleToNodeRule OBJECT-TYPE
                        SYNTAX  INTEGER
                        ACCESS  read-write
                        STATUS  mandatory
                        DESCRIPTION
                                "The rule number that applies to this
			entry."

                        ::= { alBrRuleToNodeEntry 3 }

-- 1.2.11.12  set group -
 
                alBrGroupTable OBJECT-TYPE
                        SYNTAX  SEQUENCE OF AlBrGroupEntry
                        ACCESS  not-accessible
                        STATUS  mandatory
                        DESCRIPTION
                                " "
                        ::= { albridge 13 }
 
                alBrGroupEntry OBJECT-TYPE
                        SYNTAX  AlBrGroupEntry
                        ACCESS  not-accessible
                        STATUS  mandatory
                        DESCRIPTION
                                " "
                        INDEX   { brGroupNumber }
 
                        ::= { alBrGroupTable 1 }
 
                AlBrGroupEntry ::= SEQUENCE {
					brGroupNumber
						INTEGER,
                                        brGroupPortsMask
                                                INTEGER,
                                        brGroupName
                                                OCTET STRING
                }

                brGroupNumber OBJECT-TYPE
                        SYNTAX  INTEGER
                        ACCESS  read-write
                        STATUS  mandatory
                        DESCRIPTION
                                "The group number by which the group is
			identified with."
 
                        ::= { alBrGroupEntry 1 }

                brGroupPortsMask OBJECT-TYPE
                        SYNTAX  INTEGER
                        ACCESS  read-write
                        STATUS  mandatory
                        DESCRIPTION
                                "The ports associated with the group number
                        identified by the instance of brGroupNumber."
 
                        ::= { alBrGroupEntry 2 }


                brGroupName OBJECT-TYPE
                        SYNTAX  OCTET STRING
                        ACCESS  read-write
                        STATUS  mandatory
                        DESCRIPTION
                                "The name of the group for which this
                        entry applies"
 
                        ::= { alBrGroupEntry 3 }
 
--	1.2.9	spantree

--		A read-write variable that can be set/reset for turning
--		on/off Spanning tree protocol. AP.

                alBridgeSTPControl OBJECT-TYPE
                        SYNTAX  INTEGER 
-- CVG, LSI					{ enable(1), disable(0) }
                        ACCESS  read-write
                        STATUS  mandatory
                        DESCRIPTION
                                "When set to 0 , disables the  spanning tree.
                                 set to 1, enables the spanning tree."

                        ::= { albridge 14 }

--		sa command

		alPortStateTable OBJECT-TYPE
			SYNTAX	SEQUENCE OF PortStateEntry
			ACCESS	not-accessible
			STATUS	mandatory
			DESCRIPTION
				" Per port state information about 
			spanning tree, dignostics and management." 

			::= { albridge 15 }

		portStateEntry OBJECT-TYPE
			SYNTAX	PortStateEntry
			ACCESS	not-accessible
			STATUS	mandatory
			DESCRIPTION
				" "				
			INDEX   { portStatePort }
			::= { alPortStateTable 1 }

		PortStateEntry ::= SEQUENCE {
					portStatePort
						INTEGER,
					portStateDiag
						INTEGER,
					portStateMgmt
						INTEGER,
					portStateStp
						INTEGER,
					portStatePortName
						DisplayString
		}

		portStatePort OBJECT-TYPE
			SYNTAX	INTEGER
			ACCESS	read-only
			STATUS	mandatory
			DESCRIPTION
				" The port number for this table entry"
			::= { portStateEntry 1 }
		
		portStateDiag OBJECT-TYPE
			SYNTAX	INTEGER 
-- CVG, LSI				{ unknown(0), good(1), bad(2) }
			ACCESS  read-only
			STATUS	mandatory
			DESCRIPTION
			 	"The diagnostics state of the port"	

			::= { portStateEntry 2 }

		portStateMgmt OBJECT-TYPE
			SYNTAX	INTEGER 
-- CVG, LSI				{ enabled(1), disabled(0) }
			ACCESS	read-only
			STATUS	mandatory
			DESCRIPTION
				"The management state of the port"

			::= { portStateEntry 3 }

		portStateStp OBJECT-TYPE
			SYNTAX	INTEGER 
			ACCESS	read-only
			STATUS	mandatory
			DESCRIPTION
				"The spanning tree state of the port. "	
			::= { portStateEntry 4 }

                portStatePortName OBJECT-TYPE
                        SYNTAX  DisplayString
                        ACCESS  read-only
                        STATUS  mandatory
                        DESCRIPTION
                                "The name of this port"  
                        ::= { portStateEntry 5 }
                                                

--	1.3.1.2	
--		. link-stats-collect 
-- 					enable/disable stats collection

		alLinkStatsCollect OBJECT-TYPE
			SYNTAX	INTEGER
			ACCESS	read-write
			STATUS	mandatory
			DESCRIPTION
				"When set to enable(1), per link stats
			collection is enabled; when set to disable(0), 
			the per link stats are not collected."

			::= { almgmt 2 }
			
--	1.3.1.3
--		. link-stats-clear   
					-- clear stats collection

		alLinkStatsClear OBJECT-TYPE
                        SYNTAX  INTEGER
                        ACCESS  read-write 
                        STATUS  mandatory
                        DESCRIPTION 
				"When set, clears the link stats"

			::= { almgmt 3 }

--	1.3.1.4
--		. link-stats	     
					-- per link stats (pkts and errors)

		alLinkStatsTable OBJECT-TYPE
			SYNTAX	SEQUENCE OF LinkStatsEntry
			ACCESS	not-accessible
			STATUS	mandatory
			DESCRIPTION
				"Per link stats table"

			::= { almgmt 4 }

		linkStatsEntry 	OBJECT-TYPE
			SYNTAX	LinkStatsEntry
			ACCESS	not-accessible
			STATUS	mandatory
			DESCRIPTION
				" "
			INDEX { linkStatsPort, linkStatsLink }
			::= { alLinkStatsTable 1 }

		LinkStatsEntry ::= SEQUENCE {
	
			linkStatsPort
				INTEGER,
			linkStatsLink
				INTEGER,
			linkStatsPktsIn
				INTEGER,
			linkStatsOctetsIn
				INTEGER,
			linkStatsBMCastPktsIn
				INTEGER,
			linkStatsGiantPkts
				INTEGER,
			linkStatsFrameErrs
				INTEGER,
			linkStatsFCSErrs
				INTEGER,
			linkStatsRcvCollisions
				INTEGER
		}

		linkStatsPort OBJECT-TYPE
			SYNTAX	INTEGER
			ACCESS	read-only
			STATUS	mandatory
			DESCRIPTION
				"Port Number"
			::= { linkStatsEntry 1 }

                linkStatsLink OBJECT-TYPE
                        SYNTAX  INTEGER
                        ACCESS  read-only
                        STATUS  mandatory
                        DESCRIPTION
                                "Link Number"
                        ::= { linkStatsEntry 2 }

                linkStatsPktsIn OBJECT-TYPE
                        SYNTAX  INTEGER
                        ACCESS  read-only
                        STATUS  mandatory
                        DESCRIPTION
                                "Pkts In - corresponds to pi"
                        ::= { linkStatsEntry 3 }
			
                linkStatsOctetsIn OBJECT-TYPE
                        SYNTAX  INTEGER
                        ACCESS  read-only
                        STATUS  mandatory
                        DESCRIPTION
                                "Octets In - corresponds to oi"
                        ::= { linkStatsEntry 4 }

                linkStatsBMCastPktsIn OBJECT-TYPE
                        SYNTAX  INTEGER
                        ACCESS  read-only
                        STATUS  mandatory
                        DESCRIPTION
                                "Bmcast Pks In - corresponds to bpi"
                        ::= { linkStatsEntry 5 }

                linkStatsGiantPkts OBJECT-TYPE
                        SYNTAX  INTEGER
                        ACCESS  read-only
                        STATUS  mandatory
                        DESCRIPTION
                                "Giant Pkts -  corresponds to gp"
                        ::= { linkStatsEntry 6 }

                linkStatsFrameErrs OBJECT-TYPE
                        SYNTAX  INTEGER
                        ACCESS  read-only
                        STATUS  mandatory
                        DESCRIPTION
                                "Frame Errors - corresponds to fa"
                        ::= { linkStatsEntry 7 }

                linkStatsFCSErrs OBJECT-TYPE
                        SYNTAX  INTEGER
                        ACCESS  read-only
                        STATUS  mandatory
                        DESCRIPTION
                                "FCS Errors corresponds to fcs"
                        ::= { linkStatsEntry 8 }

                linkStatsRcvCollisions OBJECT-TYPE
                        SYNTAX  INTEGER
                        ACCESS  read-only
                        STATUS  mandatory
                        DESCRIPTION
                                "Receive Collisions- corresponds to rc"
                        ::= { linkStatsEntry 9 }

			
--	1.3.1.5

--		. link-state-display - per link state
--		. showcfg	     - per link
--		. link-state-control - enable/disable link

                alLinkControlTable OBJECT-TYPE
                        SYNTAX  SEQUENCE OF LinkControlEntry
                        ACCESS  not-accessible
                        STATUS  mandatory
                        DESCRIPTION
                                "Per link stats table"

			::= { almgmt 5 }

                linkControlEntry  OBJECT-TYPE
                        SYNTAX  LinkControlEntry
                        ACCESS  not-accessible
                        STATUS  mandatory
                        DESCRIPTION
                                " "
                        INDEX { linkControlPort, linkControlLink }
                        ::= { alLinkControlTable 1 }

		LinkControlEntry ::= SEQUENCE {
					linkControlPort
						INTEGER,
					linkControlLink
						INTEGER,
					linkControlEnlState
						INTEGER,
					linkControlLinkTest
						INTEGER,
					linkControlPartition
						INTEGER,
					linkControlPolarity
						INTEGER,
					linkControlEnable
						INTEGER
		}
		

		linkControlPort	OBJECT-TYPE
			SYNTAX	INTEGER
			ACCESS	read-only
			STATUS	mandatory
			DESCRIPTION	
				"Port number for this entry."
			::= { linkControlEntry 1 }

                linkControlLink OBJECT-TYPE
                        SYNTAX  INTEGER
                        ACCESS  read-only
                        STATUS  mandatory
                        DESCRIPTION     
                                "Link number for this entry."
                        ::= { linkControlEntry 2 }

                linkControlEnlState OBJECT-TYPE
                        SYNTAX  INTEGER
                        ACCESS  read-only
                        STATUS  mandatory
                        DESCRIPTION     
                                "Enable state for the link corresponds to enl
			option in lkd command."
                        ::= { linkControlEntry 3 }

                linkControlLinkTest OBJECT-TYPE
                        SYNTAX  INTEGER
                        ACCESS  read-only
                        STATUS  mandatory
                        DESCRIPTION     
                                "Link test status for the link; corresponds to
			lt option of the lkd command."
                        ::= { linkControlEntry 4 }

                linkControlPartition OBJECT-TYPE
                        SYNTAX  INTEGER
                        ACCESS  read-only
                        STATUS  mandatory
                        DESCRIPTION     
                                "Partitioning state of the link"
                        ::= { linkControlEntry 5 }

                linkControlPolarity OBJECT-TYPE
                        SYNTAX  INTEGER
                        ACCESS  read-only
                        STATUS  mandatory
                        DESCRIPTION     
                                "Polarity of the link"
                        ::= { linkControlEntry 6 }

                linkControlEnable OBJECT-TYPE
                        SYNTAX  INTEGER
                        ACCESS  read-write
                        STATUS  mandatory
                        DESCRIPTION     
                                "Setting the value of this object to Enable
			(1), will enable the link and setting to Disable(2),
			will disable the link."
                        ::= { linkControlEntry 7 }

			 
--		. setlinktype	     - per port

		alPortLinkTable OBJECT-TYPE
                        SYNTAX  SEQUENCE OF PortLinkEntry
                        ACCESS  not-accessible
                        STATUS  mandatory
                        DESCRIPTION
                                " Per port link type "

			::= { almgmt 6 }

                portLinkEntry OBJECT-TYPE
                        SYNTAX  PortLinkEntry
                        ACCESS  not-accessible
                        STATUS  mandatory
                        DESCRIPTION
                                " "
                        INDEX   { portLinkPort }
			::= { alPortLinkTable 1 }

                PortLinkEntry ::= SEQUENCE {
                                        portLinkPort
                                                INTEGER,
                                        portLinkType
                                                INTEGER
		}

                portLinkPort   OBJECT-TYPE
                        SYNTAX  INTEGER
                        ACCESS  read-only
                        STATUS  mandatory
                        DESCRIPTION
                                "The port number for which the port type
			is to be set"
                        ::= { portLinkEntry 1 }

		portLinkType OBJECT-TYPE 
                        SYNTAX  INTEGER {
						aui(1),
						bnc(2),
						bnct(3),
						utp(4),
						fiber(5),
						unknown(6)
				}
                        ACCESS  read-write 
                        STATUS  mandatory 
                        DESCRIPTION 
                                "The type of port"

                        ::= { portLinkEntry 2 }


--		. fiber-security-violation
--		. fiberauistatus

                alFiberStatsTable OBJECT-TYPE
                        SYNTAX  SEQUENCE OF FiberStatsEntry
                        ACCESS  not-accessible
                        STATUS  mandatory
                        DESCRIPTION
                                " Per port fiber stats and Fiber Security"
			::= { almgmt 7 }

                fiberStatsEntry OBJECT-TYPE
                        SYNTAX  FiberStatsEntry
                        ACCESS  not-accessible
                        STATUS  mandatory
                        DESCRIPTION
                                " "
                        INDEX   { fiberStatsPort }
			::= { alFiberStatsTable 1 }
 
                FiberStatsEntry ::= SEQUENCE {
                                        fiberStatsPort
                                                INTEGER,
                                        fiberAuiStatus 
                                                INTEGER,
					fiberSecurityViolation
						INTEGER
                }


		fiberStatsPort OBJECT-TYPE
                        SYNTAX  INTEGER
                        ACCESS  read-only
                        STATUS  mandatory
                        DESCRIPTION
                                "The fiber port for which the stats are
			requested or the Fiber violation is set "

                        ::= { fiberStatsEntry 1 }

                fiberAuiStatus OBJECT-TYPE
                        SYNTAX  INTEGER
                        ACCESS  read-only
                        STATUS  mandatory
                        DESCRIPTION
                                "The fiber aui status for the port that is 
                        specified by the instance of fiberStatsPort"
 
                        ::= { fiberStatsEntry 2 }

                fiberSecurityViolation OBJECT-TYPE
                        SYNTAX  INTEGER {
						detect(1),
						ignore(2),
						clear(3)
				}
                        ACCESS  read-write
                        STATUS  mandatory
                        DESCRIPTION
                                "The fiber port for which the stats are
                        requested or the Fiber violation is set "
 
                        ::= { fiberStatsEntry 3 }


-- *** CVG		. utpstatus  What is the difference between utpstatus
--		  and the link-state-display ??

--	1.3.2	Set/show generic system parameters --

--		. ethaddr
--		. promver
--		. gettime/settime

--	1.3.3	Saving/restoring configuration files --

--		. fremove
--		. endcfg
--		. listdir
--		. showfile

--		The above four commands are very specific to the floppy
--		disk operation and will be matched to any MIB variable.

--		. readcfg
--		. savecfg

--	1.3.4	RS-232 ports configuration --
		
--		. dcd-detection
--		. setbaud
		
--	1.3.5	Port monitoring --

--		. port-monitor close
		
		alPortMonitorClose OBJECT-TYPE
                       SYNTAX  INTEGER
                       ACCESS  read-write
                       STATUS  mandatory
                       DESCRIPTION
                                "Setting the value to close(1), will 
		   	turn the port monitoring off."
	
			::= { almgmt 8 }

--		. port-monitor view

        	alPortMonitorTable  OBJECT-TYPE
                	SYNTAX  SEQUENCE OF PortMonitorEntry
                	ACCESS  not-accessible
                	STATUS  mandatory
                	DESCRIPTION
                          " "

			::= { almgmt 9 }

        	portMonitorEntry   OBJECT-TYPE
                	SYNTAX  PortMonitorEntry
                	ACCESS  not-accessible
                	STATUS  mandatory
                	DESCRIPTION
                          " "
                	INDEX { portMonSrcPort, portMonDstPort }
                	::= { alPortMonitorTable 1 }

        	PortMonitorEntry ::= SEQUENCE {
                                		portMonSrcPort
                                        		INTEGER,
                                		portMonDstPort
                                        		INTEGER,
                                		portMonTrafficType
                                        		INTEGER
        			
				}
		

		portMonSrcPort   OBJECT-TYPE 
                        SYNTAX  INTEGER  
                        ACCESS  read-write 
                        STATUS  mandatory 
                        DESCRIPTION 
                          "The traffic to/from this port will be monitored
			   on the portMonDstPort" 
			::= { portMonitorEntry 1 }

                portMonDstPort   OBJECT-TYPE  
                        SYNTAX  INTEGER   
                        ACCESS  read-write  
                        STATUS  mandatory  
                        DESCRIPTION  
                          "The traffic to/from portMonSrcPort will be 
			   monitored on this port "  
                        ::= { portMonitorEntry 2 }

                portMonTrafficType   OBJECT-TYPE  
			SYNTAX  INTEGER {
-- CVG, LSI                                                notapplicable(0),
                                                forwarded(1),
                                                incoming(2),
                                                forwardedincoming(3),
                                                generated(4),
                                                forwardedgenerated(5),
                                                incominggenerated(6),
                                                all(7)
                                        }
                        ACCESS  read-write  
                        STATUS  mandatory  
                        DESCRIPTION  
                          " Setting this value to 1, will let the port monitor
			monitor forwarded traffic; setting to 0 means the
			forwarded traffic will not be monitored."  

                        ::= { portMonitorEntry 3 }


--	1.3.6	Reboot --

--		. reboot

		alReboot OBJECT-TYPE
                   SYNTAX  INTEGER
                   ACCESS  read-write
                   STATUS  mandatory
                   DESCRIPTION
                           "Setting the value to Reboot(1), will reboot
			    the PowerHub." 
		   ::= { almgmt 10 }

                alPortMonitorViewTable  OBJECT-TYPE
                        SYNTAX  SEQUENCE OF PortMonitorViewEntry
                        ACCESS  not-accessible
                        STATUS  mandatory
                        DESCRIPTION
                          " "

                        ::= { almgmt 11 }

                portMonitorViewEntry   OBJECT-TYPE
                        SYNTAX  PortMonitorViewEntry
                        ACCESS  not-accessible
                        STATUS  mandatory
                        DESCRIPTION
                          " "
                        INDEX { portMonViewSrcPort, portMonViewDstPort }
                        ::= { alPortMonitorViewTable 1 }

                PortMonitorViewEntry ::= SEQUENCE {
                                                portMonViewSrcPort
                                                        INTEGER,
                                                portMonViewDstPort
                                                        INTEGER,
                                                portMonViewMonitorPort
                                                        INTEGER
                                
                                }


		portMonViewSrcPort   OBJECT-TYPE 
                        SYNTAX  INTEGER  
                        ACCESS  read-only 
                        STATUS  mandatory 
                        DESCRIPTION 
                          "The traffic from this port  to the port
			   designated by portMonViewDstPort will be monitored
			   on portMonViewMonitorPort."
			::= { portMonitorViewEntry 1 }

                portMonViewDstPort   OBJECT-TYPE  
                        SYNTAX  INTEGER   
                        ACCESS  read-only  
                        STATUS  mandatory  
                        DESCRIPTION  
                          "The traffic to this port from the port
			   designated by portMonViewSrcPort will be monitored
			   on portMonViewMonitorPort." 
                        ::= { portMonitorViewEntry 2 }

                portMonViewMonitorPort   OBJECT-TYPE
                        SYNTAX  INTEGER
                        ACCESS  read-write
                        STATUS  mandatory                  
                        DESCRIPTION
                          "The traffic to portMonViewDstPort from the port 
                           designated by portMonViewSrcPort will be monitored 
                           on portMonViewMonitorPort." 
                        ::= { portMonitorViewEntry 3 }


-- 1.4	The "rip" subsystem --

--	1.4.1

--	. showcfg
--	. set

--	The above two commands show/set the RIP configuration for the
--	indicated port(s). Since they operate on the port(s), a RIP
--	configuration table can be modeled that stores the per port
--	RIP parameters.

                alRipConfigTable OBJECT-TYPE
                        SYNTAX  SEQUENCE OF RipConfigEntry
                        ACCESS  not-accessible
                        STATUS  mandatory
                        DESCRIPTION
                                " Per port RIP configuration."

			::= { alrip 1 }

                ripConfigEntry OBJECT-TYPE
                        SYNTAX  RipConfigEntry
                        ACCESS  not-accessible
                        STATUS  mandatory
                        DESCRIPTION
                                " "
                        INDEX   { ripConfigPort }
                        ::= { alRipConfigTable 1 }
 
                RipConfigEntry ::= SEQUENCE {
                                        ripConfigPort
                                                INTEGER,
                                        ripConfigTalk
                                                INTEGER,
                                        ripConfigListen
                                                INTEGER,
					ripConfigPoison
						INTEGER,
					ripConfigRptStaticRt
						INTEGER,
					ripConfigRptDefaultRt
						INTEGER,
					ripConfigAccptDefaultRt
						INTEGER	
                }
 
 
                ripConfigPort OBJECT-TYPE
                        SYNTAX  INTEGER
                        ACCESS  read-write
                        STATUS  mandatory
                        DESCRIPTION
				"Port number for which the RIP parameters
			are to be set or viewed."

			::= { ripConfigEntry 1 }

                ripConfigTalk OBJECT-TYPE
                        SYNTAX  INTEGER 
-- CVG, LSI					{ yes (1), no (0) }
                        ACCESS  read-write 
                        STATUS  mandatory
                        DESCRIPTION
				"Controls whether the hub generates RIP
			packets on the port identified by the instance of 
			ripConfigPort."

                        ::= { ripConfigEntry 2 }


                ripConfigListen OBJECT-TYPE
                        SYNTAX  INTEGER 
-- CVG, LSI					{  yes (1), no (0) }
                        ACCESS  read-write 
                        STATUS  mandatory
                        DESCRIPTION
				"Controls whether the hub processes RIP
			packets received on the port identified by the 
			instance of ripConfigPort."

                        ::= { ripConfigEntry 3 }

                ripConfigPoison OBJECT-TYPE
                        SYNTAX  INTEGER 
-- CVG, LSI					{ yes(1), no (0) }
                        ACCESS  read-write 
                        STATUS  mandatory
                        DESCRIPTION
				"Controls what happens when a route goes down.
			If set to no(0), the hub simply stops reporting the
			route. If set to yes(1), the hub reports it one more
			time, but with a metric value of 16, which infinity
			as far as RIP is concerned. Thus other routers learn
			immediately that the route is down."

                        ::= { ripConfigEntry 4 }

                ripConfigRptStaticRt OBJECT-TYPE
                        SYNTAX  INTEGER 
-- CVG, LSI					{  yes (1), no (0) }
                        ACCESS  read-write 
                        STATUS  mandatory
                        DESCRIPTION
				"When RIP packets are generated on the port,
			controls whether the hub reports the static routes
			in its route table."

                        ::= { ripConfigEntry 5 }

                ripConfigRptDefaultRt OBJECT-TYPE
                        SYNTAX  INTEGER  
-- CVG, LSI                                       {    yes(1), no (0) }
                        ACCESS  read-write 
                        STATUS  mandatory
                        DESCRIPTION
				"When RIP packets are generated on the port,
			controls whether the hub reports the default routes,
			if any, in ints route table."

                        ::= { ripConfigEntry 6 }

                ripConfigAccptDefaultRt OBJECT-TYPE
                        SYNTAX  INTEGER  
-- CVG, LSI                                  { yes(1), no (0) }
                        ACCESS  read-write 
                        STATUS  mandatory
                        DESCRIPTION
				"When RIP packets are received on the port,
			controls whether the hub accepts(learns) a default
			route that is reported in a RIP packet."

                        ::= { ripConfigEntry 7 }

--	1.4.2  

--	. stats-clear

                alRipstatsClear OBJECT-TYPE
                        SYNTAX  INTEGER
                        ACCESS  read-write
                        STATUS  mandatory
                        DESCRIPTION
                                "When set, clears the RIP stats"
			
			::= { alrip 2 }

	
--	. stats

--	  There are two kinds of stats -- 

--	  . static - The stats that the user cannot clear.
--	  	     These are cleared only when the system
--		     resets. Corresponds to the "-t" option
--		     of the stats command.

--	  . dynamic - The stats that the user can reset 
--		     any time during when the system is up.
				

--	  .static stats --

	   	alRipStatPktsRcvd OBJECT-TYPE
			SYNTAX	  INTEGER
			ACCESS	  read-only
			STATUS	  mandatory
			DESCRIPTION
				"Packets Received."
		
			::= { alrip 3 }

                alRipStatPktsXmitted OBJECT-TYPE 
                        SYNTAX    INTEGER 
                        ACCESS    read-only 
                        STATUS    mandatory 
                        DESCRIPTION 
                                "Packets Sent."

			::= { alrip 4 }

                alRipStatReqsRcvd OBJECT-TYPE 
                        SYNTAX    INTEGER 
                        ACCESS    read-only 
                        STATUS    mandatory 
                        DESCRIPTION 
                                "Requests Received."

			::= { alrip 5 }

                alRipStatRespRcvd OBJECT-TYPE 
                        SYNTAX    INTEGER 
                        ACCESS    read-only 
                        STATUS    mandatory 
                        DESCRIPTION 
                                "Responses Received."

			::= { alrip 6 }

                alRipStatReqsXmitted OBJECT-TYPE 
                        SYNTAX    INTEGER 
                        ACCESS    read-only 
                        STATUS    mandatory 
                        DESCRIPTION 
                                "Requests Sent."

			::= { alrip 7 }

                alRipStatRespXmitted OBJECT-TYPE 
                        SYNTAX    INTEGER 
                        ACCESS    read-only 
                        STATUS    mandatory 
                        DESCRIPTION 
                                "Responses Sent."
			
			::= { alrip 8 }

                alRipStatRouteTimeOuts OBJECT-TYPE 
                        SYNTAX    INTEGER 
                        ACCESS    read-only 
                        STATUS    mandatory 
                        DESCRIPTION 
                                "Route Timeouts."

			::= { alrip 9 }

                alRipStatShortPkts OBJECT-TYPE 
                        SYNTAX    INTEGER 
                        ACCESS    read-only 
                        STATUS    mandatory 
                        DESCRIPTION 
                                "Short packets received."
		
			::= { alrip 10 }

                alRipStatBadVer OBJECT-TYPE 
                        SYNTAX    INTEGER 
                        ACCESS    read-only 
                        STATUS    mandatory 
                        DESCRIPTION 
                                "Bad version pkts received."
		
			::= { alrip 11 }

                alRipStatBadZeroes OBJECT-TYPE 
                        SYNTAX    INTEGER 
                        ACCESS    read-only 
                        STATUS    mandatory 
                        DESCRIPTION 
                                "Bad zeroes received."
		
			::= { alrip 12 }

                alRipStatBadSrcPort OBJECT-TYPE 
                        SYNTAX    INTEGER 
                        ACCESS    read-only 
                        STATUS    mandatory 
                        DESCRIPTION 
                                "Packets with bad Source port received."

			::= { alrip 13 }

                alRipStatBadSrcIp OBJECT-TYPE 
                        SYNTAX    INTEGER 
                        ACCESS    read-only 
                        STATUS    mandatory 
                        DESCRIPTION 
                                "Packets with bad source IP address received."

			::= { alrip 14 }

                alRipStatPktsSelf OBJECT-TYPE 
                        SYNTAX    INTEGER 
                        ACCESS    read-only 
                        STATUS    mandatory 
                        DESCRIPTION 
                                "Packets from self received."

			::= { alrip 15 }

                alRipStatPktsQueued OBJECT-TYPE 
                        SYNTAX    INTEGER 
                        ACCESS    read-only 
                        STATUS    mandatory 
                        DESCRIPTION 
                                "Packets queued."

			::= { alrip 16 }

                alRipStatFreeQueue OBJECT-TYPE 
                        SYNTAX    INTEGER 
                        ACCESS    read-only 
                        STATUS    mandatory 
                        DESCRIPTION 
                                "Free entries in the RIP processing queue."

			::= { alrip 17 }


--	. dynamic stats

                alRipDynPktsRcvd OBJECT-TYPE
                        SYNTAX    INTEGER
                        ACCESS    read-only
                        STATUS    mandatory
                        DESCRIPTION
                                "Packets Received."

			::= { alrip 18 }

                alRipDynPktsXmitted OBJECT-TYPE
                        SYNTAX    INTEGER
                        ACCESS    read-only
                        STATUS    mandatory
                        DESCRIPTION
                                "Packets Sent."

			::= { alrip 19 }

                alRipDynReqsRcvd OBJECT-TYPE
                        SYNTAX    INTEGER
                        ACCESS    read-only
                        STATUS    mandatory
                        DESCRIPTION
                                "Requests Received."

			::= { alrip 20 }
 
                alRipDynRespRcvd OBJECT-TYPE
                        SYNTAX    INTEGER
                        ACCESS    read-only
                        STATUS    mandatory
                        DESCRIPTION
                                "Responses Received."

			::= { alrip 21 }

                alRipDynReqsXmitted OBJECT-TYPE
                        SYNTAX    INTEGER
                        ACCESS    read-only
                        STATUS    mandatory
                        DESCRIPTION
                                "Requests Sent."

			::= { alrip 22 }
 
                alRipDynRespXmitted OBJECT-TYPE
                        SYNTAX    INTEGER
                        ACCESS    read-only
                        STATUS    mandatory
                        DESCRIPTION
                                "Responses Sent."

			::= { alrip 23 }
 
                alRipDynRouteTimeOuts OBJECT-TYPE
                        SYNTAX    INTEGER
                        ACCESS    read-only
                        STATUS    mandatory
                        DESCRIPTION
                                "Route Timeouts."

			::= { alrip 24 }
 
                alRipDynShortPkts OBJECT-TYPE
                        SYNTAX    INTEGER
                        ACCESS    read-only
                        STATUS    mandatory
                        DESCRIPTION
                                "Short packets received."

			::= { alrip 25 }

                alRipDynBadVer OBJECT-TYPE
                        SYNTAX    INTEGER
                        ACCESS    read-only
                        STATUS    mandatory
                        DESCRIPTION
                                "Bad version pkts received."

			::= { alrip 26 }

                alRipDynBadZeroes OBJECT-TYPE
                        SYNTAX    INTEGER
                        ACCESS    read-only
                        STATUS    mandatory
                        DESCRIPTION
                                "Bad zeroes received."

			::= { alrip 27 }


                alRipDynBadSrcPort OBJECT-TYPE
                        SYNTAX    INTEGER
                        ACCESS    read-only
                        STATUS    mandatory
                        DESCRIPTION
                                "Packets with bad Source port received."

			::= { alrip 28 }
 
                alRipDynBadSrcIp OBJECT-TYPE
                        SYNTAX    INTEGER
                        ACCESS    read-only
                        STATUS    mandatory
                        DESCRIPTION
                                "Packets with bad source IP address received."

			::= { alrip 29 }

                alRipDynPktsSelf OBJECT-TYPE
                        SYNTAX    INTEGER
                        ACCESS    read-only
                        STATUS    mandatory
                        DESCRIPTION
                                "Packets from self received."

			::= { alrip 30 }

                alRipDynPktsQueued OBJECT-TYPE
                        SYNTAX    INTEGER
                        ACCESS    read-only
                        STATUS    mandatory
                        DESCRIPTION
                                "Packets queued."

			::= { alrip 31 }

                alRipDynFreeQueue OBJECT-TYPE
                        SYNTAX    INTEGER
                        ACCESS    read-only
                        STATUS    mandatory
                        DESCRIPTION
                                "Free entries in the RIP processing queue."
			
			::= { alrip 32 }



--	1.4.3

--	. rip-accept-filter

--	  Modeled as a table with filter number as the index.

                alRipAccptFilTable OBJECT-TYPE
                        SYNTAX  SEQUENCE OF RipAccptFilEntry
                        ACCESS  not-accessible
                        STATUS  mandatory
                        DESCRIPTION
                                "RIP Accept filter table" 

			::= { alrip 33 }

                ripAccptFilEntry OBJECT-TYPE
                        SYNTAX  RipAccptFilEntry
                        ACCESS  not-accessible
                        STATUS  mandatory
                        DESCRIPTION
                                "RIP Accept filter entry "
                        INDEX   { ripAccptFilNumber }
                        ::= { alRipAccptFilTable 1 }

                RipAccptFilEntry ::= SEQUENCE {
                                        ripAccptFilNumber
                                                INTEGER,
                                        ripAccptFilAddr
                                                IpAddress,
                                        ripAccptFilMask
                                                IpAddress,
                                        ripAccptFilPort
                                                INTEGER
                }

	 
                ripAccptFilNumber OBJECT-TYPE
                        SYNTAX  INTEGER
                        ACCESS  read-write
                        STATUS  mandatory
                        DESCRIPTION
                                "Filter Number; Range 1-64"

                        ::= { ripAccptFilEntry 1 }


                ripAccptFilAddr OBJECT-TYPE 
                        SYNTAX  IpAddress 
                        ACCESS  read-write 
                        STATUS  mandatory 
                        DESCRIPTION 
                                "Valid network or subnet address" 
 
                        ::= { ripAccptFilEntry 2 }

                ripAccptFilMask OBJECT-TYPE 
                        SYNTAX  IpAddress 
                        ACCESS  read-write 
                        STATUS  mandatory 
                        DESCRIPTION 
                                "Mask" 
 
                        ::= { ripAccptFilEntry 3 }

                ripAccptFilPort OBJECT-TYPE 
                        SYNTAX  INTEGER 
                        ACCESS  read-write 
                        STATUS  mandatory 
                        DESCRIPTION 
                                "Port number on which network should be 
				 accepted or not. Range 1-14. 
				 CVG This range will change for PH2??" 
 
                        ::= { ripAccptFilEntry 4 }

--	1.4.4

--	. rip-report-filter

                alRipReportFilTable OBJECT-TYPE
                        SYNTAX  SEQUENCE OF RipReportFilEntry
                        ACCESS  not-accessible
                        STATUS  mandatory
                        DESCRIPTION
                                "RIP Report filter table"

			::= { alrip 34 }
 
                ripReportFilEntry OBJECT-TYPE
                        SYNTAX  RipReportFilEntry
                        ACCESS  not-accessible
                        STATUS  mandatory
                        DESCRIPTION
                                "RIP Report filter entry "
                        INDEX   { ripReportFilNumber }
                        ::= { alRipReportFilTable 1 }
 
                RipReportFilEntry ::= SEQUENCE {
                                        ripReportFilNumber
                                                INTEGER,
                                        ripReportFilAddr
                                                IpAddress,
                                        ripReportFilMask
                                                IpAddress,
                                        ripReportFilPort
                                                INTEGER
                }

                ripReportFilNumber OBJECT-TYPE
                        SYNTAX  INTEGER
                        ACCESS  read-write
                        STATUS  mandatory
                        DESCRIPTION
                                "Filter Number; Range 1-64"
 
                        ::= { ripReportFilEntry 1 }
 
 
                ripReportFilAddr OBJECT-TYPE
                        SYNTAX  IpAddress
                        ACCESS  read-write
                        STATUS  mandatory
                        DESCRIPTION
                                "Valid network or subnet address"
 
                        ::= { ripReportFilEntry 2 }
 
                ripReportFilMask OBJECT-TYPE
                        SYNTAX  IpAddress
                        ACCESS  read-write
                        STATUS  mandatory
                        DESCRIPTION
                                "Mask"
 
                        ::= { ripReportFilEntry 3 }

                ripReportFilPort OBJECT-TYPE
                        SYNTAX  INTEGER
                        ACCESS  read-write
                        STATUS  mandatory
                        DESCRIPTION
                                "Port number on which network should be
                                 reported or not. Port number range 1-14
				 CVG This range will probably change for
				 PH2??."
 
                        ::= { ripReportFilEntry 4 }



-- 1.5	The "tcpstack" subsystem  --

--   	1.5.1 

--     	  1.5.1.1  showcfg and set

--		PowerHub UI                  	MIB- II

--		Round Trip Algorithm         	tcpRtoAlgorithm 
--		Min Rexmit Interval          	tcpRtoMin
--		Max Rexmit Interval		tcpRtoMax
--		Max Connections Allowed		tcpMaxConn
		
--		The following parameters in the showcfg and set commands
--		do not map to any MIB-II variables.

--		connection-idle-time
--		keep-alive-interval
--		Time to disconnect on idle conn

                alTcpConnIdleTime OBJECT-TYPE
                        SYNTAX    INTEGER
                        ACCESS    read-write
                        STATUS    mandatory
                        DESCRIPTION
                                "Time in minutes before sending keep-alives.
			The range is 5 to 30 minutes."

			::= { altcp 1 }


                alTcpKeepAliveInt OBJECT-TYPE 
                        SYNTAX    INTEGER 
                        ACCESS    read-write 
                        STATUS    mandatory 
                        DESCRIPTION 
                                "Time interval in seconds between two 
			successive keep-alive sends. The range is 30 to 240
			seconds."

			::= { altcp 2 }


                alTcpDisconnectInt OBJECT-TYPE  
                        SYNTAX    INTEGER  
                        ACCESS    read-only  
                        STATUS    mandatory  
                        DESCRIPTION  
                                "Time interval in seconds, before an idle
			connection is dropped. This equals to the sum of
			alTcpConnIdleTime plus eight times the 
			alTcpKeepAliveInt interval."
 
                        ::= { altcp 3 }



--	  1.5.1.2  stats

--		PowerHub UI			MIB-II
--		------------------------------------------------------

--		Active Opens			tcpActiveOpens
--		Passive Opens			tcpPassiveOpens
--		Failed Conn Attempts		tcpAttemptFails
--		Resets In Estb State		tcpEstabResets
--		Current Open Conns		tcpCurrEstab
--		Segments Received		tcpInSegs
--		Segments Sent			tcpOutSegs
--		Rexmitted segments		tcpRetransSegs
--		Segments Rcvd With Err		tcpInErrs
--		Resets Sent			tcpOutRsts

--		The stat that the PH supports but which does not match
--		any MIB-II variable is 

--		Short Segments Rcvd --

                alTcpShortSegRcvd OBJECT-TYPE
                        SYNTAX    INTEGER
                        ACCESS    read-only
                        STATUS    mandatory
                        DESCRIPTION
                                "Number of short segments received."
 
                        ::= { altcp 4 }
		
--	  1.5.1.3  stats-clear

		alTcpStatsClear OBJECT-TYPE
                        SYNTAX    INTEGER
                        ACCESS    read-write
                        STATUS    mandatory
                        DESCRIPTION
                                "When set to 1, clears the TCP stats."

                        ::= { altcp 5 }


--	1.5.2

--	  1.5.2.1
-- 		. tcp-table

          	alTcpConnTable OBJECT-TYPE
              		SYNTAX  SEQUENCE OF AlTcpConnEntry
              		ACCESS  not-accessible
              		STATUS  mandatory
              		DESCRIPTION
                      		"A table containing TCP connection-specific
                      	information."

              		::= { altcp 6 }

          	alTcpConnEntry OBJECT-TYPE
              		SYNTAX  AlTcpConnEntry
              		ACCESS  not-accessible
              		STATUS  mandatory
              		DESCRIPTION
                      		"Information about a particular current TCP
                      	connection.  An object of this type is transient,
                      	in that it ceases to exist when (or soon after)
                      	the connection makes the transition to the CLOSED
                      	state."
              		INDEX   { alTcpConnId }

              		::= { alTcpConnTable 1 }

          	AlTcpConnEntry ::=
              		SEQUENCE {
		  			alTcpConnId
		      				INTEGER,
                  			alTcpConnState
                      				INTEGER,
                  			alTcpConnLocalAddress
                      				IpAddress,
                  			alTcpConnLocalPort
                      				INTEGER,
                  			alTcpConnRemAddress
                      				IpAddress,
                  			alTcpConnRemPort
                      				INTEGER 
              		}

                alTcpConnId 	OBJECT-TYPE
                        SYNTAX  INTEGER
                        ACCESS  read-only
                        STATUS  mandatory
                        DESCRIPTION
                                "The connection Identifier by which a 
			connection is addressed." 

                        ::= { alTcpConnEntry 1 }

          	alTcpConnState OBJECT-TYPE
              		SYNTAX  INTEGER {
                          		closed(1),
                          		listen(2),
                          		synSent(3),
                          		synReceived(4),
                          		established(5),
                          		finWait1(6),
                          		finWait2(7),
                          		closeWait(8),
                          		lastAck(9),
                          		closing(10),
                          		timeWait(11),
                          		deleteTCB(12)
                      		}

              		ACCESS  read-write
              		STATUS  mandatory
              		DESCRIPTION
                      		"The state of this TCP connection.
                      	The only value which may be set by a management
			station is deleteTCB(12).  Accordingly, it is
                      	appropriate for an agent to return a `badValue'
                      	response if a management station attempts to set
                      	this object to any other value.
 
                      	If a management station sets this object to the
                      	value deleteTCB(12), then this has the effect of
                      	deleting the TCB (as defined in RFC 793) of the
                      	corresponding connection on the managed node,
                      	resulting in immediate termination of the
                      	connection."

			::= { alTcpConnEntry 2 }

          	alTcpConnLocalAddress OBJECT-TYPE
              		SYNTAX  IpAddress
              		ACCESS  read-only
              		STATUS  mandatory
              		DESCRIPTION
                      		"The local IP address for this TCP connection. 
                      	In the case of a connection in the listen state which
                      	is willing to accept connections for any IP
                      	interface associated with the node, the value
                      	0.0.0.0 is used."

              		::= { alTcpConnEntry 3 }

          	alTcpConnLocalPort OBJECT-TYPE
              		SYNTAX  INTEGER 
              		ACCESS  read-only
              		STATUS  mandatory
              		DESCRIPTION
                      		"The local port number for this TCP connection."

              		::= { alTcpConnEntry 4 }
 
          	alTcpConnRemAddress OBJECT-TYPE
              		SYNTAX  IpAddress
              		ACCESS  read-only
              		STATUS  mandatory
              		DESCRIPTION
                      		"The remote IP address for this TCP connection."

              		::= { alTcpConnEntry 5 }

          	alTcpConnRemPort OBJECT-TYPE
              		SYNTAX  INTEGER 
              		ACCESS  read-only
              		STATUS  mandatory
              		DESCRIPTION
                      		"The remote port number for this TCP 
   			connection."

              		::= { alTcpConnEntry 6 }

--	  1.5.2.2
--		. kill-connection

--		  This command will be executed by sending a deleteTCB(12)
--		  to the connection indexed by the alTcpConnId. This will
--		  delete the connection.

--	1.5.3
	
--		. tcp-filter ( to add/change/show the tcp-filter )

                alTcpFilTable OBJECT-TYPE
                        SYNTAX  SEQUENCE OF TcpFilEntry
                        ACCESS  not-accessible
                        STATUS  mandatory
                        DESCRIPTION
                                "TCP filter table"

			::= { altcp 7 }

                tcpFilEntry OBJECT-TYPE
                        SYNTAX  TcpFilEntry
                        ACCESS  not-accessible
                        STATUS  mandatory
                        DESCRIPTION
                                "TCP filter entry "
                        INDEX   { tcpFilNumber }
                        ::= { alTcpFilTable 1 }
 
                TcpFilEntry ::= SEQUENCE {
                                        tcpFilNumber
                                                INTEGER,
                                        tcpFilSrcAddr
                                                IpAddress,
                                        tcpFilSrcMask
                                                IpAddress,
					tcpFilProtocol
						INTEGER,
                                        tcpFilDstPort
                                                INTEGER
                }

                tcpFilNumber    OBJECT-TYPE
                        SYNTAX  INTEGER
                        ACCESS  read-write
                        STATUS  mandatory
                        DESCRIPTION
                                "Filter Number; Range 1-32"
 
                        ::= { tcpFilEntry 1 }

                tcpFilSrcAddr OBJECT-TYPE
                        SYNTAX  IpAddress
                        ACCESS  read-write
                        STATUS  mandatory
                        DESCRIPTION
                                "Source address"
 
                        ::= { tcpFilEntry 2 }

                tcpFilSrcMask OBJECT-TYPE
                        SYNTAX  IpAddress
                        ACCESS  read-write
                        STATUS  mandatory
                        DESCRIPTION
                                "Mask"
 
                        ::= { tcpFilEntry 3 }

                tcpFilProtocol OBJECT-TYPE
                        SYNTAX  INTEGER
                        ACCESS  read-write
                        STATUS  mandatory
                        DESCRIPTION
                                "tcp(1) or udp(2)"
 
                        ::= { tcpFilEntry 4 }

                tcpFilDstPort OBJECT-TYPE
                        SYNTAX  INTEGER
                        ACCESS  read-write
                        STATUS  mandatory
                        DESCRIPTION
                                "smtp(1000), telnet(2000),
			ftp(3000) or valid port Number"
 
                        ::= { tcpFilEntry 5 }

--	1.5.4

--		. set-ctrlchar-cur
--		. show-ctrlchar-cur
--		. set-ctrlchar-def
--		. show-ctrlchar-def
		

-- 1.6	The "ip" subsystem --

-- 1.6.1	The arp related commands --

-- 1.6.1.1 add-arp/del-arp/arp-table --

--	Map to the ipNetToMediaTable of the IP group in the MIB-II.
	
-- 1.6.1.4 arp-tableclear

                alArpTableClear OBJECT-TYPE
                        SYNTAX  INTEGER
                        ACCESS  read-write
                        STATUS  mandatory
                        DESCRIPTION
                                "When set, clears the ARP table."

			::= { alip 1 }

	
-- 1.6.1.5 set-arpage

               	 alArpAge 	OBJECT-TYPE
                        SYNTAX  INTEGER
                        ACCESS  read-write
                        STATUS  mandatory
                        DESCRIPTION
                                "Timeout in minutes for aging ARP entries;
			when set to zero, set-arpage is turned off."

			::= { alip 2 }

-- 1.6.1.6 stats arp

--	. static stats - equivalent to "stats arp -t"

                alArpStatReqsRcvd OBJECT-TYPE
                        SYNTAX    INTEGER
                        ACCESS    read-only
                        STATUS    mandatory
                        DESCRIPTION
                                "Requests Received."

			::= { alip 3 }

                alArpStatRepliesRcvd OBJECT-TYPE 
                        SYNTAX    INTEGER 
                        ACCESS    read-only 
                        STATUS    mandatory 
                        DESCRIPTION 
                                "Replies Received."

			::= { alip 4 }

                alArpStatInvalidOpcodes OBJECT-TYPE 
                        SYNTAX    INTEGER 
                        ACCESS    read-only 
                        STATUS    mandatory 
                        DESCRIPTION 
                                "Invalid Opcodes Received."

			::= { alip 5 }

                alArpStatRequestsSent OBJECT-TYPE 
                        SYNTAX    INTEGER 
                        ACCESS    read-only 
                        STATUS    mandatory 
                        DESCRIPTION 
                                "Requests Sent."

			::= { alip 6 }

                alArpStatRepliesSent OBJECT-TYPE 
                        SYNTAX    INTEGER 
                        ACCESS    read-only 
                        STATUS    mandatory 
                        DESCRIPTION 
                                "Replies Sent."
			
			::= { alip 7 }


--	. dynamic stats - equivalent to "stats arp"

		alArpDynReqsRcvd OBJECT-TYPE
                        SYNTAX    INTEGER
                        ACCESS    read-only
                        STATUS    mandatory
                        DESCRIPTION
                                "Requests Received."
	
			::= { alip 8 }
 
                alArpDynRepliesRcvd OBJECT-TYPE
                        SYNTAX    INTEGER
                        ACCESS    read-only
                        STATUS    mandatory
                        DESCRIPTION
                                "Replies Received."
 
			::= { alip 9 }

                alArpDynInvalidOpcodes OBJECT-TYPE
                        SYNTAX    INTEGER
                        ACCESS    read-only
                        STATUS    mandatory
                        DESCRIPTION
                                "Invalid Opcodes Received."

			::= { alip 10 }    
 
                alArpDynRequestsSent OBJECT-TYPE
                        SYNTAX    INTEGER
                        ACCESS    read-only
                        STATUS    mandatory
                        DESCRIPTION
                                "Requests Sent."

			::= { alip 11 }
 
                alArpDynRepliesSent OBJECT-TYPE
                        SYNTAX    INTEGER
                        ACCESS    read-only
                        STATUS    mandatory
                        DESCRIPTION
				"Replies Sent."

			::= { alip 12 }


-- 1.6.1.7 proxy-arp

                alArpProxyTable OBJECT-TYPE
                        SYNTAX  SEQUENCE OF ArpProxyEntry
                        ACCESS  not-accessible
                        STATUS  mandatory
                        DESCRIPTION
                                " Per port proxy arp enable/disable "

			::= { alip 13 }
 
                arpProxyEntry OBJECT-TYPE
                        SYNTAX  ArpProxyEntry
                        ACCESS  not-accessible
                        STATUS  mandatory
                        DESCRIPTION
                                " "
                        INDEX   { arpProxyPort }
                        ::= { alArpProxyTable 1 }
 
                ArpProxyEntry ::= SEQUENCE {
                                        arpProxyPort
                                                INTEGER,
                                        arpProxyEnable
                                                INTEGER
				}


                arpProxyPort OBJECT-TYPE
                        SYNTAX  INTEGER
                        ACCESS  read-only
                        STATUS  mandatory
                        DESCRIPTION
                                "Port Number "
                        ::= { arpProxyEntry 1 }
 
                arpProxyEnable OBJECT-TYPE
                        SYNTAX  INTEGER
                        ACCESS  read-write
                        STATUS  mandatory
                        DESCRIPTION
                                "If set to Enable(1), enables proxy arp
			for arp requests received on the port identified by 
			the instance of arpProxyPort. If set to Disable(0), it
			disables the proxy arp for arp requests received on
			the ports identified by the instance of arpProxyPort."

                        ::= { arpProxyEntry 2 }


-- 1.6.2	IP Filtering

-- 1.6.2.1 IP Filter Templates --
	
-- 	. ip-fil-template add
-- 	. ip-fil-template chng
-- 	. ip-fil-template del
-- 	. ip-fil-template show

-- 	This will be modeled as a table indexed by the template number.

                alIpTemplateTable OBJECT-TYPE
                        SYNTAX  SEQUENCE OF IpTemplateEntry
                        ACCESS  not-accessible
                        STATUS  mandatory
                        DESCRIPTION
                                " Per template information"

			::= { alip 14 }

                ipTemplateEntry OBJECT-TYPE
                        SYNTAX  IpTemplateEntry
                        ACCESS  not-accessible
                        STATUS  mandatory
                        DESCRIPTION
                                " "
                        INDEX   { ipTemplateNumber }
                        ::= { alIpTemplateTable 1 }

                IpTemplateEntry ::= SEQUENCE {
                                        ipTemplateNumber
                                                INTEGER,
					ipTemplateDelete
						INTEGER,
                                        ipTemplateAction
						INTEGER,
					ipTemplateSrcAddr
						IpAddress,
                                        ipTemplateSrcMask
                                                IpAddress,
					ipTemplateDstAddr
						IpAddress, 
                                        ipTemplateDstMask
                                                IpAddress,
					ipTemplateProtocol
						INTEGER,
					ipTemplateOperator
						DisplayString,
					ipTemplateDstPort
						INTEGER
				}
					

		ipTemplateNumber OBJECT-TYPE
			SYNTAX	INTEGER
			ACCESS	read-write
			STATUS	mandatory
			DESCRIPTION	
				"The number of the template with which it
			is identified."

			::= { ipTemplateEntry 1 }
			
                ipTemplateDelete OBJECT-TYPE
                        SYNTAX  INTEGER
                        ACCESS  read-write
                        STATUS  mandatory
                        DESCRIPTION
                                "When set to Delete(1), this entry is
			deleted."

                        ::= { ipTemplateEntry 2 }

                ipTemplateAction OBJECT-TYPE
                        SYNTAX  INTEGER { 
						forward(1),
						block(2)
					}
                        ACCESS  read-write
                        STATUS  mandatory
                        DESCRIPTION
                                "Whether the packet being filtered should 
			be forwarded or blocked"
 
                        ::= { ipTemplateEntry 3 }

                ipTemplateSrcAddr OBJECT-TYPE
                        SYNTAX  IpAddress
                        ACCESS  read-write
                        STATUS  mandatory
                        DESCRIPTION
                                "The portion of the packet's source address
			specified by ipTemplateSrcMask is matched with 
			this address."
 
                        ::= { ipTemplateEntry 4 }

                ipTemplateSrcMask OBJECT-TYPE
                        SYNTAX  IpAddress
                        ACCESS  read-write
                        STATUS  mandatory
                        DESCRIPTION
                                "Source Mask. The portion specified by 
			this mask is matched with source address."
 
                        ::= { ipTemplateEntry 5 }

                ipTemplateDstAddr OBJECT-TYPE
                        SYNTAX  IpAddress
                        ACCESS  read-write
                        STATUS  mandatory
                        DESCRIPTION
                                "The portion of the packet's destination 
                        address specified by ipTemplateDstMask is matched 
                        with this address." 

                        ::= { ipTemplateEntry 6 }

                ipTemplateDstMask OBJECT-TYPE
                        SYNTAX  IpAddress
                        ACCESS  read-write
                        STATUS  mandatory
                        DESCRIPTION
                                "Destination mask. The portion specified by
                        this mask is matched with destination address."
 
                        ::= { ipTemplateEntry 7 }

                ipTemplateProtocol OBJECT-TYPE
                        SYNTAX  INTEGER
                        ACCESS  read-write
                        STATUS  mandatory
                        DESCRIPTION
				"Determines the type of packets that need 
			to be filtered"
 
                        ::= { ipTemplateEntry 8 }

                ipTemplateOperator OBJECT-TYPE
                        SYNTAX  DisplayString
                        ACCESS  read-write
                        STATUS  mandatory
                        DESCRIPTION
                                "Allowed only if the protocol field is tcp
			or udp."
 
                        ::= { ipTemplateEntry 9 }

                ipTemplateDstPort OBJECT-TYPE
                        SYNTAX  INTEGER
                        ACCESS  read-write
                        STATUS  mandatory
                        DESCRIPTION
                                "This is expressed as either a well-known 
			protocol name or a well-known tcp or udp port
			number"

                        ::= { ipTemplateEntry 10 }


-- 1.6.2.2	IP Filter Rules

--	. ip-fil-rule add
--	. ip-fil-rule del
--	. ip-fil-rule chng
--	. ip-fil-rule show


                alIpRuleTable OBJECT-TYPE
                        SYNTAX  SEQUENCE OF IpRuleEntry
                        ACCESS  not-accessible
                        STATUS  mandatory
                        DESCRIPTION
                                " Per template information"

			::= { alip 15 }

                ipRuleEntry OBJECT-TYPE
                        SYNTAX  IpRuleEntry
                        ACCESS  not-accessible
                        STATUS  mandatory
                        DESCRIPTION
                                " "
                        INDEX   { ipRuleNumber }
                        ::= { alIpRuleTable 1 }
 
                IpRuleEntry ::= SEQUENCE {
                                        ipRuleNumber
                                                INTEGER,
					ipRuleDelete
						INTEGER,
                                        ipRuleTemplates
                                                DisplayString
				}


                ipRuleNumber OBJECT-TYPE
                        SYNTAX  INTEGER
                        ACCESS  read-write
                        STATUS  mandatory
                        DESCRIPTION
                                "The number of the rule with which it is
                        identified."
 
                        ::= { ipRuleEntry 1 }

                ipRuleDelete OBJECT-TYPE
                        SYNTAX  INTEGER
                        ACCESS  read-write
                        STATUS  mandatory
                        DESCRIPTION
                                "If set to 1 the entry is deleted."

                        ::= { ipRuleEntry 2 }

                ipRuleTemplates OBJECT-TYPE
                        SYNTAX  DisplayString
                        ACCESS  read-write
                        STATUS  mandatory
                        DESCRIPTION
                                "The templates associated with the rule
			identified by the instance of ipRuleNumber." 
 
                        ::= { ipRuleEntry 3 }



-- 1.6.2.3	IP Filter Access Control 

--	. ip-fil-acs-ctrl add
--	. ip-fil-acs-ctrl del
--	. ip-fil-acs-ctrl show


                ipAcsCtrlTable OBJECT-TYPE
                        SYNTAX  SEQUENCE OF IpAcsCtrlEntry
                        ACCESS  not-accessible
                        STATUS  mandatory
                        DESCRIPTION
                                "Per port IP access control filters "

			::= { alip 16 }
 
                ipAcsCtrlEntry OBJECT-TYPE
                        SYNTAX  IpAcsCtrlEntry
                        ACCESS  not-accessible
                        STATUS  mandatory
                        DESCRIPTION
                                " "
                        INDEX   { ipAcsCtrlPort }
                        ::= { ipAcsCtrlTable 1 }
 
                IpAcsCtrlEntry ::= SEQUENCE {
                                        ipAcsCtrlPort
                                                INTEGER,
                                        ipAcsCtrlDelete
                                                INTEGER,
                                        ipAcsCtrlSrcRule
                                                INTEGER,
                                        ipAcsCtrlDstRule
                                                INTEGER
                }

                ipAcsCtrlPort   OBJECT-TYPE
                        SYNTAX  INTEGER
                        ACCESS  read-write
                        STATUS  mandatory
                        DESCRIPTION
                                "Port number of the port for which the
			source and destination access filter apply. "

                        ::= { ipAcsCtrlEntry 1 }

                ipAcsCtrlDelete   OBJECT-TYPE
                        SYNTAX  INTEGER
                        ACCESS  read-write
                        STATUS  mandatory
                        DESCRIPTION
                                "If set to 1, the entry is deleted."
 
                        ::= { ipAcsCtrlEntry 2 }

 
                ipAcsCtrlSrcRule OBJECT-TYPE
                        SYNTAX  INTEGER
                        ACCESS  read-write
                        STATUS  mandatory
                        DESCRIPTION
                                "Source IP access filter rule "
                        ::= { ipAcsCtrlEntry 3 }

                ipAcsCtrlDstRule OBJECT-TYPE
                        SYNTAX  INTEGER
                        ACCESS  read-write                   
                        STATUS  mandatory
                        DESCRIPTION                         
                                "Destination IP access filter rule "
                        ::= { ipAcsCtrlEntry 4 }


-- 1.6.2.4	IP Filter Statistics
	
--	. ip-fil-stats	show [-t]

                ipFilStatStatsTable OBJECT-TYPE
                        SYNTAX  SEQUENCE OF IpFilStatStatsEntry
                        ACCESS  not-accessible
                        STATUS  mandatory
                        DESCRIPTION
                                " Per template static statistics -- stats
			from the beginning of the last system reboot."

			::= { alip 17 }
 
                ipFilStatStatsEntry OBJECT-TYPE
                        SYNTAX  IpFilStatStatsEntry
                        ACCESS  not-accessible
                        STATUS  mandatory
                        DESCRIPTION
                                " "
                        INDEX   { ipFilStatStatsTemplate }
                        ::= { ipFilStatStatsTable 1 }
 
                IpFilStatStatsEntry ::= SEQUENCE {
                                        ipFilStatStatsTemplate
                                                INTEGER,
                                        ipFilStatStatsInPkts
						INTEGER,
					ipFilStatStatsInBytes
						INTEGER,
					ipFilStatStatsOutPkts
						INTEGER,	
					ipFilStatStatsOutBytes
						INTEGER
					}

		ipFilStatStatsTemplate	OBJECT-TYPE
				SYNTAX	INTEGER
				ACCESS	read-only
				STATUS	mandatory
				DESCRIPTION
					"The template number for which 
				the stats are displayed"
				
				::= { ipFilStatStatsEntry 1 }

                ipFilStatStatsInPkts  OBJECT-TYPE
                                SYNTAX  INTEGER
                                ACCESS  read-only
                                STATUS  mandatory
                                DESCRIPTION
                                        "The number of packets that matched 
				the template identified by the instance of
				ipFilStatStatsTemplate. The template has to 
				be a Source template."

                                ::= { ipFilStatStatsEntry 2 }

                ipFilStatStatsInBytes  OBJECT-TYPE
                                SYNTAX  INTEGER
                                ACCESS  read-only
                                STATUS  mandatory
                                DESCRIPTION
                                        "The number of bytes that matched
                                the template identified by the instance of
                                ipFilStatStatsTemplate. The template has to
                                be a Source template."

                                ::= { ipFilStatStatsEntry 3 }

                ipFilStatStatsOutPkts  OBJECT-TYPE
                                SYNTAX  INTEGER
                                ACCESS  read-only
                                STATUS  mandatory
                                DESCRIPTION
                                        "The number of packets that matched
                                the template identified by the instance of
                                ipFilStatStatsTemplate. The template has to
                                be a Destination template."


                                ::= { ipFilStatStatsEntry 4 }

                ipFilStatStatsOutBytes  OBJECT-TYPE
                                SYNTAX  INTEGER
                                ACCESS  read-only
                                STATUS  mandatory
                                DESCRIPTION
                                        "The number of bytes that matched 
                                the template identified by the instance of 
                                ipFilStatStatsTemplate. The template has to 
                                be a Destination template." 

                                ::= { ipFilStatStatsEntry 5 }

--	. dynamic stats - stats from the last clear
--	. ip-fil-stats	clear

                ipFilDynStatsTable OBJECT-TYPE
                        SYNTAX  SEQUENCE OF IpFilDynStatsEntry
                        ACCESS  not-accessible
                        STATUS  mandatory
                        DESCRIPTION
                                " Per template dynamic statistics -- stats
                        from the beginning of the last clear." 

			::= { alip 18 }

                ipFilDynStatsEntry OBJECT-TYPE
                        SYNTAX  IpFilDynStatsEntry
                        ACCESS  not-accessible
                        STATUS  mandatory
                        DESCRIPTION
                                " "
                        INDEX   { ipFilDynStatsTemplate }
                        ::= { ipFilDynStatsTable 1 }

                IpFilDynStatsEntry ::= SEQUENCE {
                                        ipFilDynStatsTemplate
                                                INTEGER,
                                        ipFilDynStatsInPkts
                                                INTEGER,
                                        ipFilDynStatsInBytes
                                                INTEGER,
                                        ipFilDynStatsOutPkts
                                                INTEGER,
                                        ipFilDynStatsOutBytes
                                                INTEGER,
					ipFilDynStatsClear
						INTEGER
                                        }

                ipFilDynStatsTemplate  OBJECT-TYPE
                                SYNTAX  INTEGER
                                ACCESS  read-only
                                STATUS  mandatory
                                DESCRIPTION
                                        "The template number for which
                                the stats are displayed"
                                
                                ::= { ipFilDynStatsEntry 1 }
 
                ipFilDynStatsInPkts  OBJECT-TYPE
                                SYNTAX  INTEGER
                                ACCESS  read-only
                                STATUS  mandatory
                                DESCRIPTION
                                        "The number of packets that matched
                                the template identified by the instance of
                                ipFilDynStatsTemplate. The template has to
                                be a Source template."

				::= { ipFilDynStatsEntry 2 }

                ipFilDynStatsInBytes  OBJECT-TYPE
                                SYNTAX  INTEGER
                                ACCESS  read-only
                                STATUS  mandatory
                                DESCRIPTION
                                        "The number of bytes that matched
                                the template identified by the instance of
                                ipFilDynStatsTemplate. The template has to
                                be a Source template."
 
                                ::= { ipFilDynStatsEntry 3 }

                ipFilDynStatsOutPkts  OBJECT-TYPE
                                SYNTAX  INTEGER
                                ACCESS  read-only
                                STATUS  mandatory
                                DESCRIPTION
                                        "The number of packets that matched
                                the template identified by the instance of
                                ipFilDynStatsTemplate. The template has to
                                be a Destination template."
 
                                ::= { ipFilDynStatsEntry 4 }

                ipFilDynStatsOutBytes  OBJECT-TYPE
                                SYNTAX  INTEGER
                                ACCESS  read-only
                                STATUS  mandatory
                                DESCRIPTION
                                        "The number of bytes that matched
                                the template identified by the instance of
                                ipFilDynStatsTemplate. The template has to
                                be a Destination template."
 
                                ::= { ipFilDynStatsEntry 5 }

                ipFilDynStatsClear  OBJECT-TYPE
                                SYNTAX  INTEGER
                                ACCESS  read-write
                                STATUS  mandatory
                                DESCRIPTION
					"Setting the value of 1, it will 
				clear all the stats for the template
				identified by the instance of 
				ipFilDynStatsTemplate."

                                ::= { ipFilDynStatsEntry 6 }


-- 1.6.3	IP port Configuration

-- 	. add-interface
--	. del-interface
--	. interface-table

          	alIpInterfaceTable OBJECT-TYPE
              		SYNTAX  SEQUENCE OF AlIpInterfaceEntry
              		ACCESS  not-accessible
              		STATUS  mandatory
              		DESCRIPTION
				"Interface table corresponding to the command
				 - interface-table."

			::= { alip 19 }
 
          	alIpInterfaceEntry OBJECT-TYPE
              		SYNTAX  AlIpInterfaceEntry
              		ACCESS  not-accessible
              		STATUS  mandatory
              		DESCRIPTION
				" "
              		INDEX   { ipInterfaceNumber, ipInterfaceAddress }

              		::= { alIpInterfaceTable 1 }

          	AlIpInterfaceEntry ::=
              			SEQUENCE {
                  				ipInterfaceNumber
                      					INTEGER,
                  				ipInterfaceAddress
                      					IpAddress,
                  				ipInterfaceSubnetMask
                      					IpAddress,
                  				ipInterfaceMtu
                      					INTEGER,
						ipInterfaceBroadCast
							INTEGER,
						ipInterfaceState
							INTEGER,
						ipInterfaceCost
							INTEGER,
						ipInterfacePktsIn
							INTEGER,
						ipInterfaceOctetsIn
							INTEGER,
						ipInterfacePktsOut
							INTEGER,
						ipInterfaceOctetsOut
							INTEGER
						
              			}
 
          	ipInterfaceNumber OBJECT-TYPE
              		SYNTAX  INTEGER
              		ACCESS  read-write
              		STATUS  mandatory
              		DESCRIPTION
                      		" "
              		::= { alIpInterfaceEntry 1 }

	
                ipInterfaceAddress OBJECT-TYPE
                        SYNTAX  IpAddress
                        ACCESS  read-write
                        STATUS  mandatory
                        DESCRIPTION
                                " "
                        ::= { alIpInterfaceEntry 2 }

                ipInterfaceSubnetMask OBJECT-TYPE
                        SYNTAX  IpAddress
                        ACCESS  read-write
                        STATUS  mandatory
                        DESCRIPTION
                                " "
                        ::= { alIpInterfaceEntry 3 }

                ipInterfaceMtu OBJECT-TYPE
                        SYNTAX  INTEGER
                        ACCESS  read-write
                        STATUS  mandatory
                        DESCRIPTION
                                " "
                        ::= { alIpInterfaceEntry 4 }

                ipInterfaceBroadCast OBJECT-TYPE
                        SYNTAX  INTEGER
                        ACCESS  read-write
                        STATUS  mandatory
                        DESCRIPTION
                                " "
                        ::= { alIpInterfaceEntry 5 }

                ipInterfaceState OBJECT-TYPE
                        SYNTAX  INTEGER
                        ACCESS  read-write
                        STATUS  mandatory
                        DESCRIPTION
                                " "
                        ::= { alIpInterfaceEntry 6 }

                ipInterfaceCost OBJECT-TYPE
                        SYNTAX  INTEGER
                        ACCESS  read-write
                        STATUS  mandatory
                        DESCRIPTION
                                " "
                        ::= { alIpInterfaceEntry 7 }

                ipInterfacePktsIn OBJECT-TYPE
                        SYNTAX  INTEGER
                        ACCESS  read-only
                        STATUS  mandatory
                        DESCRIPTION
                                " "
                        ::= { alIpInterfaceEntry 8 }

                ipInterfaceOctetsIn OBJECT-TYPE
                        SYNTAX  INTEGER
                        ACCESS  read-only
                        STATUS  mandatory
                        DESCRIPTION
                                " "
                        ::= { alIpInterfaceEntry 9 }

                ipInterfacePktsOut OBJECT-TYPE
                        SYNTAX  INTEGER
                        ACCESS  read-only
                        STATUS  mandatory
                        DESCRIPTION
                                " "
                        ::= { alIpInterfaceEntry 10 }

                ipInterfaceOctetsOut OBJECT-TYPE
                        SYNTAX  INTEGER
                        ACCESS  read-only
                        STATUS  mandatory
                        DESCRIPTION
                                " "
                        ::= { alIpInterfaceEntry 11 }


-- 1.6.4	Route Cache Commands
	
-- 	. display-routecache
--	. flush-routecache

                alIpRtCacheTable OBJECT-TYPE
                        SYNTAX  SEQUENCE OF AlIpRtCacheEntry
                        ACCESS  not-accessible
                        STATUS  mandatory
                        DESCRIPTION
                                "IP Route Cache for all ports"

			::= { alip 20 }

                alIpRtCacheEntry OBJECT-TYPE
                        SYNTAX  AlIpRtCacheEntry
                        ACCESS  not-accessible
                        STATUS  mandatory
                        DESCRIPTION
                                "IP Route cache for each port "
                        INDEX   { ipRtCachePort, ipRtCacheDstAddress }
 
                        ::= { alIpRtCacheTable 1 }

                AlIpRtCacheEntry ::=
                                SEQUENCE {
                                                ipRtCachePort
                                                        INTEGER,
                                                ipRtCacheDstAddress
                                                        IpAddress,
						ipRtCacheClear
							INTEGER
				}


                ipRtCachePort OBJECT-TYPE
                        SYNTAX  INTEGER
                        ACCESS  read-write
                        STATUS  mandatory
                        DESCRIPTION
                                " "
                        ::= { alIpRtCacheEntry 1 }


                ipRtCacheDstAddress OBJECT-TYPE
                        SYNTAX  IpAddress
                        ACCESS  read-write
                        STATUS  mandatory
                        DESCRIPTION
                                " "
                        ::= { alIpRtCacheEntry 2 }

                ipRtCacheClear OBJECT-TYPE
                        SYNTAX  INTEGER
                        ACCESS  read-write
                        STATUS  mandatory
                        DESCRIPTION
                                "Setting this to Clear(1), will clear the
			routecache for the port and Destination address
			identified by the instance of ipRtCachePort and
			ipRtCacheDstAddress."

                        ::= { alIpRtCacheEntry 3 }


END

-- 1.6.5	Show Configuration / Set Configuration constants

--	. set ipDefaultTTL -> ipDefalutTTL in mib2
--	. set ipForwarding -> ipForwarding in mib2
--	. set ipBridging   -> in bridge subsystem; refer to 1.2.10.4
--	. set ARP aging    -> in IP subsystem ;    refer to 1.6.1.5
