--                      SAGEM SA
--                      11, 13 rue Watt
--                      75013 PARIS
--                      FRANCE
--
--                      phone   01 55 75 75 75
--                      fax     01 55 75 31 13
--
-- Introduction
--
-- This document defines the SNMP Management Information Base (MIB)
-- variables that are implemented in the MegaPAC suite of "Switch-Router"
-- software products, manufactured by Sat.  This MIB*
-- includes all Gateway Emulation, Terminal Emulation, Bridge / Router,
-- Protocol Translator and serial / packet Switching functions.
-- The document relies upon the Structure of Management Information
-- (SMI), RFC1155.  It is presented in a format described in RFC1212,
-- the Concise MIB document.
--
--      MIB Version ................... 25    (Fevrier , 1999)
--

SAT-MEGA-MIB --{ iso org(3) dod(6) internet(1) private(4) enterprises(1) 1038 4 }
   DEFINITIONS ::= BEGIN
   IMPORTS
		DisplayString FROM SNMPv2-TC
           OBJECT-TYPE, Counter, enterprises
                   FROM RFC1155-SMI
		TRAP-TYPE FROM RFC-1215;

        sat             OBJECT IDENTIFIER ::= { enterprises 1038 }
        mega            OBJECT IDENTIFIER ::= { sat 4 }

        products        OBJECT IDENTIFIER ::= { mega 1 }
        base            OBJECT IDENTIFIER ::= { mega 2 }
        controller      OBJECT IDENTIFIER ::= { mega 3 }
        channel         OBJECT IDENTIFIER ::= { mega 4 }
        x25File         OBJECT IDENTIFIER ::= { mega 5 }
        nameFile        OBJECT IDENTIFIER ::= { mega 6 }
        passFile        OBJECT IDENTIFIER ::= { mega 7 }
        macFile         OBJECT IDENTIFIER ::= { mega 8 }
        ilanFile        OBJECT IDENTIFIER ::= { mega 9 }
        elogFile        OBJECT IDENTIFIER ::= { mega 10 }
        billFile        OBJECT IDENTIFIER ::= { mega 11 }

-- The Products Group
-- The product group defined below identifies each model of MegaPAC
-- processor. Each model has a unique object identifier allocated
-- from this section which is referenced by the sysObjectID variable
-- from RFC1156. New products will be added at the end of this list.

        megaPAC-E-cpu-C         OBJECT IDENTIFIER ::= { products 1 }
        megaPAC-ESL             OBJECT IDENTIFIER ::= { products 2 }
        megaPAC-E-cpu-D-E       OBJECT IDENTIFIER ::= { products 3 }
        megaPAC-V-cpu-8         OBJECT IDENTIFIER ::= { products 4 }
        megaPAC-V-cpu-16        OBJECT IDENTIFIER ::= { products 5 }
        megaPAC-V-cpu-68040     OBJECT IDENTIFIER ::= { products 6 }
        megaPAC-V-cpu-68060     OBJECT IDENTIFIER ::= { products 7 }

-- The BASE Group
-- The BASE Group describes the global attributes of the MegaPAC.

        baseVersion     OBJECT-TYPE
            SYNTAX      DisplayString (SIZE (4))
            ACCESS      read-only
            STATUS      mandatory
            DESCRIPTION
                "Software Version.
                The software version currently running. Defined as YMMR (i.e.
                Year, Month, Revision"
            ::= { base 1 }

        baseRestartTime OBJECT-TYPE
            SYNTAX      DisplayString (SIZE (20))
            ACCESS      read-only
            STATUS      mandatory
            DESCRIPTION
                "BASE Restart Time.
                The time and data of the last system restart (i.e. power-on
                 or last BOOT)"
            ::= { base 2 }

        baseMaxPacketSize OBJECT-TYPE
            SYNTAX      INTEGER
            ACCESS      read-only
            STATUS      mandatory
            DESCRIPTION
                "Node Maximum Packet Size.
                The maximum single buffer size available on the MegaPAC."
            ::= { base 3 }

        baseBuffPoolMax OBJECT-TYPE
            SYNTAX      INTEGER
            ACCESS      read-only
            STATUS      mandatory
            DESCRIPTION
                "Node Buffer Pool Maximum.
                The maximum number of buffers available temporary storage of
                transitting data."
            ::= { base 4 }

        baseBuffPoolNow OBJECT-TYPE
            SYNTAX      INTEGER
            ACCESS      read-only
            STATUS      mandatory
            DESCRIPTION
                "Node Current Buffer Pool.
                The current number of free buffers available temporary storage of
                transitting data."
            ::= { base 5 }

        baseBufferPoolLowest OBJECT-TYPE
            SYNTAX      INTEGER
            ACCESS      read-only
            STATUS      mandatory
            DESCRIPTION
                "Node Buffer Pool Lowest.
                The lowest value the buffer pool has ever reached."
            ::= { base 6 }

        baseBufferPoolEmpty OBJECT-TYPE
            SYNTAX      INTEGER
            ACCESS      read-only
            STATUS      mandatory
            DESCRIPTION
                "Node Buffer Pool Empty.
                The number of times that the free buffer pool has fallen below
                the minimum buffer threshold 'baseBuffThreshold'."
            ::= { base 7 }

        baseStatBufferThreshold OBJECT-TYPE
            SYNTAX      INTEGER (5..1000)
            ACCESS      read-only
            STATUS      mandatory
            DESCRIPTION
                "Node Buffer Threshold.
                When the number of buffers in the free buffer pool reaches
                this threshold, flow control will occur."
            ::= { base 8 }

        baseMemorySize OBJECT-TYPE
            SYNTAX      INTEGER
            ACCESS      read-only
            STATUS      mandatory
            DESCRIPTION
                "Node Memory Size.
                The size of the system memory installed in the MegaPAC."
            ::= { base 9 }

        baseDataFramesIn OBJECT-TYPE
            SYNTAX      Counter
            ACCESS      read-only
            STATUS      mandatory
            DESCRIPTION
                "Node Frames In.
                The total number of frames received by the MegaPAC."
            ::= { base 10 }

        baseDataFramesOut OBJECT-TYPE
            SYNTAX      Counter
            ACCESS      read-only
            STATUS      mandatory
            DESCRIPTION
                "Node Frames Out.
                The total number of frames transmitted by the MegaPAC."
            ::= { base 11 }

        baseDataFrameRateIn OBJECT-TYPE
            SYNTAX      Counter
            ACCESS      read-only
            STATUS      mandatory
            DESCRIPTION
                "Node Frame Rate In.
                The rate measured in frames per second that the MegaPAC
                is currently receiving frames."
            ::= { base 12 }

        baseDataFrameRateOut OBJECT-TYPE
            SYNTAX      Counter
            ACCESS      read-only
            STATUS      mandatory
            DESCRIPTION
                "Node Frames Rate Out.
                The rate measured in frames per second that the MegaPAC
                is currently transmitting frames."
            ::= { base 13 }

        baseTotalCallSetUps OBJECT-TYPE
            SYNTAX      Counter
            ACCESS      read-only
            STATUS      mandatory
            DESCRIPTION
                "Node Total Call Set ups.
                The total number of calls successfully established by the
                MegaPAC."
            ::= { base 14 }

        baseCurrentCalls OBJECT-TYPE
            SYNTAX      Counter
            ACCESS      read-only
            STATUS      mandatory
            DESCRIPTION
                "Current calls.
                The number of calls currently active on the MegaPAC."
            ::= { base 15 }

        baseRetransmissions OBJECT-TYPE
            SYNTAX      Counter
            ACCESS      read-only
            STATUS      mandatory
            DESCRIPTION
                "Node Retransmissions.
                The total number of frames which have been retransmitted
                by the MegaPAC."
            ::= { base 16 }

        baseRejects OBJECT-TYPE
            SYNTAX      Counter
            ACCESS      read-only
            STATUS      mandatory
            DESCRIPTION
                "Node Rejects.
                The total number of frames that have been rejected by the
                MegaPAC."
            ::= { base 17 }

        baseTotalTransportCalls OBJECT-TYPE
            SYNTAX      Counter
            ACCESS      read-only
            STATUS      mandatory
            DESCRIPTION
                "Node Total Transport calls.
                The total number of transport calls established by the
                MegaPAC."
            ::= { base 18 }

        baseCurrentTransportCalls OBJECT-TYPE
            SYNTAX      Counter
            ACCESS      read-only
            STATUS      mandatory
            DESCRIPTION
                "Current Transport Calls.
                The number of transport calls currently active on the
                MegaPAC."
            ::= { base 19 }

        baseRunStatus OBJECT-TYPE
            SYNTAX      INTEGER { prom(1), ram(2) }
            ACCESS      read-only
            STATUS      mandatory
            DESCRIPTION
                "Node Run Status.
                This parameter indicates whether the operating system has
                been 'Booted' from RAM (TELELOAD) or EPROM (default)."
            ::= { base 20 }

        baseReports OBJECT-TYPE
            SYNTAX      DisplayString (SIZE (4))
            ACCESS      read-write
            STATUS      mandatory
            DESCRIPTION
                "Node Reporting channel.
                The name of the logical resource (channel) that the system
                reports will be directed to."
            ::= { base 21 }

        baseSessionStatistics OBJECT-TYPE
            SYNTAX      DisplayString (SIZE (4))
            ACCESS      read-write
            STATUS      mandatory
            DESCRIPTION
                "Node Session Statistics reporting channel.
                The name of the logical resource (channel) that the system
                session statistics will be directed to."
            ::= { base 22 }

        baseBufferThreshold OBJECT-TYPE
            SYNTAX      INTEGER (5..1000)
            ACCESS      read-write
            STATUS      mandatory
            DESCRIPTION
                "Node Buffer Threshold.
                The threshold before flow control is invoked"
            ::= { base 23 }

        baseInitialPresentationTimer OBJECT-TYPE
            SYNTAX      INTEGER (0..300)
            ACCESS      read-write
            STATUS      mandatory
            DESCRIPTION
                "Node Initial Presentation Timer.
                The maximum time allowed between initial connection to the
                presentation service and the user entering a valid resource.
                The call will be disconnected if this timer elapses."
            ::= { base 24 }

        baseSecondaryPresentationTimer OBJECT-TYPE
            SYNTAX      INTEGER (0..300)
            ACCESS      read-write
            STATUS      mandatory
            DESCRIPTION
                "Node Secondary Presentation Timer.
                After a call has been cleared by the Host DTE the user
                has the option to use the presentation service to
                establish another call, failure to do so within this time
                period will result in the initial call being cleared."
            ::= { base 25 }

        baseInactivityDetectTimer OBJECT-TYPE
            SYNTAX      INTEGER (0..30)
            ACCESS      read-write
            STATUS      mandatory
            DESCRIPTION
                "Node Inactivity Timer.
                This timer will cause calls to be cleared if the IDLE option
                has been configured on the channel."
            ::= { base 26 }

        baseSegmentAccounting OBJECT-TYPE
            SYNTAX      INTEGER { no(1), yes(2) }
            ACCESS      read-write
            STATUS      mandatory
            DESCRIPTION
                "Node Segment Accounting.
                This parameter causes the frames in/out parameters to
                be displayed in terms of 64 byte SEGMENTS rather than frames."
            ::= { base 27 }

        baseTerminalEmulationBuffers OBJECT-TYPE
            SYNTAX      INTEGER (0..640)
            ACCESS      read-write
            STATUS      mandatory
            DESCRIPTION
                "Terminal Emulation Buffers.
                The number of system buffers allocated for Terminal Emulation
                purposes."
            ::= { base 28 }

        baseTransportBuffers OBJECT-TYPE
            SYNTAX      INTEGER (0..2048)
            ACCESS      read-write
            STATUS      mandatory
            DESCRIPTION
                "Transport Buffers.
                The number of transport buffers allocated for TP 0,2,3,4
                sessions."
            ::= { base 29 }

        baseCountrySettings OBJECT-TYPE
            SYNTAX      INTEGER { none(1), japn(2) }
            ACCESS      read-write
            STATUS      mandatory
            DESCRIPTION
                "Country Setting.
                Invokes the ASCII representation of the Japanese
                character set."
            ::= { base 30 }

        baseTeleloadEnabled OBJECT-TYPE
            SYNTAX      INTEGER { no(1), yes(2), k256(3), k160(129) }
            ACCESS      read-write
            STATUS      mandatory
            DESCRIPTION
                "Teleload enable.
                If set to yes the MegaPAC software may be downloaded by
                ASCII file transfer."
            ::= { base 31 }

        baseDefaultToPromCompatible OBJECT-TYPE
            SYNTAX      INTEGER { no(1), yes(2) }
            ACCESS      read-write
            STATUS      mandatory
            DESCRIPTION
                "Cold Boot From PROM.
                If set to yes the MegaPAC software may be downloaded by
                ASCII file transfer."
            ::= { base 32 }

-- The Controller Group (Statistics Section)
-- The Controller Group described below relates to MegaPAC protocol
-- interfaces that support a physical or virtual interface
-- connection.  The controller Group defines all parameters available
-- in "flat table format", and as such, certain object types may or
-- may not be presented depending on the controller type being used.

        ctrlNumberConfigured OBJECT-TYPE
            SYNTAX      INTEGER
            ACCESS      read-only
            STATUS      mandatory
            DESCRIPTION
                "Total Number of Controllers Configured.
                The number of controllers in the MegaPAC which have been
                configured."
            ::= { controller 1 }

        ctrlTotalNumber OBJECT-TYPE
            SYNTAX      INTEGER
            ACCESS      read-only
            STATUS      mandatory
            DESCRIPTION
                "Total Number of Controllers.
                The TOTAL number of controllers in the MegaPAC including
                unconfigured (NULL) controllers."
            ::= { controller 2 }

        ctrlStatTable OBJECT-TYPE
            SYNTAX      SEQUENCE OF CtrlStatEntry
            ACCESS      not-accessible
            STATUS      mandatory
            ::= { controller 3 }

        ctrlStatEntry OBJECT-TYPE
            SYNTAX      CtrlStatEntry
            ACCESS      not-accessible
            STATUS      mandatory
            DESCRIPTION
                ""
            INDEX       { ctrlStatIndex }
            ::= { ctrlStatTable 1 }

        CtrlStatEntry ::= SEQUENCE { ctrlStatIndex
                                     INTEGER,
                                     ctrlStatName
                                     DisplayString,
                                     ctrlStatType
                                     INTEGER,
                                     ctrlStatSubType
                                     INTEGER,
                                     ctrlStatNumberChannels
                                     INTEGER,
                                     ctrlStatFirstChannelIndex
                                     INTEGER,
                                     ctrlStatCRCErrors
                                     Counter,
                                     ctrlStatTotalCallSetUps
                                     Counter,
                                     ctrlStatCurrentCalls
                                     INTEGER,
                                     ctrlStatDataIn
                                     Counter,
                                     ctrlStatDataOut
                                     Counter,
                                     ctrlStatDataFramesIn
                                     Counter,
                                     ctrlStatDataFramesOut
                                     Counter,
                                     ctrlStatDataFrameRateIn
                                     INTEGER,
                                     ctrlStatDataFrameRateOut
                                     INTEGER,
                                     ctrlStatCallsReceived
                                     Counter,
                                     ctrlStatCallsSent
                                     Counter,
                                     ctrlStatClearsReceived
                                     Counter,
                                     ctrlStatRetransmissions
                                     Counter,
                                     ctrlStatRejects
                                     Counter,
                                     ctrlStatState
                                     INTEGER,
                                     ctrlStatSubState
                                     INTEGER,
                                     ctrlStatNoTries
                                     Counter,
                                     ctrlStatOptions
                                     INTEGER,
                                     ctrlStatLCGN
                                     INTEGER,
                                     ctrlStatResetsReceived
                                     Counter,
                                     ctrlStatInterruptsReceived
                                     Counter,
                                     ctrlStatOutputQueueLength
                                     INTEGER,
                                     ctrlStatStationAddress
                                     DisplayString,
                                     ctrlStatDestinationAddress
                                     DisplayString,
                                     ctrlStatEIA
                                     DisplayString,
                                     ctrlStatSdlcOptions
                                     INTEGER,
                                     ctrlStatArpRequestRec
                                     INTEGER,
                                     ctrlStatArpRequestSent
                                     INTEGER,
                                     ctrlStatArpResponsesRec
                                     INTEGER,
                                     ctrlStatFRTxSeqLost
                                     INTEGER,
                                     ctrlStatFRRxSeqLost
                                     INTEGER,
                                     ctrlStatFRCurTxSeq
                                     INTEGER,
                                     ctrlStatFRCurRxSeq
                                     INTEGER,
                                     ctrlStatFRRcvBecn
                                     INTEGER,
                                     ctrlStatFRRcvFecn
                                     INTEGER,
                                     ctrlStatFRThroughput
                                     INTEGER,
                                     ctrlStatFRLMI
                                     INTEGER,
                                     ctrlStatFRrespLmi
                                     INTEGER,
                                     ctrlStatFRCurSndSeq
                                     INTEGER,
                                     ctrlStatFRCurRcvSeq
                                     INTEGER,
                                     ctrlStatFRRcvDe
                                     INTEGER }

        ctrlStatIndex OBJECT-TYPE
            SYNTAX      INTEGER
            ACCESS      read-only
            STATUS      mandatory
            DESCRIPTION
                "Controller index.
                The position of this controller in relation to 'BASE'.
                 i.e.   BASE = 0
                        NMSC = 1
                        PS01 = 2
                        ..."
            REFERENCE
                "ALL"
            ::={ ctrlStatEntry 1 }

        ctrlStatName OBJECT-TYPE
            SYNTAX      DisplayString (SIZE(4))
            ACCESS      read-only
            STATUS      mandatory
            DESCRIPTION
                "Controller name.
                The unique 4 character name by which this controller is
                known."
            REFERENCE
                "ALL"
            ::={ ctrlStatEntry 2 }

        ctrlStatType OBJECT-TYPE
            SYNTAX      INTEGER { x25(1),    mux(2),   null(3),  epci(4),  hdlc(8),  qllc(9),
                                  xlan(10),  ilan(11), term(12), lan(13),  clus(14), mult(15),
                                  sdlc(16),  ip(17),   sru(18),  v25b(19), cons(20), nmsc(21),
                                  dlc(22),   map(23),  tlan(24), snmp(25), nfrm(26), xfrm(27),
                                  tip(28),   rout(29), ppp(30),  ipx(31),  tipx(32), esis(34),
                                  tesis(35), vfrm(36), smdx(37), dlcx(38), edlc(39) }
            ACCESS      read-only
            STATUS      mandatory
            DESCRIPTION
                "Controller Type.
                The type of controller this is.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::={ ctrlStatEntry 3 }

        ctrlStatSubType OBJECT-TYPE
            SYNTAX      INTEGER { none(1), sio(2), xio(3),
                                  xio-sio(4), generic(5),scc(17), vio(33) }
            ACCESS      read-only
            STATUS      mandatory
            DESCRIPTION
                "Sub Type.
                The serial I/O board installed."
            REFERENCE
                "PPP X25 XFRM NFRM VFRM SDLC QLLC HDLC"
            ::={ ctrlStatEntry 4 }

        ctrlStatNumberChannels OBJECT-TYPE
            SYNTAX      INTEGER
            ACCESS      read-only
            STATUS      mandatory
            DESCRIPTION
                "Channel Count.
                The number of channels assigned to a controller.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::={ ctrlStatEntry 5 }

        ctrlStatFirstChannelIndex OBJECT-TYPE
            SYNTAX      INTEGER
            ACCESS      read-only
            STATUS      mandatory
            DESCRIPTION
                "First Channnel.
                The 1st channel index number used by the controller
                : PPP, X.25, XFRM, NFRM VFRM, CONS, IP, TIP, IPX, TIPX,
                ESIS, DLC, LAN, TLAN, ILAN, XLAN SDLC, TERM, QLLC & HDLC"
            REFERENCE
                "PPP X25 XFRM NFRM VFRM CONS IP TIP IPX TIPX ESIS
                DLC LAN TLAN ILAN XLAN SDLC TERM QLLC HDLC"
            ::={ ctrlStatEntry 6 }

        ctrlStatCRCErrors OBJECT-TYPE
            SYNTAX      Counter
            ACCESS      read-only
            STATUS      mandatory
            DESCRIPTION
                "CRC Errors.
                The number of packets received for which the checksum
                was not valid.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 7 }

        ctrlStatTotalCallSetUps OBJECT-TYPE
            SYNTAX      Counter
            ACCESS      read-only
            STATUS      mandatory
            DESCRIPTION
                "Total Call Set ups.
                The total number of successful calls established on this
                link.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 8 }

        ctrlStatCurrentCalls OBJECT-TYPE
            SYNTAX      INTEGER
            ACCESS      read-only
            STATUS      mandatory
            DESCRIPTION
                "Current Calls.
                The number of calls currently active on this link.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 9 }

        ctrlStatDataIn OBJECT-TYPE
            SYNTAX      Counter
            ACCESS      read-only
            STATUS      mandatory
            DESCRIPTION
                "Data In.
                The total number of data bytes received on this link.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 10 }

        ctrlStatDataOut OBJECT-TYPE
            SYNTAX      Counter
            ACCESS      read-only
            STATUS      mandatory
            DESCRIPTION
                "Data Out.
                The total number of data bytes transmitted on this link.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 11 }

        ctrlStatDataFramesIn OBJECT-TYPE
            SYNTAX      Counter
            ACCESS      read-only
            STATUS      mandatory
            DESCRIPTION
                "Data Frames In.
                The total number of data frames received on this link.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 12 }

        ctrlStatDataFramesOut OBJECT-TYPE
            SYNTAX      Counter
            ACCESS      read-only
            STATUS      mandatory
            DESCRIPTION
                "Data Frames Out.
                The total number of data frames transmitted on this
                link.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 13 }

        ctrlStatDataFrameRateIn OBJECT-TYPE
            SYNTAX      INTEGER
            ACCESS      read-only
            STATUS      mandatory
            DESCRIPTION
                "Data Frame Rate In.
                The rate that frames are arriving on this link,
                specified in frames per second.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 14 }

        ctrlStatDataFrameRateOut OBJECT-TYPE
            SYNTAX      INTEGER
            ACCESS      read-only
            STATUS      mandatory
            DESCRIPTION
                "Data Frame Frate Out.
                The rate that frames are being transmitted on this link,
                specified in frames per second.
                Applicable controllers: PPP, X.25, XFRM, NFRM VFRM, CONS,
                IP, TIP, IPX, TIPX, ESIS, DLC, LAN, TLAN, ILAN, XLAN
                SDLC, TERM, QLLC AND HDLC"
            REFERENCE
                "PPP X25 XFRM NFRM VFRM CONS IP TIP IPX TIPX ESIS
                DLC LAN TLAN ILAN XLAN SDLC TERM QLLC HDLC"
            ::= { ctrlStatEntry 15 }

        ctrlStatCallsReceived OBJECT-TYPE
            SYNTAX      Counter
            ACCESS      read-only
            STATUS      mandatory
            DESCRIPTION
                "Calls Received.
                The total number of incoming call requests seen on this
                link.
                Applicable controllers: PPP, X.25, XFRM, NFRM VFRM, CONS,
                DLC, SDLC, TERM, QLLC, HDLC, IPX, TIPX, ESIS,
                LAN, TLAN, ILAN AND XLAN"
            REFERENCE
                "PPP X25 XFRM NFRM VFRM CONS DLC SDLC TERM QLLC
                HDLC IPX TIPX ESIS LAN TLAN ILAN XLAN"
            ::= { ctrlStatEntry 16 }

        ctrlStatCallsSent OBJECT-TYPE
            SYNTAX      Counter
            ACCESS      read-only
            STATUS      mandatory
            DESCRIPTION
                "Calls Sent.
                The total number of call requests sent out on this link.
                Applicable controllers: PPP, X.25, XFRM, NFRM VFRM, CONS,
                DLC, SDLC, TERM, QLLC, HDLC, IPX, TIPX, ESIS,
                LAN, TLAN, ILAN AND XLAN"
            REFERENCE
                "PPP X25 XFRM NFRM VFRM CONS DLC SDLC TERM QLLC
                HDLC IPX TIPX ESIS LAN TLAN ILAN XLAN"
            ::= { ctrlStatEntry 17 }

        ctrlStatClearsReceived OBJECT-TYPE
            SYNTAX      Counter
            ACCESS      read-only
            STATUS      mandatory
            DESCRIPTION
                "Clears Received.
                The total number of call clear requests received on this
                link.
                Applicable controllers: PPP, X.25, XFRM, NFRM VFRM, CONS,
                DLC, SDLC, TERM, QLLC, HDLC, IPX, TIPX, ESIS,
                LAN, TLAN, ILAN AND XLAN"
            REFERENCE
                "PPP X25 XFRM NFRM VFRM CONS DLC SDLC TERM QLLC
                HDLC IPX TIPX ESIS LAN TLAN ILAN XLAN"
            ::= { ctrlStatEntry 18 }

        ctrlStatRetransmissions OBJECT-TYPE
            SYNTAX      Counter
            ACCESS      read-only
            STATUS      mandatory
            DESCRIPTION
                "Retransmissions.
                The number of packets that have been transmitted more
                than once on this link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 19 }

        ctrlStatRejects OBJECT-TYPE
            SYNTAX      Counter
            ACCESS      read-only
            STATUS      mandatory
            DESCRIPTION
                "Rejects.
                The total number of packets which have been rejected on
                this link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 20 }

        ctrlStatState OBJECT-TYPE
            SYNTAX      INTEGER { disc(1), sabm(9), data(11),
                                  blkd(13), wake(15), cls(17),
                                  frmr(19), stop(21), xidr(23),
                                  xidc(25) }
            ACCESS      read-only
            STATUS      mandatory
            DESCRIPTION
                "State.
                The level 2 data state of the link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 21 }

        ctrlStatSubState OBJECT-TYPE
            SYNTAX      INTEGER { norm(1), rej(5), disc(9),
                                  idle(1), actv(3), new(129) }
            ACCESS      read-only
            STATUS      mandatory
            DESCRIPTION
                "Sub State.
                The level 3 state of this link.
                Applicable controllers: PPP, X.25, XFRM, NFRM, VFRM, CONS,
                DLC, SDLC, TERM, QLLC AND HDLC"
            REFERENCE
                "PPP X25 XFRM NFRM VFRM CONS DLC SDLC TERM QLLC
                HDLC"
            ::= { ctrlStatEntry 22 }

        ctrlStatNoTries OBJECT-TYPE
            SYNTAX      Counter
            ACCESS      read-only
            STATUS      mandatory
            DESCRIPTION
                "Tries.
                The number of un-numbered control frames sent to try and
                establish the link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 23 }

        ctrlStatOptions OBJECT-TYPE
            SYNTAX      INTEGER { none(1),     iso1984(16385),
                                  poll(32769), ext(8193),
                                  hold(4097),  stat(2049),
                                  net(257),    dmod(1025),
                                  dcd(513),    ui(17),
                                  xidc(5),     xidr(9),
                                  test(3),     dtr(2),
                                  poll-ext(40961) }
            ACCESS      read-only
            STATUS      mandatory
            DESCRIPTION
                "Options
                The options currently configured for this link. Note, that
                the values returned by the MegaPAC may be additive
                values - representing combined combinations for the
                table listed e.g. poll+ext.
                In this situation modify the MIB entering the resulting
                integer value minus one e.g. 32769+8193-1=40961 (poll+ext)
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 24 }

        ctrlStatLCGN OBJECT-TYPE
            SYNTAX      INTEGER
            ACCESS      read-only
            STATUS      mandatory
            DESCRIPTION
                "LCGN
                The logical channel group number for this link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 25 }

        ctrlStatResetsReceived OBJECT-TYPE
            SYNTAX      Counter
            ACCESS      read-only
            STATUS      mandatory
            DESCRIPTION
                "Resets Received.
                The total number of reset packets received on this link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 26 }

        ctrlStatInterruptsReceived OBJECT-TYPE
            SYNTAX      Counter
            ACCESS      read-only
            STATUS      mandatory
            DESCRIPTION
                "Interupts Received.
                The total number of interrupt packets received on this
                link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 27 }

        ctrlStatOutputQueueLength OBJECT-TYPE
            SYNTAX      INTEGER
            ACCESS      read-only
            STATUS      mandatory
            DESCRIPTION
                "Output Queue Length.
                The number of packets queued for transmission on this
                link.
                Applicable controllers: PPP, X.25, XFRM, NFRM VFRM, CONS,
                DLC, SDLC, TERM, QLLC AND HDLC"
            REFERENCE
                "PPP X25 XFRM NFRM VFRM CONS DLC SDLC TERM QLLC
                HDLC"
            ::= { ctrlStatEntry 28 }

        ctrlStatStationAddress OBJECT-TYPE
            SYNTAX      DisplayString (SIZE(12))
            ACCESS      read-only
            STATUS      mandatory
            DESCRIPTION
                "Local MAC Address
                The MAC Address of the MegaPAC.
                Applicable controllers: CONS, IPX, TIPX, ESIS, IP, TIP
                LAN, TLAN, ILAN AND XLAN"
            REFERENCE
                "CONS IPX TIPX ESIS LAN TLAN ILAN XLAN IP TIP"
            ::= { ctrlStatEntry 29 }

        ctrlStatDestinationAddress OBJECT-TYPE
            SYNTAX      DisplayString (SIZE(12))
            ACCESS      read-only
            STATUS      mandatory
            DESCRIPTION
                "Destination MAC Address.
                The MAC Address of the destination device.
                Applicable controllers: CONS only"
            REFERENCE
                "CONS"
            ::= { ctrlStatEntry 30 }

        ctrlStatEIA OBJECT-TYPE
            SYNTAX      DisplayString (SIZE(8))
            ACCESS      read-only
            STATUS      mandatory
            DESCRIPTION
                "EIA state.
                Displays the EIA signals currently on the link.
                Applicable controllers: X.25, QLLC and HDLC"
            REFERENCE
                "X25 QLLC HDLC"
            ::= { ctrlStatEntry 31 }

        ctrlStatSdlcOptions OBJECT-TYPE
            SYNTAX      INTEGER { none(1),  pu4(33),  wait(65),
                                  xid(129), idle(17), wait-xid(193) }
            ACCESS      read-only
            STATUS      mandatory
            DESCRIPTION
                "SDLC Options.
                A range of link level options used for establishing
                IBM connections. Note, that the values returned by the
                MegaPAC may be additive values - representing
                combined combinations for the table listed e.g. wait+xid.
                In this situation modify the MIB entering the resulting
                integer value minus one e.g. 129+65-1=193 (wait+xid)"
            REFERENCE
              "QLLC SDLC"
            ::= { ctrlStatEntry 32 }

        ctrlStatArpRequestRec OBJECT-TYPE
            SYNTAX      INTEGER
            ACCESS      read-only
            STATUS      mandatory
            DESCRIPTION
                "ARP Requests Received.
                The number of ARP requests sent to the MegaPAC"
            REFERENCE
                "IP TIP"
            ::= { ctrlStatEntry 33 }

        ctrlStatArpRequestSent OBJECT-TYPE
            SYNTAX      INTEGER
            ACCESS      read-only
            STATUS      mandatory
            DESCRIPTION
                "ARP Requests Sent.
                The number of ARP requests processed to the local LAN
                by the MegaPAC"
            REFERENCE
                "IP TIP"
            ::= { ctrlStatEntry 34 }

        ctrlStatArpResponsesRec OBJECT-TYPE
            SYNTAX      INTEGER
            ACCESS      read-only
            STATUS      mandatory
            DESCRIPTION
                "ARP Respones Received.
                The number of ARP responses returned to the
                the MegaPAC"
            REFERENCE
                "IP TIP"
            ::= { ctrlStatEntry 35 }

        ctrlStatFRTxSeqLost OBJECT-TYPE
            SYNTAX      INTEGER
            ACCESS      read-only
            STATUS      mandatory
            DESCRIPTION "Number of LMI without Reply"
            REFERENCE
                " XFRM NFRM VFRM"
            ::= { ctrlStatEntry 36 }

        ctrlStatFRRxSeqLost OBJECT-TYPE
            SYNTAX      INTEGER
            ACCESS      read-only
            STATUS      mandatory
            DESCRIPTION "Number of Lost LMI"
            REFERENCE
                " XFRM NFRM VFRM"
            ::= { ctrlStatEntry 37 }

        ctrlStatFRCurTxSeq OBJECT-TYPE
            SYNTAX      INTEGER
            ACCESS      read-only
            STATUS      mandatory
            DESCRIPTION "LMI sequence number sent in enquiries"
            REFERENCE
                " XFRM NFRM VFRM"
            ::= { ctrlStatEntry 38 }

        ctrlStatFRCurRxSeq OBJECT-TYPE
            SYNTAX      INTEGER
            ACCESS      read-only
            STATUS      mandatory
            DESCRIPTION "LMI sequence number received in responses"
            REFERENCE
                " XFRM NFRM VFRM"
            ::= { ctrlStatEntry 39 }

        ctrlStatFRRcvBecn OBJECT-TYPE
            SYNTAX      INTEGER
            ACCESS      read-only
            STATUS      mandatory
            DESCRIPTION "Number of received frames with BECN"
            REFERENCE
                " XFRM NFRM VFRM"
            ::= { ctrlStatEntry 40 }

        ctrlStatFRRcvFecn OBJECT-TYPE
            SYNTAX      INTEGER
            ACCESS      read-only
            STATUS      mandatory
            DESCRIPTION "Number of received frames with FECN"
            REFERENCE
                " XFRM NFRM VFRM"
            ::= { ctrlStatEntry 41 }

        ctrlStatFRThroughput OBJECT-TYPE
            SYNTAX      INTEGER
            ACCESS      read-only
            STATUS      mandatory
            DESCRIPTION "Number of characters during T"
            REFERENCE
                " XFRM NFRM VFRM"
            ::= { ctrlStatEntry 42 }

        ctrlStatFRLMI OBJECT-TYPE
            SYNTAX      INTEGER  { down(0), up(2) }
            ACCESS      read-only
            STATUS      mandatory
            DESCRIPTION "Status of LMI"
            REFERENCE
                " XFRM NFRM VFRM"
            ::= { ctrlStatEntry 43 }

        ctrlStatFRrespLmi OBJECT-TYPE
            SYNTAX      INTEGER
            ACCESS      read-only
            STATUS      mandatory
            DESCRIPTION "Count of LMI responses"
            REFERENCE
                " XFRM NFRM VFRM"
            ::= { ctrlStatEntry 44 }

        ctrlStatFRCurSndSeq OBJECT-TYPE
            SYNTAX      INTEGER
            ACCESS      read-only
            STATUS      mandatory
            DESCRIPTION "LMI sequence number sent in responses"
            REFERENCE
                " XFRM NFRM VFRM"
            ::= { ctrlStatEntry 45 }

        ctrlStatFRCurRcvSeq OBJECT-TYPE
            SYNTAX      INTEGER
            ACCESS      read-only
            STATUS      mandatory
            DESCRIPTION "LMI sequence number received in enquiries"
            REFERENCE
                " XFRM NFRM VFRM"
            ::= { ctrlStatEntry 46 }

        ctrlStatFRRcvDe OBJECT-TYPE
            SYNTAX      INTEGER
            ACCESS      read-only
            STATUS      mandatory
            DESCRIPTION "Number of received frames with DE bit set"
            REFERENCE
                " XFRM NFRM VFRM"
            ::= { ctrlStatEntry 47 }


--      The Controller configuration section
        ctrlParamTable OBJECT-TYPE
            SYNTAX      SEQUENCE OF CtrlParamEntry
            ACCESS      not-accessible
            STATUS      mandatory
            DESCRIPTION
                "The controller configuration table."
            ::= { controller 4 }

        ctrlParamEntry OBJECT-TYPE
            SYNTAX      CtrlParamEntry
            ACCESS      not-accessible
            STATUS      mandatory
            DESCRIPTION
                "An individual controller configuration."
            INDEX       { ctrlParamIndex }
            ::= { ctrlParamTable 1 }

        CtrlParamEntry ::= SEQUENCE {ctrlParamIndex
                                     INTEGER,
                                     ctrlParamName
                                     DisplayString,
                                     ctrlParamType
                                     INTEGER,
                                     ctrlParamSubType
                                     INTEGER,
                                     ctrlParamNoChannels
                                     INTEGER,
                                     ctrlParamSpeed
                                     INTEGER,
                                     ctrlParamInterfaceType
                                     INTEGER,
                                     ctrlParamPacketSize
                                     INTEGER,
                                     ctrlParamV54Modem
                                     INTEGER,
                                     ctrlParamAddress
                                     INTEGER,
                                     ctrlParamOptions
                                     INTEGER,
                                     ctrlParamInitFrame
                                     INTEGER,
                                     ctrlParamT1
                                     INTEGER,
                                     ctrlParamTries
                                     INTEGER,
                                     ctrlParamKLevel2
                                     INTEGER,
                                     ctrlParamKLevel3
                                     INTEGER,
                                     ctrlParamLineGroup
                                     INTEGER,
                                     ctrlParamLCGN
                                     INTEGER,
                                     ctrlParamLCNOffset
                                     INTEGER,
                                     ctrlParamAddressGroup
                                     INTEGER,
                                     ctrlParamFrameSequence
                                     INTEGER,
                                     ctrlParamCallTimeOut
                                     INTEGER,
                                     ctrlParamErrorThreshold
                                     INTEGER,
                                     ctrlParamLoopBarPriority
                                     INTEGER,
                                     ctrlParamExtendedCallMgmt
                                     INTEGER,
                                     ctrlParamOptionalTimers
                                     INTEGER,
                                     ctrlParamOptionalFlags
                                     INTEGER,
                                     ctrlParamTransportLevelType
                                     INTEGER,
                                     ctrlParamTransportClass
                                     INTEGER,
                                     ctrlParamDefaultWindowSize
                                     INTEGER,
                                     ctrlParamDisableFlowControl
                                     INTEGER,
                                     ctrlParamTSAPFormat
                                     INTEGER,
                                     ctrlParamMaximumTPDUSize
                                     INTEGER,
                                     ctrlParamTTRTime
                                     INTEGER,
                                     ctrlParamTWRTime
                                     INTEGER,
                                     ctrlParamDestinationAddress
                                     DisplayString,
                                     ctrlParamDSAP
                                     INTEGER,
                                     ctrlParamSSAP
                                     INTEGER,
                                     ctrlParamSDLCOptions
                                     INTEGER,
                                     ctrlParamPrimaryStation
                                     INTEGER,
                                     ctrlParamIdleDetectTime
                                     INTEGER,
                                     ctrlParamPollInterval
                                     INTEGER,
                                     ctrlParamDuplex
                                     INTEGER,
                                     ctrlParamTransmitDelay
                                     INTEGER,
                                     ctrlParamSlowPollTimer
                                     INTEGER,
                                     ctrlParamMaxCallInterval
                                     INTEGER,
                                     ctrlParamMaxCallCycles
                                     INTEGER,
                                     ctrlParamGroupPoll
                                     INTEGER,
                                     ctrlParamDelayToRTSLow
                                     INTEGER,
                                     ctrlParamDelayToCTSHigh
                                     INTEGER,
                                     ctrlParamInputSyncDeletion
                                     INTEGER,
                                     ctrlParamOutputSyncInsertion
                                     INTEGER,
                                     ctrlParamDCDFilter
                                     INTEGER,
                                     ctrlParamInhibitTimeFill
                                     INTEGER,
                                     ctrlParamDirectedBroadcasts
                                     INTEGER,
                                     ctrlParamDefaultLocalPrinter
                                     INTEGER,
                                     ctrlParamNewLANInterface
                                     INTEGER,
                                     ctrlParamNewSerialInterface
                                     INTEGER,
                                     ctrlParamDlci
                                     INTEGER,
                                     ctrlParamMode
                                     INTEGER,
                                     ctrlParamLmi
                                     INTEGER,
                                     ctrlParamKeepAliveTimer
                                     INTEGER,
                                     ctrlParamFullStatusInterval
                                     INTEGER,
                                     ctrlParamBandwidth
                                     INTEGER,
                                     ctrlParamBurstCommit
                                     INTEGER,
                                     ctrlParamBurstEligibility
                                     INTEGER,
                                     ctrlParamTimerT3
                                     INTEGER,
                                     ctrlParamFlowControl
                                     INTEGER,
                                     ctrlParamConfigState
                                     INTEGER,
                                     ctrlParamTry
                                     INTEGER
                                        }

        ctrlParamIndex OBJECT-TYPE
            SYNTAX      INTEGER
            ACCESS      read-only
            STATUS      mandatory
            DESCRIPTION
                "Index
                The position of this controller in relation to 'BASE'.
                 i.e.   BASE = 0
                        NMSC = 1
                        PS01 = 2
                        ...
                Applicable: All controller types"
            REFERENCE
                "ALL"
            ::={ ctrlParamEntry 1 }

        ctrlParamName OBJECT-TYPE
            SYNTAX      DisplayString (SIZE(4))
            ACCESS      read-write
            STATUS      mandatory
            DESCRIPTION
                "Name.
                The unique 4 character name by which this controller is
                known.
                Applicable: All controller types"
            REFERENCE
                "ALL"
            ::={ ctrlParamEntry 2 }

        ctrlParamType OBJECT-TYPE
            SYNTAX      INTEGER { x25(1),    mux(2),   null(3),
                                  epci(4),   hdlc(8),  qllc(9),
                                  xlan(10),  ilan(11), term(12),
                                  lan(13),   clus(14), mult(15),
                                  sdlc(16),  ip(17),   sru(18),
                                  v25b(19),  cons(20), nmsc(21),
                                  dlc(22),   map(23),  tlan(24),
                                  snmp(25),  nfrm(26), xfrm(27),
                                  tip(28),   rout(29), ppp(30),
                                  ipx(31),   tipx(32), esis(34),
                                  tesis(35), vfrm(36), smdx(37),
                                  dlcx(38), edlc(39) }
            ACCESS      read-write
            STATUS      mandatory
            DESCRIPTION
                "Type.
                The type of controller this is.
                Applicable: All controller types"
            REFERENCE
                "ALL"
            ::={ ctrlParamEntry 3 }

        ctrlParamSubType OBJECT-TYPE
            SYNTAX      INTEGER { none(1), sio(2), xio(3), xio-sio(4),
                                  generic(5), scc(17), vio(33) }
            ACCESS      read-write
            STATUS      mandatory
            DESCRIPTION
                "Sub-Type.
                The link between the controller and its associated hardware
                type.
                Applicable: X25, SDLC, QLLC, HDLC and NULL controller types"
            REFERENCE
                "NFRM VFRM PPP QLLC SDLC X25 NULL XFRM"
            ::= { ctrlParamEntry 4 }

        ctrlParamNoChannels OBJECT-TYPE
            SYNTAX      INTEGER (0..4096)
            ACCESS      read-write
            STATUS      mandatory
            DESCRIPTION
                "Number of channels.
                The number of logical channels configured on the controller.
                Applicable: All controller types"
            REFERENCE
                "ALL"
            ::= { ctrlParamEntry 5 }

        ctrlParamSpeed OBJECT-TYPE
            SYNTAX      INTEGER { speed-2mbps(19),    speed-1mbps(18),
                                  speed-512kbps(17),  speed-256kbps(16),
                                  speed-128kbps(15),  speed-64kbps(14),
                                  speed-12-75bps(13), speed-19200bps(12),
                                  speed-9600bps(11),  speed-7200bps(10),
                                  speed-4800bps(9),   speed-3600bps(8),
                                  speed-2400bps(7),   speed-2000bps(6),
                                  speed-1800bps(5),   speed-1200bps(4),
                                  speed-600bps(3),    speed-300bps(2),
                                  ext-clock(1), none(0) }
            ACCESS      read-write
            STATUS      mandatory
            DESCRIPTION
                "Speed.
                The clock speed of the interface.
                Applicable: X25, SDLC, QLLC, HDLC and NULL controller types"
            REFERENCE
                "NFRM VFRM PPP QLLC SDLC X25 NULL XFRM"
            ::= { ctrlParamEntry 6 }

        ctrlParamInterfaceType OBJECT-TYPE
            SYNTAX      INTEGER { x21(2), v35(3), v24(1) }
            ACCESS      read-write
            STATUS      mandatory
            DESCRIPTION
                "The serial interface type.  Note, Only applicable to MegaCard
                Applicable: XFRM, NFRM, PPP, X25, HDLC
                controller types"
            REFERENCE
                "NFRM VFRM PPP QLLC SDLC X25 NULL XFRM"
            ::= { ctrlParamEntry 7 }

        ctrlParamPacketSize OBJECT-TYPE
            SYNTAX      INTEGER { bytes-32(2),  bytes-64(3),   bytes-128(5),
                                  bytes-256(9), bytes-512(17), bytes-1024(33),
                                  tran(1) }
            ACCESS      read-write
            STATUS      mandatory
            DESCRIPTION
                "Packet Size.
                The maximum packet size in bytes of outgoing packets,
                this parameter must be less than or equal to the 'BASE'
                statistic 'maxPacketSize'.
                Applicable: X25, TERM, HDLC, CONS, DLC and NULL
                controller types"
            REFERENCE
                "CONS DLC TERM X25 NULL HDLC"
            ::= { ctrlParamEntry 8 }

        ctrlParamV54Modem OBJECT-TYPE
            SYNTAX      INTEGER { yes(61), no(1) }
            ACCESS      read-write
            STATUS      mandatory
            DESCRIPTION
                "V54 Modem.
                Enable V54 loop back testing. Note this does not initiate
                loop back testing, the loop back is initiated by typing
                in the 'TEST' command.
                Applicable: X25, HDLC and NULL controller types"
            REFERENCE
                "X25 NULL HDLC"
            ::= { ctrlParamEntry 9 }

        ctrlParamAddress OBJECT-TYPE
            SYNTAX      INTEGER { dte-a(1), dce-b(2) }
            ACCESS      read-write
            STATUS      mandatory
            DESCRIPTION
                "Address.
                The logical address designation of the controller.
                Applicable: X25, HDLC and NULL controller types"
            REFERENCE
                "X25 NULL HDLC"
            ::= { ctrlParamEntry 10 }

        ctrlParamOptions OBJECT-TYPE
            SYNTAX      INTEGER { none(1),       iso1984(16385), poll(32769),
                                poll-net(33025), ext(8193),      hold(4097),
                                stat(2049),      net(257),       dmod(1025),
                                dcd(513),        ui(17),         xidc(5),
                                xidr(9),         test(3),        dtr(2),
                                poll-ext(40961) }
            ACCESS      read-write
            STATUS      mandatory
            DESCRIPTION
                "Options.
                A range of controller options, options may be specified
                individually or added together. Note, that
                the values returned by the MegaPAC may be additive
                values - representing combined combinations for the
                table listed e.g. poll+ext.
                In this situation modify the MIB entering the resulting
                integer value minus one e.g. 32769+8193-1=40961 (poll+ext)
                Applicable: X25, HDLC, CONS, ILAN, XLAN, DLC"
            REFERENCE
                "CONS DLC ILAN QLLC SDLC X25 NULL XLAN"
            ::= { ctrlParamEntry 11 }

        ctrlParamInitFrame OBJECT-TYPE
            SYNTAX      INTEGER { sabm(48), sabm-pbit(64),
                                  disc(68), disc-pbit(84),
                                  none(1) }
            ACCESS      read-write
            STATUS      mandatory
            DESCRIPTION
                "Initial Frame.
                Applicable: X25, HDLC, CONS, ILAN, XLAN, DLC and NULL
                controller types"
            REFERENCE
                "CONS DLC ILAN X25 NULL XLAN"
            ::= { ctrlParamEntry 12 }

        ctrlParamT1 OBJECT-TYPE
            SYNTAX      INTEGER (2..80)
            ACCESS      read-write
            STATUS      mandatory
            DESCRIPTION
                "T1.
                Timer for retransmission of unacknowleged frames. Specified
                in 0.1 second units.
                Applicable: X25, HDLC, CONS, ILAN, XLAN, DLC and
                NULL controller types"
            REFERENCE
                "CONS DLC ILAN X25 NULL XLAN HDLC"
            ::= { ctrlParamEntry 13 }

        ctrlParamTries OBJECT-TYPE
            SYNTAX      INTEGER (2..50)
            ACCESS      read-write
            STATUS      mandatory
            DESCRIPTION
                "Tries.
                The number of times a frame will be retransmitted before
                a link restart is initiated.
                Applicable: X25, SDLC, QLLC, HDLC, CONS, ILAN, XLAN, DLC
                and NULL controller types"
            REFERENCE
                "CONS DLC ILAN QLLC SDLC X25 NULL XLAN HDLC"
            ::= { ctrlParamEntry 14 }

        ctrlParamKLevel2 OBJECT-TYPE
            SYNTAX      INTEGER (1..31)
            ACCESS      read-write
            STATUS      mandatory
            DESCRIPTION
                "KLevel 2.
                The level 2 window size.
                Applicable: X25, HDLC, CONS, ILAN, XLAN, DLC and NULL
                controller types"
            REFERENCE
                "CONS X25 NULL XLAN ILAN DLC HDLC"
            ::= { ctrlParamEntry 15 }

        ctrlParamKLevel3 OBJECT-TYPE
            SYNTAX      INTEGER (1..127)
            ACCESS      read-write
            STATUS      mandatory
            DESCRIPTION
                "KLevel 3.
                The level 3 window size.
                Applicable: X25, HDLC, CONS, ILAN, XLAN, DLC and NULL
                controller types"
            REFERENCE
                "CONS X25 NULL XFRM XLAN HDLC DLC ILAN"
            ::= { ctrlParamEntry 16 }

        ctrlParamLineGroup OBJECT-TYPE
            SYNTAX      INTEGER (0..15)
            ACCESS      read-write
            STATUS      mandatory
            DESCRIPTION
                "Line Group.
                The line group is used for load sharing. If two links
                have same (non-zero) line group then data may be shared
                between them.
                Applicable: X25, HDLC, CONS, ILAN, XLAN, DLC and NULL
                controller types"
            REFERENCE
                "CONS ILAN X25 NULL XFRM XLAN"
            ::= { ctrlParamEntry 17 }

        ctrlParamLCGN OBJECT-TYPE
            SYNTAX      INTEGER (0..15)
            ACCESS      read-write
            STATUS      mandatory
            DESCRIPTION
                "LCGN.
                The logical channel group number for this link.
                Applicable: X25, HDLC, CONS, ILAN, XLAN, DLC and NULL
                controller types"
            REFERENCE
                "CONS ILAN X25 NULL XFRM XLAN"
            ::= { ctrlParamEntry 18 }

        ctrlParamLCNOffset OBJECT-TYPE
            SYNTAX      INTEGER (0..4095)
            ACCESS      read-write
            STATUS      mandatory
            DESCRIPTION
                "LCN Offset.
                This parameter is used in conjunction with the LCGN. It's
                purpose is to shift the channel range by the appropriate
                offset.
                Applicable: X25, HDLC, CONS, ILAN, XLAN, DLC and NULL
                controller types"
            REFERENCE
                "CONS ILAN X25 NULL XFRM XLAN"
            ::= { ctrlParamEntry 19 }

        ctrlParamAddressGroup OBJECT-TYPE
            SYNTAX      INTEGER (0..15)
            ACCESS      read-write
            STATUS      mandatory
            DESCRIPTION
                "Address Group.
                This parameter is used in conjunction with the address
                group field in the x25 file to provide different addressing
                domains.
                Applicable: X25, HDLC, CONS, ILAN, XLAN, DLC and NULL
                controller types"
            REFERENCE
                "CONS ILAN X25 NULL XFRM XLAN"
            ::= { ctrlParamEntry 20 }

        ctrlParamFrameSequence OBJECT-TYPE
            SYNTAX      INTEGER { extended(15), normal(7) }
            ACCESS      read-write
            STATUS      mandatory
            DESCRIPTION
                "Frame Sequence.
                This parameter determines if normal or extended frame
                sequencing is supported.
                Applicable: X25, SDLC, QLLC, HDLC, CONS, ILAN, XLAN, DLC
                and NULL controller types"
            REFERENCE
                "CONS ILAN QLLC SDLC X25 NULL XFRM XLAN"
            ::= { ctrlParamEntry 21 }

        ctrlParamCallTimeOut OBJECT-TYPE
            SYNTAX      INTEGER (2..200)
            ACCESS      read-write
            STATUS      mandatory
            DESCRIPTION
                "Call Time Out.
                The time in seconds the MegaPAC will wait to receive a call
                accept packet before clearing the call.
                Applicable: X25, TERM, SDLC, QLLC, HDLC, CONS, ILAN,
                XLAN, DLC and NULL controller types"
            REFERENCE
                "CONS ILAN QLLC SDLC TERM X25 NULL XFRM XLAN"
            ::= { ctrlParamEntry 22 }

        ctrlParamErrorThreshold OBJECT-TYPE
            SYNTAX      INTEGER (1..250)
            ACCESS      read-write
            STATUS      mandatory
            DESCRIPTION
                "Error Threshold.
                The number of CRC errors that will be accepted before
                generating an error report.
                Applicable: X25, HDLC, CONS, ILAN, XLAN, DLC
                and NULL controller types"
            REFERENCE
                "CONS ILAN X25 NULL XFRM XLAN HDLC"
            ::= { ctrlParamEntry 23 }

        ctrlParamLoopBarPriority OBJECT-TYPE
            SYNTAX      INTEGER (0..15)
            ACCESS      read-write
            STATUS      mandatory
            DESCRIPTION
                "Loop Bar Priority.
                Prevents calls from looping on the same controller.
                Applicable: X25, HDLC, CONS, XLAN, DLC and NULL
                controller types"
            REFERENCE
                "CONS X25 NULL XFRM XLAN HDLC"
            ::= { ctrlParamEntry 24 }

        ctrlParamExtendedCallMgmt OBJECT-TYPE
            SYNTAX      INTEGER { in(2) , out(3), in-out(4),
                                  v25b(5), v25m(13), none(1),
                                  poll(17), fep(33) }
            ACCESS      read-write
            STATUS      mandatory
            DESCRIPTION
                "Extended Call Management.
                Invokes extended packet processing facilities
                via the MAC file. For PPP, IN and OUT have
                special meaning: IN stands for PAP and OUT for CHAP.
                Applicable: X25, HDLC, CONS, XLAN, DLC and NULL
                controller types. Also for PPP."
            REFERENCE
                "CONS X25 NULL XFRM XLAN HDLC PPP"
            ::= { ctrlParamEntry 25 }

        ctrlParamOptionalTimers OBJECT-TYPE
            SYNTAX      INTEGER { t13(2), t23(3), none(1) }
            ACCESS      read-write
            STATUS      mandatory
            DESCRIPTION
                "Optional Timers.
                Optional level 3 timers for clearing calls when a clear
                confirmation has not been received after a clear request has
                been sent. T13 is used if the controller is set to be a
                logical DCE and the timeout will be 60 seconds. T23 is used
                if the controller is a logical DTE and the timeout is 180
                seconds.
                Applicable: X25, HDLC, CONS, XLAN, DLC and NULL
                controller types"
            REFERENCE
                "CONS X25 NULL XFRM XLAN HDLC"
            ::= { ctrlParamEntry 26 }

        ctrlParamOptionalFlags OBJECT-TYPE
            SYNTAX      INTEGER (0..60)
            ACCESS      read-write
            STATUS      mandatory
            DESCRIPTION
                "Optional Flags.
                This parameter is used to insert extra flags between frames
                to slow down the rate of transmission. It will only take
                effect on controllers with a sub-type of XIO.
                Applicable: X25, HDLC, CONS, XLAN, DLC and NULL
                controller types"
            REFERENCE
                "CONS X25 NULL XFRM XLAN HDLC"
            ::= { ctrlParamEntry 27 }

        ctrlParamTransportLevelType OBJECT-TYPE
            SYNTAX      INTEGER { iso(34), none(1) }
            ACCESS      read-write
            STATUS      mandatory
            DESCRIPTION
                "Transport Level Type.
                Enable the ISO transport facility.
                Applicable: X25, HDLC, CONS, XLAN, DLC and NULL
                controller types"
            REFERENCE
                "CONS X25 NULL XFRM XLAN HDLC"
            ::= { ctrlParamEntry 28 }

        ctrlParamTransportClass OBJECT-TYPE
            SYNTAX      INTEGER { class3(49), class2(33), none(1) }
            ACCESS      read-write
            STATUS      mandatory
            DESCRIPTION
                "Transport Class.
                The type of transport class implemented.
                Applicable: X25, HDLC, CONS, XLAN, DLC and NULL
                controller types"
            REFERENCE
                "CONS X25 NULL XFRM XLAN HDLC"
            ::= { ctrlParamEntry 29 }

        ctrlParamDefaultWindowSize OBJECT-TYPE
            SYNTAX      INTEGER (0..7)
            ACCESS      read-write
            STATUS      mandatory
            DESCRIPTION
                "Default Window Size.
                The initial credit limit to be used on a transport
                session.
                Applicable: X25, HDLC, CONS, XLAN, DLC and NULL
                controller types"
            REFERENCE
                "CONS X25 NULL XFRM XLAN HDLC"
            ::= { ctrlParamEntry 30 }

        ctrlParamDisableFlowControl OBJECT-TYPE
            SYNTAX      INTEGER { yes(2), no(1) }
            ACCESS      read-write
            STATUS      mandatory
            DESCRIPTION
                "Disable Flow Control.
                Enable/disable flow control on a transport class 2 call.
                Applicable: X25, HDLC, CONS, XLAN, DLC and NULL
                controller types"
            REFERENCE
                "CONS X25 NULL XFRM XLAN HDLC"
            ::= { ctrlParamEntry 31 }

        ctrlParamTSAPFormat OBJECT-TYPE
            SYNTAX      INTEGER { text(2), hex(1) }
            ACCESS      read-write
            STATUS      mandatory
            DESCRIPTION
                "TSAP Format.
                Determines how the TSAP's will be treated internally by the
                MegaPAC. If set to text the local and remote TSAP's will be
                converted to form a 4 character internal resource name. If
                set to hex the first two hexadecimal pairs will form the
                resource name.
                Applicable: X25, HDLC, CONS, XLAN, DLC and NULL
                controller types"
            REFERENCE
                "CONS X25 NULL XFRM XLAN HDLC"
            ::= { ctrlParamEntry 32 }

        ctrlParamMaximumTPDUSize OBJECT-TYPE
            SYNTAX      INTEGER { bytes-1024(11), bytes-512(10), bytes-256(9),
                                  bytes128(8),    bytes-128(1) }
            ACCESS      read-write
            STATUS      mandatory
            DESCRIPTION
                "Max. TPDU Size.
                The maximum Transport Protocol Data Unit Size.
                Applicable: X25, HDLC, CONS, ILAN, XLAN and NULL
                controller types"
            REFERENCE
                "CONS X25 NULL XFRM XLAN HDLC ILAN"
            ::= { ctrlParamEntry 33 }

        ctrlParamTTRTime OBJECT-TYPE
            SYNTAX      INTEGER (0..120)
            ACCESS      read-write
            STATUS      mandatory
            DESCRIPTION
                "TTR Timer.
                Time To Resynchronise. Specifies the time delay in seconds
                for the transport class three timer to resync at the initiating
                end.
                Applicable: X25, HDLC, CONS, XLAN and NULL
                controller types"
            REFERENCE
                "CONS X25 NULL XFRM XLAN HDLC"
            ::= { ctrlParamEntry 34 }

        ctrlParamTWRTime OBJECT-TYPE
            SYNTAX      INTEGER (0..120)
            ACCESS      read-write
            STATUS      mandatory
            DESCRIPTION
                "TWR Timer.
                Time to Wait for Resynchronisation. The time delay in seconds
                allowed for the transport class 3 timer at the responding end
                to wait for resynchronisation, before clearing down the
                transport session.
                Applicable: X25, HDLC, CONS, XLAN and NULL
                controller types"
            REFERENCE
                "CONS X25 NULL XFRM XLAN HDLC"
            ::= { ctrlParamEntry 35 }

        ctrlParamDestinationAddress OBJECT-TYPE
            SYNTAX      DisplayString
            ACCESS      read-write
            STATUS      mandatory
            DESCRIPTION
                "Destination Address.
                The physical address of the target device.
                Applicable: CONS, ILAN, DLC and XLAN controller types"
            REFERENCE
                "CONS DLC ILAN XLAN"
            ::= { ctrlParamEntry 36 }

        ctrlParamDSAP OBJECT-TYPE
            SYNTAX      INTEGER (2..254)
            ACCESS      read-write
            STATUS      mandatory
            DESCRIPTION
                "DSAP.
                The Destination Service Access Point.
                Applicable: CONS, ILAN, DLC and XLAN controller types"
            REFERENCE
                "CONS DLC ILAN XLAN"
            ::= { ctrlParamEntry 37 }

        ctrlParamSSAP OBJECT-TYPE
            SYNTAX      INTEGER (2..254)
            ACCESS      read-write
            STATUS      mandatory
            DESCRIPTION
                "SSAP.
                The Source Service Access Point.
                Applicable: CONS, ILAN, DLC and XLAN controller types"
            REFERENCE
                "CONS DLC ILAN XLAN"
            ::= { ctrlParamEntry 38 }

        ctrlParamSDLCOptions OBJECT-TYPE
            SYNTAX      INTEGER { none(1), pu4(33), wait(65),
                                  xid(129), idle(17), wait-xid(193) }
            ACCESS      read-write
            STATUS      mandatory
            DESCRIPTION
                "SDLC Options.
                A range of link level options used for establishing
                IBM connections.
                Applicable: SDLC and QLLC controller types"
            REFERENCE
                "SDLC QLLC"
            ::= { ctrlParamEntry 39 }

        ctrlParamPrimaryStation OBJECT-TYPE
            SYNTAX      INTEGER { yes(2), no(1) }
            ACCESS      read-write
            STATUS      mandatory
            DESCRIPTION
                "Primary Station.
                This parameter determines whether the MegaPAC will operate
                as a HOST primary connection (yes) or a CLUSTER secondary
                connection (no).
                Applicable: SDLC and QLLC controller types"
            REFERENCE
                "SDLC QLLC"
            ::= { ctrlParamEntry 40 }

        ctrlParamIdleDetectTime OBJECT-TYPE
            SYNTAX      INTEGER (0..100)
            ACCESS      read-write
            STATUS      mandatory
            DESCRIPTION
                "Idle Detect Timer.
                This parameter determines the time period in tenths
                of a second before an unacknowleged POLL/RESPONSE frame
                will be retransmitted.
                Applicable: SDLC, QLLC and SRU controller types"
            REFERENCE
                "SDLC QLLC SRU"
            ::= { ctrlParamEntry 41 }

        ctrlParamPollInterval OBJECT-TYPE
            SYNTAX      INTEGER (0..100)
            ACCESS      read-write
            STATUS      mandatory
            DESCRIPTION
                "Poll Interval.
                The time period in tenths of a second between sending
                POLL frames.
                Applicable: SDLC, QLLC, MAP and MULT controller types"
            REFERENCE
                "MAP MULT NFRM VFRM QLLC SDLC XFRM"
            ::= { ctrlParamEntry 42 }

        ctrlParamDuplex OBJECT-TYPE
            SYNTAX      INTEGER { full(1), half(2) }
            ACCESS      read-write
            STATUS      mandatory
            DESCRIPTION
                "Duplex.
                Enables SDLC full duplex operation, half duplex operation
                is reserved for future use.
                Applicable: SDLC and QLLC controller types"
            REFERENCE
                "SDLC QLLC"
            ::= { ctrlParamEntry 43 }

        ctrlParamTransmitDelay OBJECT-TYPE
            SYNTAX      INTEGER (0..20)
            ACCESS      read-write
            STATUS      mandatory
            DESCRIPTION
                "Transmit Delay.
                Determines the time period in tenths of a second between
                the MegaPAC receiving an RR frame with the P-Bit set and the
                MegaPAC issuing an RR response with the F-Bit set.
                Applicable: SDLC and QLLC controller types"
            REFERENCE
                "SDLC QLLC"
            ::= { ctrlParamEntry 44 }

        ctrlParamSlowPollTimer OBJECT-TYPE
            SYNTAX      INTEGER (0..255)
            ACCESS      read-write
            STATUS      mandatory
            DESCRIPTION
                "Slow Poll Timer.
                When the controller has been defined as a primary station
                a slow poll rate can be specified for polling a Cluster
                controller that is down. This is to avoid causing delays to
                working Cluster controllers in a multi-point mode. The value
                is specified in tenths of a second.
                Applicable: SDLC and QLLC controller types"
            REFERENCE
                "SDLC QLLC"
            ::= { ctrlParamEntry 45 }

        ctrlParamMaxCallInterval OBJECT-TYPE
            SYNTAX      INTEGER (0..20)
            ACCESS      read-write
            STATUS      mandatory
            DESCRIPTION
                "Max. Call Interval.
                When controller is configured as a primary station, a call
                request retry interval may be defined, so as to avoid the
                situation where successive call requests are continuously
                generated to the network. The initial call interval is 2
                seconds, this interval is progressively doubled until the
                Maximum Call Interval (defined in minutes) is reached.
                Applicable: SDLC and QLLC controller types"
            REFERENCE
                "SDLC QLLC"
            ::= { ctrlParamEntry 46 }

        ctrlParamMaxCallCycles OBJECT-TYPE
            SYNTAX      INTEGER (0..255)
            ACCESS      read-write
            STATUS      mandatory
            DESCRIPTION
                "Max. Call Cycles.
                This parameter is used in conjunction with the Maximum
                Call Interval parameter. It specifies the maximum number of
                call request cycles that can take effect before call requests
                continue at the Maximum Call Interval parameter setting. Each
                cycle consisting of call requests being initiated at intervals
                in incrementing multiples of two seconds, up to the Maximum Call
                Interval parameter.
                Applicable: SDLC and QLLC controller types"
            REFERENCE
                "SDLC QLLC"
            ::= { ctrlParamEntry 47 }

        ctrlParamGroupPoll OBJECT-TYPE
            SYNTAX      INTEGER (0..255)
            ACCESS      read-write
            STATUS      mandatory
            DESCRIPTION
                "Group Poll.
                Used in SNA applications, where the specified value
                would generate multiple down-stream poll requests.
                Applicable: QLLC, DLC controllers"
            REFERENCE
                "SDLC QLLC"
            ::= { ctrlParamEntry 48 }

        ctrlParamDelayToRTSLow OBJECT-TYPE
            SYNTAX      INTEGER (0..256)
            ACCESS      read-write
            STATUS      mandatory
            DESCRIPTION
                "Delay RTS Low.
                Specifies the number of padding characters to be inserted
                between the end of data transmission and the dropping of the
                RTS signal. Only required for synchronous operation.
                Applicable: TERM controller only"
            REFERENCE
                "TERM"
            ::= { ctrlParamEntry 49 }

        ctrlParamDelayToCTSHigh OBJECT-TYPE
            SYNTAX      INTEGER (0..256)
            ACCESS      read-write
            STATUS      mandatory
            DESCRIPTION
                "Delay CTS High.
                Specifies the number of padding characters to be inserted
                between the dropping of RTS and the raising of CTS. Only
                required for synchronous operation.
                Applicable: TERM controller only"
            REFERENCE
                "TERM"
            ::= { ctrlParamEntry 50 }

        ctrlParamInputSyncDeletion OBJECT-TYPE
            SYNTAX      INTEGER { yes(1), no(2) }
            ACCESS      read-write
            STATUS      mandatory
            DESCRIPTION
                "Input Sync Deletion.
                If set, all SYNC characters will be stripped prior to
                transmission. Only effective in synchronous full duplex mode.
                Applicable: TERM controller only"
            REFERENCE
                "TERM"
            ::= { ctrlParamEntry 51 }

        ctrlParamOutputSyncInsertion OBJECT-TYPE
            SYNTAX      INTEGER (0..255)
            ACCESS      read-write
            STATUS      mandatory
            DESCRIPTION
                "Output Sync Insertion.
                Specifies the number of SYNC characters to be transmitted
                prior to the start of the data block. Only effective in
                synchronous operation.
                Applicable: TERM controller only"
            REFERENCE
                "TERM"
            ::= { ctrlParamEntry 52 }

        ctrlParamDCDFilter OBJECT-TYPE
            SYNTAX      INTEGER (0..20)
            ACCESS      read-write
            STATUS      mandatory
            DESCRIPTION
                "DCD Filter.
                A filter delay specified in tenths of a second which
                prevents unwanted link restarts caused by toggling of DCD
                signal.
                Applicable: TERM controller only"
            REFERENCE
                "TERM"
            ::= { ctrlParamEntry 53 }

        ctrlParamInhibitTimeFill OBJECT-TYPE
            SYNTAX      INTEGER { yes(1), no(2) }
            ACCESS      read-write
            STATUS      mandatory
            DESCRIPTION
                "Inhibit Time Fill
                Allows the insertion of time fill frames to compensate
                for network delays. Effective in synchronous mode only.
                Applicable: TERM controller only"
            REFERENCE
                "TERM"
            ::= { ctrlParamEntry 54 }

        ctrlParamDirectedBroadcasts OBJECT-TYPE
            SYNTAX      INTEGER { yes(1), no(2) }
            ACCESS      read-write
            STATUS      mandatory
            DESCRIPTION
                "Directed Broadcasts.
                ???.
                Applicable: LAN and TLAN Controllers only"
            REFERENCE
                "LAN TLAN"
            ::= { ctrlParamEntry 55 }

        ctrlParamDefaultLocalPrinter OBJECT-TYPE
            SYNTAX      INTEGER (0..128)
            ACCESS      read-write
            STATUS      mandatory
            DESCRIPTION
                "Default Local Printer.
                The number of the channel which is reserved for a Screen
                Print server, a value of (0) disables the Screen Print facility.
                Applicable: Cluster Controllers only"
            REFERENCE
                "CLUS"
            ::= { ctrlParamEntry 56 }

        ctrlParamNewLANInterface OBJECT-TYPE
            SYNTAX      INTEGER { no(2), yes(1) }
            ACCESS      read-write
            STATUS      mandatory
            DESCRIPTION
                "New NFRM Port.
                The controller marks the first position of a controller
                connection to a LAN interface. All other controllers
                defined as NEWPhysicalInterface/ NO will map to the same
                interface defined as NewPhysicalInterface/ YES."
            REFERENCE
                "IP TIP IPX TIPX ESIS DLC LAN TLAN ILAN XLAN"
            ::= { ctrlParamEntry 57 }

        ctrlParamNewSerialInterface OBJECT-TYPE
            SYNTAX      INTEGER { no(1), yes(2) }
            ACCESS      read-write
            STATUS      mandatory
            DESCRIPTION
                "New NFRM Port.
                The controller marks the first position of a controller
                connection to a serial interface. All other controllers
                defined as NEWPhysicalInterface/ NO will map to the same
                interface defined as NewPhysicalInterface/ YES."
            REFERENCE
                "PPP X25 XFRM NFRM VFRM SDLC QLLC HDLC"
            ::= { ctrlParamEntry 58 }

        ctrlParamDlci OBJECT-TYPE
            SYNTAX      INTEGER (1..1022)
            ACCESS      read-write
            STATUS      mandatory
            DESCRIPTION
                "DLCI Number"
            REFERENCE
                " XFRM NFRM VFRM"
            ::= { ctrlParamEntry 59 }

        ctrlParamMode OBJECT-TYPE
            SYNTAX      INTEGER { dte(2), dce(3), dte-dce(4) }
            ACCESS      read-write
            STATUS      mandatory
            DESCRIPTION
                "Status of DLCI.
                Defines a Network to Network Interfaces (NNI) or
                User Network Interface (UNI) implentation.
                Where MegaPAC connects to a Frame Relay switch,
                this parameter just be defined as DTE i.e. a UNI.
                When MegaPAC acts as a Frame Relay switch,
                connecting to DTE using Network side of UNI,
                DCE operation must be specified.
                Otherwise when operating as a switch, connected
                to another switch, NNI i.e. DCE+DTE operation
                must be specified.
                All controllers mapped to the same physical
                interface must be configured the same mode setting."
            REFERENCE
                " XFRM NFRM VFRM"
            ::= { ctrlParamEntry 60 }

        ctrlParamLmi OBJECT-TYPE
            SYNTAX      INTEGER { no(1), yes(2), ansi(129) }
            ACCESS      read-write
            STATUS      mandatory
            DESCRIPTION
                "Type of Local Management Interface (LMI).
                Ansi = ANSI LMI
                yes  = T1.S1 LMI
                no   = LMI disabled."
            REFERENCE
                " XFRM NFRM VFRM"
            ::= { ctrlParamEntry 61 }

        ctrlParamKeepAliveTimer OBJECT-TYPE
            SYNTAX      INTEGER (2..80)
            ACCESS      read-write
            STATUS      mandatory
            DESCRIPTION
                "Only applicable if the LMI is active. Specifies in
                seconds the interval between keep alive messages.
                If this end is a DTE, this is the actual interval
                between Status Requests generated to the DCE (T391).
                If this end is a DCE, then the timer is used simply
                to detect whether connection to the DTE has been lost (T392).
                Note : it is the DTE which is the active partner across
                the LMI interface, in accordance with the LMI specification."
            REFERENCE
                " XFRM NFRM VFRM"
            ::= { ctrlParamEntry 62 }

        ctrlParamFullStatusInterval OBJECT-TYPE
            SYNTAX      INTEGER (0..100)
            ACCESS      read-write
            STATUS      mandatory
            DESCRIPTION
                "Full status enquiry timer (number of times of T391/T392)
                Specifies how often a DTE sends a or a DCE
                expects a Full Status Request message. The number specified
                is the ratio between Status Requests messages, and Full
                Status Request enquiries (N391/N393)."
            REFERENCE
                " XFRM NFRM VFRM"
            ::= { ctrlParamEntry 63 }

        ctrlParamBandwidth OBJECT-TYPE
            SYNTAX      INTEGER (0..32767)
            ACCESS      read-write
            STATUS      mandatory
            DESCRIPTION
               "Rhe sample period used in enforcing the committed
               information rate (CIR). The CIR expressed in terms
               of characters per 1/10 th second. There are two further
               parameters which appear directly after the BANDWIDTH/
               promt which are designed to handle bursty traffic
               (i.e. Bc and Be)"
            REFERENCE
                " XFRM NFRM VFRM"
            ::= { ctrlParamEntry 64 }

        ctrlParamBurstCommit OBJECT-TYPE
            SYNTAX      INTEGER(0..32767)
            ACCESS      read-write
            STATUS      mandatory
            DESCRIPTION
               "Burst Commit, i.e the number of characters
               the remote end is committed to buffering, in our case
               in a 1/10 th of a second period"
            REFERENCE
                " XFRM NFRM VFRM"
            ::= { ctrlParamEntry 65 }

        ctrlParamBurstEligibility OBJECT-TYPE
            SYNTAX      INTEGER(0..32767)
            ACCESS      read-write
            STATUS      mandatory
            DESCRIPTION
               "Burst Eligibility, i.e the DLCI in questions is
               enabled to transmit a burst beyond its committed
               information rate, when enabled to do so by the
               state of the other DLCIs."
            REFERENCE
                " XFRM NFRM VFRM"
            ::= { ctrlParamEntry 66 }

        ctrlParamTimerT3 OBJECT-TYPE
            SYNTAX      INTEGER  (0..255)
            ACCESS      read-write
            STATUS      mandatory
            DESCRIPTION
                "T3.
                Timer to disconnect the link if no flags are received. Specified
                in 0.1 second units.
                Applicable: X25 controller types with XIO subtype"
            ::= { ctrlParamEntry 67 }

        ctrlParamFlowControl OBJECT-TYPE
            SYNTAX      INTEGER
            ACCESS      read-write
            STATUS      mandatory
            DESCRIPTION
                "Enables MULT flow control. On MULT controller type
                 flow control inhibits data on all ressources when a
                 single ressource requires flow control."
            REFERENCE
                " MULT "
            ::= { ctrlParamEntry 68 }

        ctrlParamConfigState OBJECT-TYPE
            SYNTAX      INTEGER (0..128)
            ACCESS      read-write
            STATUS      mandatory
            DESCRIPTION
                "Command to set the state of the controller.
                 Set this parameter to 1 to restart the controller.
                 Set this parameter to 2 to stop the controller.
                 The value read is meaningless."
            ::={ ctrlParamEntry 69 }

        ctrlParamTry OBJECT-TYPE
            SYNTAX      INTEGER (0..99)
            ACCESS      read-write
            STATUS      mandatory
            DESCRIPTION
                "This value used to detect whether connection to the
                other end has been lost. The number specified
                is the ratio between Status Requests messages, and Full
                Status Request enquiries, above which an LMI error
                is recognized (N392)."
            REFERENCE
                "XFRM NFRM VFRM"
            ::={ ctrlParamEntry 70 }

-- The Channel Group (Statistics)
-- The Channel Group described below forms a direct association with
-- a MegaPAC controller, and form the principle routing interface
-- by which data movement is internally switched between a source
-- (i.e. inbound connection) and destination resource (i.e. out-
-- bound connection).

        chanNumberConfigured OBJECT-TYPE
            SYNTAX      INTEGER
            ACCESS      read-only
            STATUS      mandatory
            DESCRIPTION
                "Number of channels.
                The number of channels configured."
            ::= { channel 1 }

        chanStatTable OBJECT-TYPE
            SYNTAX      SEQUENCE OF ChanStatEntry
            ACCESS      not-accessible
            STATUS      mandatory
            DESCRIPTION
                "A table of channels associated with a controller."
            ::= { channel 2 }

        chanStatEntry OBJECT-TYPE
            SYNTAX      ChanStatEntry
            ACCESS      not-accessible
            STATUS      mandatory
            DESCRIPTION
                "An individual channel entry."
            INDEX       { chanStatIndex }
            ::= { chanStatTable 1 }

        ChanStatEntry ::= SEQUENCE { chanStatIndex
                                     INTEGER,
                                     chanStatName
                                     DisplayString,
                                     chanStatControllerIndex
                                     INTEGER,
                                     chanStatNameCtrlName
                                     DisplayString,
                                     chanStatConnectedToChannelIndex
                                     INTEGER,
                                     chanStatState
                                     INTEGER,
                                     chanStatSessionStatus
                                     INTEGER,
                                     chanStatEIA
                                     INTEGER,
                                     chanStatTotalFramesIn
                                     Counter,
                                     chanStatTotalFramesOut
                                     Counter,
                                     chanStatTotalCharsIn
                                     Counter,
                                     chanStatTotalCharsOut
                                     Counter,
                                     chanStatTxWindow
                                     INTEGER,
                                     chanStatRxWindow
                                     INTEGER,
                                     chanStatTxSize
                                     INTEGER,
                                     chanStatRxSize
                                     INTEGER,
                                     chanStatCause
                                     INTEGER,
                                     chanStatDiagnostic
                                     INTEGER,
                                     chanStatResetCause
                                     INTEGER,
                                     chanStatResetDiagnostic
                                     INTEGER,
                                     chanStatResetCauseReceived
                                     INTEGER,
                                     chanStatResetDiagReceived
                                     INTEGER,
                                     chanStatLevel3State
                                     INTEGER,
                                     chanStatCallPriority
                                     INTEGER,
                                     chanStatResourcePriority
                                     INTEGER,
                                     chanStatPadEnable
                                     INTEGER,
                                     chanStatPortMatch
                                     INTEGER,
                                     chanStatPrimaryStation
                                     INTEGER,
                                     chanStatSDLCState
                                     INTEGER,
                                     chanStatQLLCState
                                     INTEGER,
                                     chanStatSDLCTransmitState
                                     INTEGER,
                                     chanStatPolls
                                     INTEGER,
                                     chanStatStationAddress
                                     INTEGER,
                                     chanStatXIDIdentification
                                     DisplayString,
                                     chanStatTries
                                     INTEGER,
                                     chanStatWindow
                                     INTEGER,
                                     chanStatLUActive
                                     INTEGER,
                                     chanStatBindActive
                                     INTEGER,
                                     chanStatLUType
                                     INTEGER,
                                     chanStatBreaksReceived
                                     Counter,
                                     chanStatFramingErrors
                                     Counter,
                                     chanStatInputOverruns
                                     Counter,
                                     chanStatParityErrors
                                     Counter,
                                     chanStatTerminalType
                                     INTEGER,
                                     chanStatCircuitType
                                     INTEGER,
                                     chanStatOptions
                                     INTEGER,
                                     chanStatBuffers
                                     INTEGER,
                                     chanStatDiscMode
                                     INTEGER,
                                     chanStatMenuNumber
                                     INTEGER,
                                     chanStatHelpNumber
                                     INTEGER,
                                     chanStatNewsNumber
                                     INTEGER,
                                     chanStatPadRecall
                                     INTEGER,
                                     chanStatEcho
                                     INTEGER,
                                     chanStatDataForwarding
                                     INTEGER,
                                     chanStatDelay
                                     INTEGER,
                                     chanStatDRI
                                     INTEGER,
                                     chanStatPadSignals
                                     INTEGER,
                                     chanStatBreak
                                     INTEGER,
                                     chanStatPadding
                                     INTEGER,
                                     chanStatFold
                                     INTEGER,
                                     chanStatDRO
                                     INTEGER,
                                     chanStatLFI
                                     INTEGER,
                                     chanStatLFPad
                                     INTEGER,
                                     chanStatEdit
                                     INTEGER,
                                     chanStatCharDel
                                     INTEGER,
                                     chanStatBufferDel
                                     INTEGER,
                                     chanStatDisp
                                     INTEGER,
                                     chanStatEditServiceSignals
                                     INTEGER,
                                     chanStatEchoMask
                                     INTEGER,
                                     chanStatParityTreatment
                                     INTEGER,
                                     chanStatPageWait
                                     INTEGER,
                                     chanStatForce
                                     INTEGER,
                                     chanStatBreakChar
                                     INTEGER,
                                     chanStatNetworkParity
                                     INTEGER,
                                     chanStatEscapeDelay
                                     INTEGER,
                                     chanStatTransportLevelState
                                     INTEGER,
                                     chanStatDestTsap
                                     DisplayString,
                                     chanStatLinkState
                                     INTEGER,
                                     chanStatProtocolState
                                     INTEGER,
                                     chanStatProtocol
                                     INTEGER,
                                     chanStatIdentity
                                     INTEGER,
                                     chanStatFrameRelayWait
                                     INTEGER        }

        chanStatIndex OBJECT-TYPE
            SYNTAX      INTEGER
            ACCESS      read-only
            STATUS      mandatory
            DESCRIPTION
                "Index.
                The position of this channel in the controller channel
                Table.
                Applicable controllers: NMS, CONS, V25B, SRU, IP, SDLC,
                MULT, CLUS, LAN, TERM, ILAN, XLAN, QLLC, HDLC,
                X25, MUX, MAP, DLC, TLAN, NFRM, XFRM, PPP, ESIS,
                IPX, TIPX, TIP, ROUT and SNMP"
            REFERENCE
                "NMS CONS V25B SRU IP SDLC MULT CLUS LAN
                TERM ILAN XLAN QLLC HDLC X25 MAP SNMP
                DLC TLAN NFRM XFRM PPP ESIS IPX TIPX TIP
                ROUT"
            ::={ chanStatEntry 1 }

        chanStatName OBJECT-TYPE
            SYNTAX      DisplayString (SIZE(4))
            ACCESS      read-only
            STATUS      mandatory
            DESCRIPTION
                "Name.
                A user defined name for routing calls to this channel.
                Applicable controllers: NMS, CONS, V25B, SRU, IP, SDLC,
                MULT, CLUS, LAN, TERM, ILAN, XLAN, QLLC, HDLC,
                X25, MUX, MAP, DLC, TLAN, NFRM, XFRM, PPP, ESIS,
                IPX, TIPX, TIP, ROUT and SNMP"
            REFERENCE
                "NMS CONS V25B SRU IP SDLC MULT CLUS LAN
                TERM ILAN XLAN QLLC HDLC X25 MAP SNMP
                DLC TLAN NFRM XFRM PPP ESIS IPX TIPX TIP
                ROUT"
            ::={ chanStatEntry 2 }

        chanStatControllerIndex OBJECT-TYPE
            SYNTAX      INTEGER
            ACCESS      read-only
            STATUS      mandatory
            DESCRIPTION
                "Controller Index.
                The index to the controller that this channel operates within.
                Applicable controllers: NMS, CONS, V25B, SRU, IP, SDLC,
                MULT, CLUS, LAN, TERM, ILAN, XLAN, QLLC, HDLC,
                X25, MUX, MAP, DLC, TLAN, NFRM, XFRM, PPP, ESIS,
                IPX, TIPX, TIP, ROUT and SNMP"
            REFERENCE
                "NMS CONS V25B SRU IP SDLC MULT CLUS LAN
                TERM ILAN XLAN QLLC HDLC X25 MAP SNMP
                DLC TLAN NFRM XFRM PPP ESIS IPX TIPX TIP
                ROUT"
            ::={ chanStatEntry 3 }

        chanStatNameCtrlName OBJECT-TYPE
            SYNTAX      DisplayString (SIZE(4))
            ACCESS      read-only
            STATUS      mandatory
            DESCRIPTION
                "Controller Name.
                The controller NAME supporting this channel
                Applicable controllers: NMS, CONS, V25B, SRU, IP, SDLC,
                MULT, CLUS, LAN, TERM, ILAN, XLAN, QLLC, HDLC,
                X25, MUX, MAP, DLC, TLAN, NFRM, XFRM, PPP, ESIS,
                IPX, TIPX, TIP,         ROUT and SNMP"
            REFERENCE
                "NMS CONS V25B SRU IP SDLC MULT CLUS LAN
                TERM ILAN XLAN QLLC HDLC X25 MAP SNMP
                DLC TLAN NFRM XFRM PPP ESIS IPX TIPX TIP
                ROUT"
            ::={ chanStatEntry 4 }

        chanStatConnectedToChannelIndex OBJECT-TYPE
            SYNTAX      INTEGER
            ACCESS      read-only
            STATUS      mandatory
            DESCRIPTION
                "Connected to Index.
                The INDEX of the controller that this channel is
                connected to.
                Applicable controllers: NMS, CONS, V25B, SRU, IP, SDLC,
                MULT, CLUS, LAN, TERM, ILAN, XLAN, QLLC, HDLC,
                X25, MUX, MAP, DLC, TLAN, NFRM, XFRM, PPP, ESIS,
                IPX, TIPX, TIP,         ROUT and SNMP"
            REFERENCE
                "NMS CONS V25B SRU IP SDLC MULT CLUS LAN
                TERM ILAN XLAN QLLC HDLC X25 MAP SNMP
                DLC TLAN NFRM VFRM XFRM PPP ESIS IPX TIPX TIP
                ROUT"
            ::={ chanStatEntry  5 }

        chanStatState OBJECT-TYPE
            SYNTAX      INTEGER { disc(1), emul(73), emul(69),
                                  post(57), busy(49), call(45),
                                  data(41), wake(37), setup(33),
                                  rout(29), addr(25), name(21),
                                  look(17), serv(13), pass(9),
                                  rung(5) }
            ACCESS      read-only
            STATUS      mandatory
            DESCRIPTION
                "State.
                The current Status of the channel, the status may be
                one or a combination of the following:
                Applicable controllers: NMS, CONS, V25B, SRU, IP, SDLC,
                MULT, CLUS, LAN, TERM, ILAN, XLAN, QLLC, HDLC,
                X25, MUX, MAP, DLC, TLAN, NFRM VFRM, XFRM, PPP, ESIS,
                IPX, TIPX, TIP,         ROUT and SNMP"
            REFERENCE
                "NMS CONS V25B SRU IP SDLC MULT CLUS LAN
                TERM ILAN XLAN QLLC HDLC X25 MAP SNMP
                DLC TLAN NFRM VFRM XFRM PPP ESIS IPX TIPX TIP
                ROUT"
            ::={ chanStatEntry 6 }

        chanStatSessionStatus OBJECT-TYPE
            SYNTAX      INTEGER { none(1),  tran(2),  dri(3),
                                  dro(5),   call(9),  pad(17),
                                  queu(33), stat(65), disc(129) }
            ACCESS      read-only
            STATUS      mandatory
            DESCRIPTION
                "Session Status.
                The Status of the channel during a call session, the
                status may be one or a combination of the following:
                State   Description
                CALL    Call Originator.
                DRI     Flow controlling input.
                DRO     Flow controlling on output.
                TRAN    Presentation service not involved in call set-up.
                QUEU    Queued to selected resource.
                STAT    Awaiting queue status information.
                PAD     In PAD Recall mode.
                DISC    Data buffers draining before clearing call.
                Applicable controllers: NMS, CONS, V25B, SRU, IP, SDLC,
                MULT, CLUS, LAN, TERM, ILAN, XLAN, QLLC, HDLC,
                X25, MUX, MAP, DLC, TLAN, NFRM VFRM, XFRM, PPP, ESIS,
                IPX, TIPX, TIP,         ROUT and SNMP"
            REFERENCE
                "NMS CONS V25B SRU IP SDLC MULT CLUS LAN
                TERM ILAN XLAN QLLC HDLC X25 MAP SNMP
                DLC TLAN NFRM VFRM XFRM PPP ESIS IPX TIPX TIP
                ROUT"
            ::={ chanStatEntry  7 }

        chanStatEIA OBJECT-TYPE
            SYNTAX      INTEGER { none(1),  dcd(2),     ring(3),
                                  x28(5),   rej(9),     iso(17),
                                  tcal(33), closed(65), down(129) }
            ACCESS      read-only
            STATUS      mandatory
            DESCRIPTION
                "EIA
                Displays the status of the V24/V28 signals on term or
                muxport links, or call status on X.25 links. The down
                state indicates that level 2 is inactive.
                Applicable controllers: NMS, CONS, V25B, SRU, IP, SDLC,
                MULT, CLUS, LAN, TERM, ILAN, XLAN, QLLC, HDLC,
                X25, MUX, MAP, DLC, TLAN, NFRM VFRM, XFRM, PPP, ESIS,
                IPX, TIPX, TIP,         ROUT and SNMP"
            REFERENCE
                "NMS CONS V25B SRU IP SDLC MULT CLUS LAN
                TERM ILAN XLAN QLLC HDLC X25 MAP ROUT
                DLC TLAN NFRM VFRM XFRM PPP ESIS IPX TIPX TIP
                SNMP"
            ::={ chanStatEntry  8 }

        chanStatTotalFramesIn OBJECT-TYPE
            SYNTAX      Counter
            ACCESS      read-only
            STATUS      mandatory
            DESCRIPTION
                "Total Frames In.
                The total number of frames received on this channel
                since it entered Data State.
                Applicable controllers:  CONS,  IP, SDLC, TIP, LAN,
                TIPX, ILAN, XLAN, QLLC, HDLC, X25, DLC, TLAN,
                NFRM VFRM, XFRM, PPP, ESIS, IPX and ROUT"
            REFERENCE
                "CONS IP SDLC LAN ILAN XLAN QLLC HDLC X25
                ROUT DLC TLAN NFRM VFRM XFRM PPP ESIS IPX TIPX
                TIP"
            ::={ chanStatEntry  9 }

        chanStatTotalFramesOut OBJECT-TYPE
            SYNTAX      Counter
            ACCESS      read-only
            STATUS      mandatory
            DESCRIPTION
                "Total Frames out.
                The total number of frames transmitted on this channel
                since it entered Data State.
                Applicable controllers:  CONS,  IP, SDLC, TIP, LAN,
                TIPX, ILAN, XLAN, QLLC, HDLC, X25, DLC, TLAN,
                NFRM VFRM, XFRM, PPP, ESIS, IPX and ROUT"
            REFERENCE
                "CONS IP SDLC LAN ILAN XLAN QLLC HDLC X25
                ROUT DLC TLAN NFRM VFRM XFRM PPP ESIS IPX TIPX
                TIP"
            ::={ chanStatEntry  10 }

        chanStatTotalCharsIn OBJECT-TYPE
            SYNTAX      Counter
            ACCESS      read-only
            STATUS      mandatory
            DESCRIPTION
                "Total Characters In.
                The total number of characters received on this channel
                since it entered Data State.
                Applicable controllers:  CONS,  IP, SDLC, TIP, LAN,
                TIPX, ILAN, XLAN, QLLC, HDLC, X25, DLC, TLAN,
                NFRM VFRM, XFRM, PPP, ESIS, IPX and ROUT"
            REFERENCE
                "CONS IP SDLC LAN ILAN XLAN QLLC HDLC X25
                ROUT DLC TLAN NFRM VFRM XFRM PPP ESIS IPX TIPX
                TIP"
            ::={ chanStatEntry  11 }

        chanStatTotalCharsOut OBJECT-TYPE
            SYNTAX      Counter
            ACCESS      read-only
            STATUS      mandatory
            DESCRIPTION
                "Total Characters Out.
                The total number of characters transmitted on this
                channel since it entered Data State.
                Applicable controllers:  CONS,  IP, SDLC, TIP, LAN,
                TIPX, ILAN, XLAN, QLLC, HDLC, X25, DLC, TLAN,
                NFRM VFRM, XFRM, PPP, ESIS, IPX and ROUT"
            REFERENCE
                "CONS IP SDLC LAN ILAN XLAN QLLC HDLC X25
                ROUT DLC TLAN NFRM VFRM XFRM PPP ESIS IPX TIPX
                TIP"
            ::={ chanStatEntry  12 }

        chanStatTxWindow OBJECT-TYPE
            SYNTAX      INTEGER
            ACCESS      read-only
            STATUS      mandatory
            DESCRIPTION
                "Tx Window.
                The Level 3 Transmit Window size.
                Applicable controllers:  CONS, ILAN, XLAN,  HDLC, X25,
                NFRM VFRM and XFRM"
            REFERENCE
                "CONS ILAN XLAN HDLC X25 NFRM VFRM XFRM "
            ::={ chanStatEntry  13 }

        chanStatRxWindow OBJECT-TYPE
            SYNTAX      INTEGER
            ACCESS      read-only
            STATUS      mandatory
            DESCRIPTION
                "Rx Window.
                The Level 3 Receive Window size.
                Applicable controllers:  CONS, ILAN, XLAN,  HDLC, X25,
                NFRM VFRM and XFRM"
            REFERENCE
                "CONS ILAN XLAN HDLC X25 NFRM VFRM XFRM "
            ::={ chanStatEntry  14 }

        chanStatTxSize OBJECT-TYPE
            SYNTAX      INTEGER
            ACCESS      read-only
            STATUS      mandatory
            DESCRIPTION
                "Tx Size.
                The maximum size for outgoing packets.
                Applicable controllers:  CONS, ILAN, XLAN,  HDLC, X25,
                NFRM VFRM and XFRM"
            REFERENCE
                "CONS ILAN XLAN HDLC X25 NFRM VFRM XFRM "
            ::={ chanStatEntry  15 }

        chanStatRxSize OBJECT-TYPE
            SYNTAX      INTEGER
            ACCESS      read-only
            STATUS      mandatory
            DESCRIPTION
                "Rx Size.
                The maximum acceptable size for incoming packets.
                Applicable controllers:  CONS, ILAN, XLAN,  HDLC, X25,
                NFRM VFRM and XFRM"
            REFERENCE
                "CONS ILAN XLAN HDLC X25 NFRM VFRM XFRM "
            ::={ chanStatEntry  16 }

        chanStatCause OBJECT-TYPE
            SYNTAX      INTEGER
            ACCESS      read-only
            STATUS      mandatory
            DESCRIPTION
                "Cause.
                The value of the cause code in the last Clear Packet
                received or transmitted (decimal).
                Applicable controllers:  CONS, QLLC, XLAN,  HDLC, X25,
                NFRM VFRM, SDLC, DLC and XFRM"
            REFERENCE
                "CONS QLLC XLAN HDLC X25 NFRM VFRM XFRM SDLC DLC"
            ::={ chanStatEntry  17 }

        chanStatDiagnostic OBJECT-TYPE
            SYNTAX      INTEGER
            ACCESS      read-only
            STATUS      mandatory
            DESCRIPTION
                "Diagnostic.
                The value of the diagnostic code in the last Clear
                Packet received or transmitted (decimal).
                Applicable controllers:  CONS, QLLC, XLAN,  HDLC, X25,
                NFRM VFRM, SDLC, DLC and XFRM"
            REFERENCE
                "CONS QLLC XLAN HDLC X25 NFRM VFRM XFRM SDLC DLC"
            ::={ chanStatEntry  18 }

        chanStatResetCause OBJECT-TYPE
            SYNTAX      INTEGER
            ACCESS      read-only
            STATUS      mandatory
            DESCRIPTION
                "Reset Cause.
                The value of the last reset code in the last RESET
                packet transmitted.
                Applicable controllers:  CONS, QLLC, XLAN,  HDLC, X25,
                NFRM VFRM, SDLC, DLC and XFRM"
            REFERENCE
                "CONS QLLC XLAN HDLC X25 NFRM VFRM XFRM SDLC DLC"
            ::={ chanStatEntry  19 }

        chanStatResetDiagnostic OBJECT-TYPE
            SYNTAX      INTEGER
            ACCESS      read-only
            STATUS      mandatory
            DESCRIPTION
                "Reset Diagnostic.
                The value of the last diagnostic code in the last RESET
                packet transmitted.
                Applicable controllers:  CONS, QLLC, XLAN,  HDLC, X25,
                NFRM VFRM, SDLC, DLC and XFRM"
            REFERENCE
                "CONS QLLC XLAN HDLC X25 NFRM VFRM XFRM SDLC DLC"
            ::={ chanStatEntry  20 }

        chanStatResetCauseReceived OBJECT-TYPE
            SYNTAX      INTEGER
            ACCESS      read-only
            STATUS      mandatory
            DESCRIPTION
                "Reset Cause Received.
                The value of the last reset code in the last RESET
                packet received.
                Applicable controllers:  CONS, QLLC, XLAN,  HDLC, X25,
                NFRM VFRM, SDLC, DLC and XFRM"
            REFERENCE
                "CONS QLLC XLAN HDLC X25 NFRM VFRM XFRM SDLC DLC"
            ::={ chanStatEntry  21 }

        chanStatResetDiagReceived OBJECT-TYPE
            SYNTAX      INTEGER
            ACCESS      read-only
            STATUS      mandatory
            DESCRIPTION
                "Reset Diagnostic Received.
                The value of the last diagnostic code in the last RESET
                packet received.
                Applicable controllers:  CONS, QLLC, XLAN,  HDLC, X25,
                NFRM VFRM, SDLC, DLC and XFRM"
            REFERENCE
                "CONS QLLC XLAN HDLC X25 NFRM VFRM XFRM SDLC DLC"
            ::={ chanStatEntry  22 }

        chanStatLevel3State OBJECT-TYPE
            SYNTAX      INTEGER { disc(1), rest(3), call(5),
                                  data(7), cls(9),  clr(11),
                                  reset(13) }
            ACCESS      read-only
            STATUS      mandatory
            DESCRIPTION
                "Level 3 State.
                The level 3 status of the channel.
                Applicable controllers:  CONS, XLAN,  HDLC, X25, NFRM VFRM
                and XFRM"
            REFERENCE
                "CONS XLAN HDLC X25 NFRM VFRM XFRM"
            ::={ chanStatEntry  23 }

        chanStatCallPriority OBJECT-TYPE
            SYNTAX      INTEGER
            ACCESS      read-only
            STATUS      mandatory
            DESCRIPTION
                "Call Priority.
                Call and Resource priorities are used primarily for
                providing alternate routing. For a call to succeed the
                Call Priority on the incoming channel must be greater
                than or equal to the Resource Priority on the outgoing
                channel.
                Applicable controllers:  CONS, XLAN,  HDLC, X25, NFRM VFRM
                and XFRM"
            REFERENCE
                "CONS XLAN HDLC X25 NFRM VFRM XFRM"
            ::={ chanStatEntry  24 }

        chanStatResourcePriority OBJECT-TYPE
            SYNTAX      INTEGER
            ACCESS      read-only
            STATUS      mandatory
            DESCRIPTION
                "Resource Priority
                See chanCallPriority above.
                Applicable controllers:  CONS, XLAN,  HDLC, X25, NFRM VFRM
                and XFRM"
            REFERENCE
                "CONS XLAN HDLC X25 NFRM VFRM XFRM"
            ::={ chanStatEntry  25 }

        chanStatPadEnable OBJECT-TYPE
            SYNTAX      INTEGER { disabled(1), enabled(2), rev(3),
                                  prof(5),     mask(17),   x28(33) }
            ACCESS      read-only
            STATUS      mandatory
            DESCRIPTION
                "PAD Enable.
                The value of this statistic reflects the setting as
                configured on the channel.
                Applicable controllers:  CONS, XLAN,  HDLC, X25, NFRM VFRM
                and XFRM"
            REFERENCE
                "CONS XLAN HDLC X25 NFRM VFRM XFRM"
            ::={ chanStatEntry  26 }

        chanStatPortMatch OBJECT-TYPE
            SYNTAX      INTEGER { no(1),     srce(2),
                                  dest(129), wild(137) }
            ACCESS      read-only
            STATUS      mandatory
            DESCRIPTION
                "Port Match.
                The TCP port that is connected
                Applicable controllers: IP, LAN, TLAN, ESIS, IPX, TIPX,
                and TIP"
            REFERENCE
                "IP LAN TLAN ESIS IPX TIPX TIP"
            ::={ chanStatEntry  27 }

        chanStatPrimaryStation OBJECT-TYPE
            SYNTAX      INTEGER { no(1), yes(2) }
            ACCESS      read-only
            STATUS      mandatory
            DESCRIPTION
                "Primary Station.
                Determines whether the MegaPAC port is functioning as a
                Primary or Secondary SDLC station.
                Applicable controllers: QLLC, SDLC and DLC"
            REFERENCE
                "SDLC QLLC DLC"
            ::={ chanStatEntry  28 }

        chanStatSDLCState OBJECT-TYPE
            SYNTAX      INTEGER { idle(1), snrm(3), active(5),
                                  poll(7), disc(9) }
            ACCESS      read-only
            STATUS      mandatory
            DESCRIPTION
                "SDLC State.
                The State of the SDLC connection, may be one of the
                following:
                State           Description
                ACTIVE                  The SNRM and UA commands have been sent
                                        successfully. If primary, the P-Bit has
                                        not been sent (i.e. has not been
                                        polled). If secondary, the P-Bit has
                                        not been received (has got F-Bit and
                                        not been polled again).
                DISC                    Primary station only. Either a 'STOP'
                                        command has been issued for the port,
                                        or a QDISC command has been received
                                        from the network.
                                        The MegaPAC will be sending an SDLC
                                        DISC command with the P-Bit set.
                POLL                    If primary, the MegaPAC has sent a
                                        frame with the P-Bit (has polled). If
                                        secondary, the MegaPAC has received the
                                        P-Bit (has been polled).
                SNRM                    Only for primary stations. The MegaPAC
                                        has sent a SNRM, but has not received a
                                        UA.
                Applicable controllers: QLLC, SDLC and DLC"
            REFERENCE
                "SDLC QLLC DLC"
            ::={ chanStatEntry  29 }

        chanStatQLLCState OBJECT-TYPE
            SYNTAX      INTEGER { inop(1),  clsd(5),  openi(9),
                                  frmr(13), clsi(17), open(21) }
            ACCESS      read-only
            STATUS      mandatory
            DESCRIPTION
                "QLLC State.
                The State of the QLLC connection, may be one of the
                following:
                State                   Description
                CLSD                    The MegaPAC has received a QDISC and
                                        sent a QUA on the network. This sets
                                        the DISC state on the SDLC port.
                CLSI                    The MegaPAC has sent a QDISC and is
                                        waiting for a QUA.
                FRMR                    The MegaPAC has received a QFRMR from
                                        the network.
                INOP                    The SVC is down.
                OPEN                    The VC is running. QSM and QUA have
                                        been sent and received.
                OPNI                    The MegaPAC has sent a QSM and is
                                        awaiting a QUA.
                Applicable controllers: QLLC, SDLC and DLC"
            REFERENCE
                "SDLC QLLC DLC"
            ::={ chanStatEntry  30 }

        chanStatSDLCTransmitState OBJECT-TYPE
            SYNTAX      INTEGER { idle(1), norm(3), rtry(7), rnr(11) }
            ACCESS      read-only
            STATUS      mandatory
            DESCRIPTION
                "SDLC Transmit State.
                May be one of the following:
                State                   Description
                NORM                    The MegaPAC is allowed to transmit
                                        data.
                NULL                    The MegaPAC is not allowed to transmit
                                        data.
                RNR                     The MegaPAC has received an RNR.
                RTRY                    The MegaPAC is in the retransmission
                                        state.
                Applicable controllers: QLLC, SDLC and DLC"
            REFERENCE
                "SDLC QLLC DLC"
            ::={ chanStatEntry  31 }

        chanStatPolls OBJECT-TYPE
            SYNTAX      INTEGER
            ACCESS      read-only
            STATUS      mandatory
            DESCRIPTION
                "Polls.
                The quantity of polls that have occured since the link
                was established
                Applicable controllers: QLLC, SDLC and DLC"
            REFERENCE
                "SDLC QLLC DLC"
            ::={ chanStatEntry  32 }

        chanStatStationAddress OBJECT-TYPE
            SYNTAX      INTEGER
            ACCESS      read-only
            STATUS      mandatory
            DESCRIPTION
                "Station Address.
                The IBM PU's address that this channel is using
                Applicable controllers: QLLC, SDLC and DLC"
            REFERENCE
                "SDLC QLLC DLC"
            ::={ chanStatEntry  33 }

        chanStatXIDIdentification OBJECT-TYPE
            SYNTAX      DisplayString
            ACCESS      read-only
            STATUS      mandatory
            DESCRIPTION
                "XID Identification.
                This field contains the first 64 bytes of the XID
                that has been used.
                Applicable controllers: QLLC, SDLC and DLC"
            REFERENCE
                "SDLC QLLC DLC"
            ::={ chanStatEntry  34 }

        chanStatTries OBJECT-TYPE
            SYNTAX      INTEGER
            ACCESS      read-only
            STATUS      mandatory
            DESCRIPTION
                "Tries.
                The number of times the current command has been
                transmitted.
                Applicable controllers: QLLC, SDLC, PPP and DLC"
            REFERENCE
                "SDLC QLLC DLC PPP"
            ::={ chanStatEntry  35 }

        chanStatWindow OBJECT-TYPE
            SYNTAX      INTEGER
            ACCESS      read-only
            STATUS      mandatory
            DESCRIPTION
                "KLevel 2.
                The level 2 window size.
                Applicable controllers: QLLC, SDLC and DLC"
            REFERENCE
                "SDLC QLLC DLC"
            ::={ chanStatEntry  36 }

        chanStatLUActive OBJECT-TYPE
            SYNTAX      INTEGER { no(1), yes(2) }
            ACCESS      read-only
            STATUS      mandatory
            DESCRIPTION
                "LU Active.
                If set to YES then the MegaPAC Logical Unit has
                responded positively to an ACTLU command. If set to NO
                the MegaPAC has either not received or has responded
                negatively to an ACTLU command.
                Applicable controllers: CLUS only"
            REFERENCE
                "CLUS"
            ::={ chanStatEntry  37 }

        chanStatBindActive OBJECT-TYPE
            SYNTAX      INTEGER { no(1), yes(2) }
            ACCESS      read-only
            STATUS      mandatory
            DESCRIPTION
                "Bind Active.
                If set to YES then the MegaPAC Logical Unit has
                responded positively to a BIND command. If set to NO the
                MegaPAC has either not received or has responded
                negatively to a BIND command.
                Applicable controllers: CLUS only"
            REFERENCE
                "CLUS"
            ::={ chanStatEntry  38 }

        chanStatLUType OBJECT-TYPE
            SYNTAX      INTEGER (0..3)
            ACCESS      read-only
            STATUS      mandatory
            DESCRIPTION
                "LU Type.
                The Session type taken from the BIND command. It
                may be one of the following:
                Session Type    Description
                0               User defined applications.
                1               Printer.
                2               Full Screen 3270 applications.
                3               Older type printers.
                Applicable controllers: CLUS only"
            REFERENCE
                "CLUS"
            ::={ chanStatEntry  39 }

        chanStatBreaksReceived OBJECT-TYPE
            SYNTAX      Counter
            ACCESS      read-only
            STATUS      mandatory
            DESCRIPTION
                "Breaks Rx
                The number of Break characters received from the
                terminal.
                Applicable controllers: TERM only"
            REFERENCE
                "TERM"
            ::={ chanStatEntry  40 }

        chanStatFramingErrors OBJECT-TYPE
            SYNTAX      Counter
            ACCESS      read-only
            STATUS      mandatory
            DESCRIPTION
                "Framing Errors.
                The number of characters received with no stop bit
                appended. The MegaPAC substitutes a '#' character in
                place of each framing error.
                Applicable controllers: TERM only"
            REFERENCE
                "TERM"
            ::={ chanStatEntry  41 }

        chanStatInputOverruns OBJECT-TYPE
            SYNTAX      Counter
            ACCESS      read-only
            STATUS      mandatory
            DESCRIPTION
                "Input Overruns.
                The number of times that data has been discarded due
                to a lack of receive buffers.
                Applicable controllers: TERM only"
            REFERENCE
                "TERM"
            ::={ chanStatEntry  42 }

        chanStatParityErrors OBJECT-TYPE
            SYNTAX      Counter
            ACCESS      read-only
            STATUS      mandatory
            DESCRIPTION
                "TParity Errors.
                he number of parity errors received on this
                channel.
                Applicable controllers: TERM only"
            REFERENCE
                "TERM"
            ::={ chanStatEntry  43 }

        chanStatTerminalType OBJECT-TYPE
          SYNTAX      INTEGER { asyn(2), sync(3), hp(225),
                                x28(209), x28f(999), ansi(177),
                                ext-ansi(161), vpad(129), mtrm(113),
                                slip(97), buf(81), tpad(65), vt200(41) }
          ACCESS      read-only
          STATUS      mandatory
          DESCRIPTION
              "Terminal Type.
              The type of emulation to be applied to the TERM
              controller, it may be one or more of the following:
              Type            comment
              ASYN    ASCII data support
              SYNC    Bi-sync data support
              MINI            Minitel terminal support
              HP      H.P ENQ / ACK async protocol support
              X28     X28 command syntax (English)
              X28F    X28 command syntax (French)
              ANSI    Async ASCII Terminal support
              VPAD    Viewdata PAD Emulation support
              MTRM    MegaTerm PC Emulation support
              BUF     Used for Buffer PVC call set-ups
              TPAD    ACAB30 transaction card terminal support
              VT22    Async VT220Terminal support"
          REFERENCE
              "TERM"
          ::={ chanStatEntry 44 }

     chanStatCircuitType OBJECT-TYPE
          SYNTAX      INTEGER { none(1), osi(5), queu(4),
                                call(2), svc(33),
                                out(17), stat(65),call-stat(66),
                                call-pvc(10), call-pvc-stat(74),
                                out-stat(81),out-pvc(25), out-pvc-stat(89),
                                svc-stat(97) }
          ACCESS      read-only
          STATUS      mandatory
          DESCRIPTION
              "Circuit Type.
              The type of circuit used on this channel, it may be
              one or more of the following:"
          REFERENCE
              "TERM"
          ::={ chanStatEntry  45 }

        chanStatOptions OBJECT-TYPE
            SYNTAX      INTEGER { none(1),    rts(2),     idle(3),
                                  busy(5),    hold(9),    nbrk(17),
                                  arps(65),   iso(129),   pass(257),
                                  bill(513),  msgs(1025), gate(2049),
                                  name(4097), talk(8193), x28(16385),
                                  supr(32769) }
            ACCESS      read-only
            STATUS      mandatory
            DESCRIPTION
                "The option(s) which have been envoked on this
                channel, one or more of:"
            REFERENCE
                "TERM"
            ::={ chanStatEntry  46 }

       chanStatBuffers OBJECT-TYPE
            SYNTAX      INTEGER
            ACCESS      read-only
            STATUS      mandatory
            DESCRIPTION
                "Buffers.
             The number of data buffers to be used as a threshold
                value before flow control to the terminal is invoked."
            REFERENCE
                "TERM"
            ::={ chanStatEntry  47 }

       chanStatDiscMode OBJECT-TYPE
              SYNTAX      INTEGER
              ACCESS      read-only
              STATUS      mandatory
              DESCRIPTION
                  "Disc mode.
               Specifies the call disconnect character that may be
                  applied having established a route via the
                  presentation service."
              REFERENCE
                  "TERM"
             ::={ chanStatEntry  48 }

        chanStatMenuNumber OBJECT-TYPE
              SYNTAX      INTEGER
              ACCESS      read-only
              STATUS      mandatory
             DESCRIPTION
                  "Menu Number.
               Specifies which menu will be displayed to the user
                 by the presentation service."
              REFERENCE
                  "TERM"
              ::={ chanStatEntry  49 }

         chanStatHelpNumber OBJECT-TYPE
              SYNTAX      INTEGER
              ACCESS      read-only
              STATUS      mandatory
              DESCRIPTION
                  "Help Number.
                Specifies which help menu will be displayed to the
                  user by the presentation service."
              REFERENCE
                  "TERM"
              ::={ chanStatEntry  50 }

         chanStatNewsNumber OBJECT-TYPE
              SYNTAX      INTEGER
              ACCESS      read-only
              STATUS      mandatory
              DESCRIPTION
                  "News Number.
               The Menu number that will be displayed if an
                  outgoing resource is unavailable."
              REFERENCE
                 "TERM"
              ::={ chanStatEntry  51 }

         chanStatPadRecall OBJECT-TYPE
              SYNTAX      INTEGER
              ACCESS      read-only
              STATUS      mandatory
              DESCRIPTION
                  "Pad Recall.
               This parameter allows the user to escape from the
                  data transfer state to the PAD command state. The
                      permitted values are:
                  0       No PAD recall
                  1       Escape character is ^P
                  2 - 126 The decimal value specified is the escape
                                  character"
              REFERENCE
                  "TERM"
              ::={ chanStatEntry  52 }

       chanStatEcho OBJECT-TYPE
            SYNTAX      INTEGER { enable(1), disable(2), controlled(3) }
            ACCESS      read-only
            STATUS      mandatory
            DESCRIPTION
                "Echo.
             Determines whether 'echo' is enabled or disabled. If
                set to controlled, the echo facility is controlled by
                the operator."
            REFERENCE
                "TERM"
            ::={ chanStatEntry  53 }

       chanStatDataForwarding OBJECT-TYPE
            SYNTAX      INTEGER
            ACCESS      read-only
            STATUS      mandatory
            DESCRIPTION
                "Data Forwarding.
             This parameter controls which character or
                characters cause the accumulated data to be
                forwarded. The possible values may be added together
                to forward on one of a number of conditions. The
                    allowable values are:

                0       Forward only on buffer full.
                128     Forward on graphics characters.
                64      Forward on all characters in columns 0 and 1
                                of the
                        International Alphabet No. 5.
                1       Forward on A-Z, a-z and 0-9.
                2       Forward on Carriage Return.
                4       Forward on ESC, BEL, ENQ, ACK.
                8       Forward on DEL, CAN, DC2.
                16      Forward on EXT, EOT.
                32      Forward on HT, LF, VT, FF."
            REFERENCE
                "TERM"
            ::={ chanStatEntry  54 }

       chanStatDelay OBJECT-TYPE
            SYNTAX      INTEGER
            ACCESS      read-only
            STATUS      mandatory
            DESCRIPTION
                "Delay.
             Specifies the idle time in tenths of a second,
                allowable between successive characters before the
                accumulated data is forwarded. A value of 0 disables
                    the timeout facility."
            REFERENCE
                "TERM"
            ::={ chanStatEntry  55 }

       chanStatDRI OBJECT-TYPE
            SYNTAX      INTEGER { enabled(2), cts(129), init-enable(3),
                                  disabled(1), rts(33), init(65) }
            ACCESS      read-only
            STATUS      mandatory
            DESCRIPTION
                "DRI.
             Flow control of terminal by the MegaPAC. Valid
                    settings are:
                enabled         MegaPAC flow controls terminal using
                                          XON/XOFF.
                cts             MegaPAC flow controls terminal using
                                          CTS.
                init+enable     MegaPAC sends XON automatically on
                                initialisation.
              disable         No flow control."
            REFERENCE
                "TERM"
            ::={ chanStatEntry  56 }

       chanStatPadSignals OBJECT-TYPE
            SYNTAX      INTEGER { enable(2), disable(1) }
            ACCESS      read-only
            STATUS      mandatory
            DESCRIPTION
                "Pad Signals.
             Enable X.28 prompts and/or messages to be displayed
                on the users terminal."
            REFERENCE
                "TERM"
            ::={ chanStatEntry  57 }

       chanStatBreak OBJECT-TYPE
            SYNTAX      INTEGER
            ACCESS      read-only
            STATUS      mandatory
            DESCRIPTION
                "Break.
             The Action the MegaPAC will take on receipt of a
                Break Signal. The valid values are:
                0       When the MegaPAC receives a Break Signal from
                        the terminal no action is taken.
                1       When the MegaPAC receives a Break Signal from
                        the terminal it will transmit an INTERRUPT
                                packet.
                2       When the MegaPAC receives a Break Signal from
                        the terminal it will transmit an RESET
                                packet.
                5       When the MegaPAC receives a Break Signal from
                        the terminal it will transmit an INTERRUPT
                        packet and an indication of Break PAD
                                message.
                8       When the MegaPAC receives a Break Signal from
                        the terminal it will escape from data
                                transfer state.
                21      When the MegaPAC receives a Break Signal from
                        the terminal it will transmit an INTERRUPT
                        packet and an indication of Break PAD
                                message, while setting (X3) parameter (8)
                        to the value 1 (discard any data
                        received from the network)."
            REFERENCE
                "TERM"
            ::={ chanStatEntry  58 }

       chanStatPadding OBJECT-TYPE
            SYNTAX      INTEGER
            ACCESS      read-only
            STATUS      mandatory
          DESCRIPTION
                "Padding.
             The number of NULL characters inserted after a
                carriage return."
            REFERENCE
                "TERM"
            ::={ chanStatEntry  59 }

       chanStatFold OBJECT-TYPE
            SYNTAX      INTEGER
            ACCESS      read-only
            STATUS      mandatory
            DESCRIPTION
                "Fold
             The number of characters output before line folding
                occurs. Setting to 0 disables line folding."
            REFERENCE
                "TERM"
            ::={ chanStatEntry  60 }

       chanStatDRO OBJECT-TYPE
            SYNTAX      INTEGER {
                        enabled(2),
--                        Terminal to flow control using XON/XOFF
                        cts(129),
--                        Flow control using CTS
                        disabled(1),
--                        No flow control by terminal
                        init(65)
                                }
            ACCESS      read-only
            STATUS      mandatory
            DESCRIPTION
                "Data Restraint Out."
            REFERENCE
                "TERM"
            ::={ chanStatEntry  61 }

       chanStatLFI OBJECT-TYPE
            SYNTAX      INTEGER
            ACCESS      read-only
            STATUS      mandatory
            DESCRIPTION
                "LFI.
             This parameter controls linefeed insertion after a
                carriage return. The valid seetings are:
                0       Line feed insertion disabled.
                1       A linefeed is inserted after a carriage
                        return, in the data forwarded to the
                                terminal.
                4       A linefeed is sent to the terminal after echo
                        of a carriage return to the terminal.
                5       As defined by values 1 + 4.
                6       Linefeed inserted after carriage return from
                        terminal and each carriage return echoed to
                                the terminal.
                7       As defined by values 1 + 6."
            REFERENCE
                "TERM"
            ::={ chanStatEntry  62 }

       chanStatLFPad OBJECT-TYPE
            SYNTAX      INTEGER
            ACCESS      read-only
            STATUS      mandatory
            DESCRIPTION
                "LFPad.
             The number of NULL padding characters sent to a
                device following a linefeed character."
            REFERENCE
                "TERM"
            ::={ chanStatEntry  63 }

       chanStatEdit OBJECT-TYPE
            SYNTAX      INTEGER { enable(2), disable(1) }
            ACCESS      read-only
            STATUS      mandatory
            DESCRIPTION
                "Edit.
             Controls editing of text in data transfer state."
            REFERENCE
                "TERM"
            ::={ chanStatEntry  64 }

       chanStatCharDel OBJECT-TYPE
            SYNTAX      INTEGER
            ACCESS      read-only
            STATUS      mandatory
            DESCRIPTION
                "Char Del.
             The keystroke used for deleting a character."
            REFERENCE
                "TERM"
            ::={ chanStatEntry  65 }

       chanStatBufferDel OBJECT-TYPE
            SYNTAX      INTEGER
            ACCESS      read-only
            STATUS      mandatory
            DESCRIPTION
                "Buffer Del.
             The keystroke used for deleting the buffer."
            REFERENCE
                "TERM"
            ::={ chanStatEntry  66 }

       chanStatDisp OBJECT-TYPE
            SYNTAX      INTEGER
            ACCESS      read-only
            STATUS      mandatory
            DESCRIPTION
                "Disp
             The keystroke used to redisplay the data in the
                    buffer."
            REFERENCE
                "TERM"
            ::={ chanStatEntry  67 }

       chanStatEditServiceSignals OBJECT-TYPE
            SYNTAX      INTEGER
            ACCESS      read-only
            STATUS      mandatory
            DESCRIPTION
                "Edit Service Signals.
             This parameter enables the user to edit the PAD
                    service signals (echoing). The valid settings are:
                0       No editing PAD service signals are echoed.
                1       A '\' will be echoed for each character
                                deleted.
                2       A 'BS' character will be echoed for each
                                character deleted.
                8 and 32-126    Specifies the decimal value of the
                                ASCII character to be echoed for each
                                character deleted."
            REFERENCE
                "TERM"
            ::={ chanStatEntry  68 }

       chanStatEchoMask OBJECT-TYPE
            SYNTAX      INTEGER
            ACCESS      read-only
            STATUS      mandatory
            DESCRIPTION
                "Echo Mask.
             This parameter controls the characters which should
                not be echoed. The valid settings are:

                0       All characters should be echoed to the
                                terminal.
                1       do not echo carriage return.
                2       do not echo linefeed.
                4       do not echo VT, HT and FF characters.
                8       do not echo BEL and BS character.
                16      do not echo ESC and ENQ.
                32      do not echo ACK, NAK, STX, SOH, EOT, ETB or
                                ETX.
                64      do not echo editing characters as defined by
                        parameters 16, 17 and 18.
                128     do not echo other control characters and DEL."
            REFERENCE
                "TERM"
            ::={ chanStatEntry  69 }

       chanStatParityTreatment OBJECT-TYPE
            SYNTAX      INTEGER
            ACCESS      read-only
            STATUS      mandatory
            DESCRIPTION
                "Parity Treatment.
             Determines the parity generation and checking
                    performed
                valid settings are:

                0       No parity generation or checking.
                1       Check parity.
                2       Generate parity.
                3       Check and generate parity."
            REFERENCE
                "TERM"
            ::={ chanStatEntry  70 }

       chanStatPageWait OBJECT-TYPE
            SYNTAX      INTEGER
            ACCESS      read-only
            STATUS      mandatory
            DESCRIPTION
                "PageWait.
             Specifies the number of lines to be transmitted,
                    after which the MegaPAC will wait until instructed by
                    the user to continue sending data (by entering <CTRL
                    >Q). A value of 0 disables the page wait facility."
            REFERENCE
                "TERM"
            ::={ chanStatEntry  71 }

       chanStatForce OBJECT-TYPE
            SYNTAX      INTEGER
            ACCESS      read-only
            STATUS      mandatory
            DESCRIPTION
                "Forward Char.
                 The ASCII character which will force data
                    forwarding, 0 disables forced data forwarding."
            REFERENCE
                "TERM"
            ::={ chanStatEntry  72 }

       chanStatBreakChar OBJECT-TYPE
            SYNTAX      INTEGER
            ACCESS      read-only
            STATUS      mandatory
            DESCRIPTION
                "Break Char.
             The ASCII character in decimal which is used to
                simulate a BREAK signal."
            REFERENCE
                "TERM"
            ::={ chanStatEntry  73 }

       chanStatNetworkParity OBJECT-TYPE
            SYNTAX      INTEGER { even(1), odd(2), mark(4), spac(8), none(0) }
            ACCESS      read-only
            STATUS      mandatory
            DESCRIPTION
                "Network Parity.
            With the Terminal type set to ASYN+X28, the parity
                an be forced onto the network side by selecting the
                approriate value."
            REFERENCE
                "TERM"
            ::={ chanStatEntry  74 }

       chanStatEscapeDelay OBJECT-TYPE
            SYNTAX      INTEGER
            ACCESS      read-only
            STATUS      mandatory
            DESCRIPTION
                "Escape Delay.
             Specifies the time in tenths of a second, that after
                receiving an ESC character, all characters are
                    buffered before being forwarded. During this time the
                    ECHO facility is turned off, and is only restored
                    when the delay timer has expired."
            REFERENCE
                "TERM"
            ::={ chanStatEntry  75 }

        chanStatTransportLevelState OBJECT-TYPE
            SYNTAX      INTEGER { disc(1), call(3), init(5), data(7), cls(9), clr(11) }
            ACCESS      read-only
            STATUS      mandatory
            DESCRIPTION
                "Transport Level State.
            Transport Class 4 session statistics"
            REFERENCE
                "ILAN"
            ::={ chanStatEntry  76 }

        chanStatDestTsap OBJECT-TYPE
            SYNTAX      DisplayString (SIZE(4))
            ACCESS      read-only
            STATUS      mandatory
            DESCRIPTION
                "Destination TSAP
                The destination Transport Service Access Point.
                Applicable controllers: ILAN only"
            REFERENCE
                "ILAN"
            ::={ chanStatEntry  77 }

        chanStatLinkState OBJECT-TYPE
            SYNTAX      INTEGER { open(15), acks(13), ackr(11), reqs(9),
                                  stpi(7),  clsi(5),  stop(3),  clos(1) }
            ACCESS      read-only
            STATUS      mandatory
            DESCRIPTION
                "Link State.
                   The current state of the Link Control Protocol
                Applicable controllers: PPP only"
            REFERENCE
                "PPP"
            ::={ chanStatEntry  78 }

        chanStatProtocolState OBJECT-TYPE
            SYNTAX      INTEGER { open(15), acks(13), ackr(11), reqs(9),
                                  stpi(7),  clsi(5),  stop(3),  clos(1) }
            ACCESS      read-only
            STATUS      mandatory
            DESCRIPTION
                "Protocol State.
                The current state of the Protocol Control Protocol
                Applicable controllers: PPP only"
            REFERENCE
                "PPP"
            ::={ chanStatEntry  79 }

        chanStatProtocol OBJECT-TYPE
            SYNTAX      INTEGER { ip(32802), ipx(32812) }
            ACCESS      read-only
            STATUS      mandatory
            DESCRIPTION
                "Protocol
                Displays the protocol configured for the channel
                Applicable controllers: PPP only"
            REFERENCE
                "PPP"
            ::={ chanStatEntry  80 }

        chanStatIdentity OBJECT-TYPE
            SYNTAX      INTEGER
            ACCESS      read-only
            STATUS      mandatory
            DESCRIPTION
                "Identity.
                The current value of the IDENTITY filed being put
                into the Link Control Protocol or Protocol Control
                Protocol commands.
                Applicable controllers: PPP only"
            REFERENCE
                "PPP"
            ::={ chanStatEntry  81 }

        chanStatFrameRelayWait OBJECT-TYPE
            SYNTAX      INTEGER
            ACCESS      read-only
            STATUS      mandatory
            DESCRIPTION
                "FrameRelayWait.
                The current value of the FRMWAIBUF counter. This counter
                is incremented each time a buffer is delayed because of
                the channel priority (DLCI currently occupied by data
                from channels with higher priority).
                Applicable controllers: NFRM only"
            REFERENCE
                "NFRM"
            ::={ chanStatEntry  82 }

--      The Channel controllers

        chanParamTable OBJECT-TYPE
            SYNTAX      SEQUENCE OF ChanParamEntry
            ACCESS      not-accessible
            STATUS      mandatory
            DESCRIPTION
                "A table of channels associated with this Level 2
                controller."
            ::= { channel 3 }

        chanParamEntry OBJECT-TYPE
            SYNTAX      ChanParamEntry
            ACCESS      not-accessible
            STATUS      mandatory
            DESCRIPTION
                "An individual Channel."
            INDEX       { chanParamIndex }
            ::= { chanParamTable 1 }

        ChanParamEntry ::= SEQUENCE {   chanParamIndex
                                        INTEGER,
                                        chanParamName
                                        DisplayString,
                                        chanParamDRCMask
                                        DisplayString,
                                        chanParamTerminalType
                                        INTEGER,
                                        chanParamCircuitType
                                        INTEGER,
                                        chanParamOptions
                                        INTEGER,
                                        chanParamBuffers
                                        INTEGER,
                                        chanParamDiscMode
                                        INTEGER,
                                        chanParamMenuNumber
                                        INTEGER,
                                        chanParamHelpNumber
                                        INTEGER,
                                        chanParamNewsNumber
                                        INTEGER,
                                        chanParamCallPriority
                                        INTEGER,
                                        chanParamResourcePriority
                                        INTEGER,
                                        chanParamPadEnable
                                        INTEGER,
                                        chanParamPadRecall
                                        INTEGER,
                                        chanParamEcho
                                        INTEGER,
                                        chanParamDataForwarding
                                        INTEGER,
                                        chanParamDelay
                                        INTEGER,
                                        chanParamDRI
                                        INTEGER,
                                        chanParamPadSignals
                                        INTEGER,
                                        chanParamBreak
                                        INTEGER,
                                        chanParamPadding
                                        INTEGER,
                                        chanParamFold
                                        INTEGER,
                                        chanParamDRO
                                        INTEGER,
                                        chanParamLFI
                                        INTEGER,
                                        chanParamLFPad
                                        INTEGER,
                                        chanParamEdit
                                        INTEGER,
                                        chanParamCharDel
                                        INTEGER,
                                        chanParamBufferDel
                                        INTEGER,
                                        chanParamDisp
                                        INTEGER,
                                        chanParamEditServiceSignals
                                        INTEGER,
                                        chanParamEchoMask
                                        INTEGER,
                                        chanParamParityTreatment
                                        INTEGER,
                                        chanParamPageWait
                                        INTEGER,
                                        chanParamForce
                                        INTEGER,
                                        chanParamBreakChar
                                        INTEGER,
                                        chanParamNetworkParity
                                        INTEGER,
                                        chanParamEscapeDelay
                                        INTEGER,
                                        chanParamStationAddress
                                        INTEGER,
                                        chanParamProvideXID
                                        INTEGER,
                                        chanParamMode
                                        INTEGER,
                                        chanParamPortMatch
                                        INTEGER,
                                        chanParamReverseTelnetPort
                                        INTEGER,
                                        chanParamBroadcastFilterTimer
                                        INTEGER,
                                        chanParamInhibitLearning
                                        INTEGER,
                                        chanParamRetainSession
                                        INTEGER,
                                        chanParamPrinterType
                                        INTEGER,
                                        chanParamScreenPrinter
                                        INTEGER,
                                        chanParamLocalPrinter
                                        INTEGER,
                                        chanParamBnnDsap
                                        INTEGER,
                                        chanParamBnnSsap
                                        INTEGER,
                                        chanParamBnnPuTyp
                                        INTEGER,
                                        chanParamPriority
                                        INTEGER        }

        chanParamIndex OBJECT-TYPE
            SYNTAX      INTEGER
            ACCESS      read-only
            STATUS      mandatory
            DESCRIPTION
                "Index.
                The position of this channel in the controller channel
                Table.
                Applicable: All controller types"
          REFERENCE
                "ALL"
          ::={ chanParamEntry 1 }

        chanParamName OBJECT-TYPE
            SYNTAX      DisplayString (SIZE(4))
            ACCESS      read-write
            STATUS      mandatory
            DESCRIPTION
                "Name.
                A user defined name for routing calls to this channel.
                Applicable: All controller types"
            REFERENCE
                "ALL"
            ::={ chanParamEntry 2 }

        chanParamDRCMask OBJECT-TYPE
            SYNTAX      DisplayString (SIZE (4))
            ACCESS      read-write
            STATUS      mandatory
            DESCRIPTION
                "DRC Mask.
                A four character string used to force expicit routing
                to the named resource.
                Applicable: All controller types"
            REFERENCE
                "ALL"
            ::={ chanParamEntry 3 }

        chanParamTerminalType OBJECT-TYPE
            SYNTAX      INTEGER { asyn(2), sync(3), hp(225),
                                x28(209), x28f(999), ansi(177),
                                ext-ansi(161), vpad(129), mtrm(113),
                                slip(97), buf(81), tpad(65), vt200(41) }
            ACCESS      read-write
            STATUS      mandatory
            DESCRIPTION
                "Terminal Type.
                If the channel is to perform terminal emulation, then the
                setting defined will be specific to the users terminal envoking
                emulation.
                Applicable: X25, CONS, HDLC, ILAN, XLAN, SDLC,
                QLLC, TERM, IP, DLC and CLUS controller types"
            REFERENCE
                "CLUS CONS IP TIP TERM X25 XFRM XLAN DLC ILAN
                SDLC QLLC"
            ::={ chanParamEntry 4 }

        chanParamCircuitType OBJECT-TYPE
            SYNTAX      INTEGER { none(1), osi(5), queu(4),
                                call(2), svc(33),
                                out(17), stat(65),call-stat(66),
                                call-pvc(10), call-pvc-stat(74),
                                out-stat(81),out-pvc(25), out-pvc-stat(89),
                                svc-stat(97) }
            ACCESS      read-write
            STATUS      mandatory
            DESCRIPTION
                "Circuit Type.
                The type of circuit used on this channel
                Applicable: X25, CONS, HDLC, ILAN, XLAN, SDLC,
                QLLC, TERM, IP, LAN, V25B, NMS, MULT, MAP, TLAN,
                DLC and SRU controller types"
            REFERENCE
                "CONS DLC ESIS HDLC ILAN IP TIP IPX TIPX LAN TLAN
                MAP MULT NFRM VFRM NMS PPP QLLC SDLC ROUT SRU TERM
                V25B X25 XFRM XLAN"
            ::={ chanParamEntry 5 }

        chanParamOptions OBJECT-TYPE
          SYNTAX      INTEGER { none(1),                    rts(2),
                                idle(3),                    busy(5),
                                hold(9),                    nbrk(17),
                                arps(65),                   diag(33),
                                iso(129),                   pass(257),
                                bill(513),                  msgs(1025),
                                gate(2049),                 name(4097),
                                talk(8193),                 x28(16385),
                                supr(32769),                msgs-name(5121),
                                msgs-name-talk(13313),      msgs-pass(1281),
                                msgs-pass-gate(3329),       msgs-name-pass(5377),
                                msgs-name-pass-talk(13569), msgs-name-pass-talk-gate(15617) }
            ACCESS      read-write
            STATUS      mandatory
            DESCRIPTION
                "Options.
                A range of channel options, these options may be
                specified individually or added together.
                Applicable: X25, CONS, HDLC, ILAN, XLAN, SDLC,
                QLLC, TERM, IP, LAN, V25, TLAN, DLC and CLUS controller
                types"
            REFERENCE
                "CLUS CONS IP TIP PPP ROUT TERM X25 XFRM XLAN"
            ::={ chanParamEntry 6 }

        chanParamBuffers OBJECT-TYPE
            SYNTAX      INTEGER (1..240)
            ACCESS      read-write
            STATUS      mandatory
            DESCRIPTION
                "Buffers.
                The number of system buffers allocated to this channel
                for incoming calls.
                Applicable: X25, CONS, HDLC, ILAN, XLAN, SDLC,
                QLLC, TERM, IP, LAN, V25B, NMS, MULT, MAP, TLAN,
                DLC and SRU controller types"
            REFERENCE
                "ALL"
            ::={ chanParamEntry 7 }

        chanParamDiscMode OBJECT-TYPE
            SYNTAX      INTEGER (0..32)
            ACCESS      read-write
            STATUS      mandatory
            DESCRIPTION
                "DISC Mode.
                The number of the character in decimal which forces
                disconnection of the call.
                Applicable: X25, CONS, HDLC, ILAN, XLAN, SDLC, QLLC
                TERM, DLC and IP controller types"
            REFERENCE
                "CONS IP TIP TERM X25 XFRM XLAN"
            ::={ chanParamEntry 8 }

        chanParamMenuNumber OBJECT-TYPE
            SYNTAX      INTEGER (0..32)
            ACCESS      read-write
            STATUS      mandatory
            DESCRIPTION
                "Menu Number.
                Specifies which menu will be displayed to the user by the
                presentation service.
                Applicable: X25, CONS, HDLC, ILAN, XLAN, SDLC, QLLC
                TERM, DLC, IP and CLUS controller types"
            REFERENCE
                "CLUS CONS IP TIP TERM X25 XFRM XLAN"
            ::={ chanParamEntry 9 }

        chanParamHelpNumber OBJECT-TYPE
            SYNTAX      INTEGER (0..32)
            ACCESS      read-write
            STATUS      mandatory
            DESCRIPTION
                "Help Number.
                Specifies which help screen will be displayed to the user by
                the presentation service.
                Applicable: X25, CONS, HDLC, ILAN, XLAN, SDLC, QLLC
                TERM, DLC and IP controller types"
            REFERENCE
                "CONS IP TIP TERM X25 XFRM XLAN"
            ::={ chanParamEntry 10 }

        chanParamNewsNumber OBJECT-TYPE
            SYNTAX      INTEGER (0..32)
            ACCESS      read-write
            STATUS      mandatory
            DESCRIPTION
                "News Number.
                The number of the menu which will be displayed if an
                outgoing channel is unavailable.
                Applicable: X25, CONS, HDLC, ILAN, XLAN, SDLC, QLLC
                TERM, DLC and IP controller types"
            REFERENCE
                "CONS IP TIP TERM X25 XFRM XLAN"
            ::={ chanParamEntry 11 }

        chanParamCallPriority OBJECT-TYPE
            SYNTAX      INTEGER (0..15)
            ACCESS      read-write
            STATUS      mandatory
            DESCRIPTION
                "Call Priority.
                Call and Resource priorities are used primarily for
                providing alternate routing. For a call to succeed the
                Call Priority on the incoming channel must be greater than
                or equal to the Resource Priority on the outgoing channel.
                Applicable: X25, HDLC, CONS, XLAN, TERM, IP, LAN,
                NMS, V25B, MULT, MAP, TLAN, DLC and SRU controller types"
            REFERENCE
                "CONS DLC ESIS HDLC ILAN IP TIP IPX TIPX LAN TLAN
                MAP MULT NFRM VFRM NMS QLLC SDLC ROUT SRU TERM V25B
                X25 XFRM XLAN"
            ::={ chanParamEntry 12 }

        chanParamResourcePriority OBJECT-TYPE
            SYNTAX      INTEGER (0..15)
            ACCESS      read-write
            STATUS      mandatory
            DESCRIPTION
                "Resource Priority.
                Call and Resource priorities are used primarily for
                providing alternate routing. For a call to succeed the
                Call Priority on the incoming channel must be greater than
                or equal to the Resource Priority on the outgoing channel.
                Applicable: X25, HDLC, CONS, XLAN, TERM, IP, LAN,
                NMS, V25B, MULT, MAP, TLAN, DLC and SRU controller types"
            REFERENCE
                "CONS DLC ESIS HDLC ILAN IP TIP IPX TIPX LAN TLAN
                MAP MULT NFRM VFRM NMS QLLC SDLC ROUT SRU TERM V25B
                X25 XFRM XLAN"
            ::={ chanParamEntry 13 }

        chanParamPadEnable OBJECT-TYPE
            SYNTAX  INTEGER { disable(1), enable(2),      rev(3),  enable-rev(4),
                              prof(5),    enable-prof(6), mask(7), enable-mask(8), x28(34) }
            ACCESS      read-write
            STATUS      mandatory
            DESCRIPTION
                "Pad Enable.
                The effect of the PAD Enable parameters are as follows:
                        enable          PAD services enabled. The logical
                                        channel will respond to X.29 packets.
                        enable-rev      REVerse PAD enabled. When a call is
                                        established to this channel, the
                                        MegaPAC will generate an X.29
                                        qualified data packet back to the
                                        caller, containing the X.3 operating
                                        values specified in the channel's
                                        configuration.
                        enable-prof     The X.3 profile settings for the channel
                                        will be derived by referencing the
                                        logical channel's NAME/ parameter to
                                        the NAME/ field in the PROF file. The
                                        X.3 settings as contained in the PROF
                                        file record are then loaded onto the
                                        channel.
                Applicable: X25, HDLC, CONS, ILAN, XLAN, SDLC, QLLC,
                IP, DLC and TERM controller types"
            REFERENCE
                "CONS IP TIP TERM X25 XFRM XLAN"
            ::={ chanParamEntry 14 }

        chanParamPadRecall OBJECT-TYPE
            SYNTAX      INTEGER (0..126)
            ACCESS      read-write
            STATUS      mandatory
            DESCRIPTION
                "Pad Recall (1).
                This parameter allows the user to escape from the data
                transfer state to the PAD command state. The permitted
                values are:
                0       No PAD recall
                1       Escape character is ^P
                2 - 126 The decimal value specified is the escape character
                Applicable: X25, HDLC, CONS, ILAN, XLAN, SDLC, QLLC,
                IP, DLC and TERM controller types"
            REFERENCE
                "CONS IP TIP TERM X25 XFRM XLAN"
            ::={ chanParamEntry 15 }

        chanParamEcho OBJECT-TYPE
            SYNTAX      INTEGER { enable(1), disable(2), controlled(3) }
            ACCESS      read-write
            STATUS      mandatory
            DESCRIPTION
                "Echo.
                Determines whether 'echo' is enabled or disabled. If
                set to controlled, the echo facility is controlled by the
                operator.
                Applicable: X25, HDLC, CONS, ILAN, XLAN, SDLC, QLLC,
                IP, DLC and TERM controller types"
            REFERENCE
                "CONS IP TIP TERM X25 XFRM XLAN"
            ::={ chanParamEntry 16 }

        chanParamDataForwarding OBJECT-TYPE
            SYNTAX      INTEGER
            ACCESS      read-write
            STATUS      mandatory
            DESCRIPTION
                "Data Forwarding.
                This parameter controls which character or characters
                cause the accumulated data to be forwarded. The possible
                values may be added together to forward on one of a number
                of conditions. The allowable values are:
                0       Forward only on buffer full.
                128     Forward on graphics characters.
                64      Forward on all characters in columns 0 and 1 of the
                        International Alphabet No. 5.
                1       Forward on A-Z, a-z and 0-9.
                2       Forward on Carriage Return.
                4       Forward on ESC, BEL, ENQ, ACK.
                8       Forward on DEL, CAN, DC2.
                16      Forward on EXT, EOT.
                32      Forward on HT, LF, VT, FF.
                Applicable: X25, HDLC, CONS, ILAN, XLAN, SDLC, QLLC,
                IP, DLC and TERM controller types"
            REFERENCE
                "CONS IP TIP TERM X25 XFRM XLAN"
            ::={ chanParamEntry 17 }

        chanParamDelay OBJECT-TYPE
            SYNTAX      INTEGER (0..255)
            ACCESS      read-write
            STATUS      mandatory
            DESCRIPTION
                "Delay.
                Specifies the idle time in tenths of a second, allowable
                between successive characters before the accumulated data
                is forwarded. A value of 0 disables the timeout facility.
                Applicable: X25, HDLC, CONS, ILAN, XLAN, SDLC, QLLC,
                IP, DLC and TERM controller types"
            REFERENCE
                "CONS IP TIP TERM X25 XFRM XLAN"
            ::={ chanParamEntry 18 }

        chanParamDRI OBJECT-TYPE
            SYNTAX      INTEGER { enabled(2), cts(129), init-enable(3),
                                  disabled(1), rts(33), init(65) }
            ACCESS      read-write
            STATUS      mandatory
            DESCRIPTION
                "DRI.
                Flow control of terminal by the MegaPAC. Valid settings are:
                enabled         MegaPAC flow controls terminal using XON/XOFF.
                cts             MegaPAC flow controls terminal using CTS.
                init+enable     MegaPAC sends XON automatically on initialisation.
                disable         No flow control.
                Applicable: X25, HDLC, CONS, ILAN, XLAN, SDLC, QLLC,
                IP, DLC and TERM controller types"
            REFERENCE
                "CONS IP TIP TERM X25 XFRM XLAN"
            ::={ chanParamEntry 19 }

        chanParamPadSignals OBJECT-TYPE
            SYNTAX      INTEGER { enable(2), disable(1) }
            ACCESS      read-write
            STATUS      mandatory
            DESCRIPTION
                "Pad Signals.
                Enable X.28 prompts and/or messages to be displayed on
                the users terminal.
                Applicable: X25, HDLC, CONS, ILAN, XLAN, SDLC, QLLC,
                IP, DLC and TERM controller types"
            REFERENCE
                "CONS IP TIP TERM X25 XFRM XLAN"
            ::={ chanParamEntry 20 }

        chanParamBreak OBJECT-TYPE
            SYNTAX      INTEGER
            ACCESS      read-write
            STATUS      mandatory
            DESCRIPTION
                "Break.
                The Action the MegaPAC will take on receipt of a Break Signal.
                The valid values are:

                0       When the MegaPAC receives a Break Signal from the
                        terminal no action is taken.
                1       When the MegaPAC receives a Break Signal from the
                        terminal it will transmit an INTERRUPT packet.
                2       When the MegaPAC receives a Break Signal from the
                        terminal it will transmit an RESET packet.
                5       When the MegaPAC receives a Break Signal from the
                        terminal it will transmit an INTERRUPT packet and an
                        indication of Break PAD message.
                8       When the MegaPAC receives a Break Signal from the
                        terminal it will escape from data transfer state.
                21      When the MegaPAC receives a Break Signal from the
                        terminal it will transmit an INTERRUPT packet and an
                        indication of Break PAD message, while setting (X3)
                        parameter (8) to the value 1 (discard any data
                        received from the network).
                Applicable: X25, HDLC, CONS, ILAN, XLAN, SDLC, QLLC,
                IP, DLC and TERM controller types"
            REFERENCE
                "CONS IP TIP TERM X25 XFRM XLAN"
            ::={ chanParamEntry 21 }

        chanParamPadding OBJECT-TYPE
            SYNTAX      INTEGER (0..255)
            ACCESS      read-write
            STATUS      mandatory
            DESCRIPTION
                "Padding.
                The number of NULL characters inserted after a carriage
                return.
                Applicable: X25, HDLC, CONS, ILAN, XLAN, SDLC, QLLC,
                IP, DLC and TERM controller types"
            REFERENCE
                "CONS IP TIP TERM X25 XFRM XLAN"
            ::={ chanParamEntry 22 }

        chanParamFold OBJECT-TYPE
            SYNTAX      INTEGER (0..255)
            ACCESS      read-write
            STATUS      mandatory
            DESCRIPTION
                "Fold.
                The number of characters output before line folding
                occurs. Setting to 0 disables line folding.
                Applicable: X25, HDLC, CONS, ILAN, XLAN, SDLC, QLLC,
                IP, DLC and TERM controller types"
            REFERENCE
                "CONS IP TIP TERM X25 XFRM XLAN"
            ::={ chanParamEntry 23 }

        chanParamDRO OBJECT-TYPE
            SYNTAX      INTEGER {
                                enabled(2),
-- Terminal to flow control
-- using XON/XOFF
                                cts(129),
-- Flow control using CTS
                                disabled(1),
-- No flow control by terminal
                                init(65)
                                }
            ACCESS      read-write
            STATUS      mandatory
            DESCRIPTION
                "Data Restraint Out.
                Applicable: X25, HDLC, CONS, ILAN, XLAN, SDLC, QLLC,
                IP, DLC and TERM controller types"
            REFERENCE
                "CONS IP TIP TERM X25 XFRM XLAN"
            ::={ chanParamEntry 24 }

        chanParamLFI OBJECT-TYPE
            SYNTAX      INTEGER
            ACCESS      read-write
            STATUS      mandatory
            DESCRIPTION
                "LFI.
                This parameter controls linefeed insertion after a
                carriage return. The valid settings are:
                0       Line feed insertion disabled.
                1       A linefeed is inserted after a carriage return,
                        in the data forwarded to the terminal.
                4       A linefeed is sent to the terminal after echo of a
                        carriage return to the terminal.
                5       As defined by values 1 + 4.
                6       Linefeed inserted after carriage return from terminal
                        and each carriage return echoed to the terminal.
                7       As defined by values 1 + 6.
                Applicable: X25, HDLC, CONS, ILAN, XLAN, SDLC, QLLC,
                IP, DLC and TERM controller types"
            REFERENCE
                "CONS IP TIP TERM X25 XFRM XLAN"
            ::={ chanParamEntry 25 }

        chanParamLFPad OBJECT-TYPE
            SYNTAX      INTEGER (0..7)
            ACCESS      read-write
            STATUS      mandatory
            DESCRIPTION
                "LFPad.
                The number of NULL padding characters sent to a device
                following a linefeed character.
                Applicable: X25, HDLC, CONS, ILAN, XLAN, SDLC, QLLC,
                IP, DLC and TERM controller types"
            REFERENCE
                "CONS IP TIP TERM X25 XFRM XLAN"
            ::={ chanParamEntry 26 }

        chanParamEdit OBJECT-TYPE
            SYNTAX      INTEGER { enable(2), disable(1) }
            ACCESS      read-write
            STATUS      mandatory
            DESCRIPTION
                "Edit.
                Controls editing of text in data transfer state.
                Applicable: X25, HDLC, CONS, ILAN, XLAN, SDLC, QLLC,
                IP, DLC and TERM controller types"
            REFERENCE
                "CONS IP TIP TERM X25 XFRM XLAN"
            ::={ chanParamEntry 27 }

        chanParamCharDel OBJECT-TYPE
            SYNTAX      INTEGER (0..128)
            ACCESS      read-write
            STATUS      mandatory
            DESCRIPTION
                "Char Delete.
                The keystroke used for deleting a character.
                Applicable: X25, HDLC, CONS, ILAN, XLAN, SDLC, QLLC,
                IP, DLC and TERM controller types"
            REFERENCE
                "CONS IP TIP TERM X25 XFRM XLAN"
            ::={ chanParamEntry 28 }

        chanParamBufferDel OBJECT-TYPE
            SYNTAX      INTEGER (0..127)
            ACCESS      read-write
            STATUS      mandatory
            DESCRIPTION
                "Buffer Delete.
                The keystroke used for deleting the buffer.
                Applicable: X25, HDLC, CONS, ILAN, XLAN, SDLC, QLLC,
                IP, DLC and TERM controller types"
            REFERENCE
                "CONS IP TIP TERM X25 XFRM XLAN"
            ::={ chanParamEntry 29 }

        chanParamDisp OBJECT-TYPE
            SYNTAX      INTEGER (0..127)
            ACCESS      read-write
            STATUS      mandatory
            DESCRIPTION
                "Disp.
                The keystroke used to redisplay the data in the buffer.
                Applicable: X25, HDLC, CONS, ILAN, XLAN, SDLC, QLLC,
                IP, DLC and TERM controller types"
            REFERENCE
                "CONS IP TIP TERM X25 XFRM XLAN"
            ::={ chanParamEntry 30 }

        chanParamEditServiceSignals OBJECT-TYPE
            SYNTAX      INTEGER (0..126)
            ACCESS      read-write
            STATUS      mandatory
            DESCRIPTION
                "Edit Service Signals.
                This parameter enables the user to edit the PAD service
                signals (echoing). The valid settings are:
                0       No editing PAD service signals are echoed.
                1       A '\' will be echoed for each character deleted.
                2       A 'BS' character will be echoed for each character
                        deleted.
                8 and 32-126    Specifies the decimal value of the ASCII
                        character to be echoed for each character deleted.
                Applicable: X25, HDLC, CONS, ILAN, XLAN, SDLC, QLLC,
                IP, DLC and TERM controller types"
            REFERENCE
                "CONS IP TIP TERM X25 XFRM XLAN"
            ::={ chanParamEntry 31 }

        chanParamEchoMask OBJECT-TYPE
            SYNTAX      INTEGER
            ACCESS      read-write
            STATUS      mandatory
            DESCRIPTION
                "Echo Mask.
                This parameter controls the characters which should not
                be echoed. The valid settings are:
                0       All characters should be echoed to the terminal.
                1       do not echo carriage return.
                2       do not echo linefeed.
                4       do not echo VT, HT and FF characters.
                8       do not echo BEL and BS character.
                16      do not echo ESC and ENQ.
                32      do not echo ACK, NAK, STX, SOH, EOT, ETB or ETX.
                64      do not echo editing characters as defined by
                        parameters 16, 17 and 18.
                128     do not echo other control characters and DEL.
                Applicable: X25, HDLC, CONS, ILAN, XLAN, SDLC, QLLC,
                IP, DLC and TERM controller types"
            REFERENCE
                "CONS IP TIP TERM X25 XFRM XLAN"
            ::={ chanParamEntry 32 }

        chanParamParityTreatment OBJECT-TYPE
            SYNTAX      INTEGER (0..3)
            ACCESS      read-write
            STATUS      mandatory
            DESCRIPTION
                "Parity Treatment.
                Determines the parity generation and checking performed
                valid settings are:
                0       No parity generation or checking.
                1       Check parity.
                2       Generate parity.
                3       Check and generate parity.
                Applicable: X25, HDLC, CONS, ILAN, XLAN, SDLC, QLLC,
                IP, DLC and TERM controller types"
            REFERENCE
                "CONS IP TIP TERM X25 XFRM XLAN"
            ::={ chanParamEntry 33 }

        chanParamPageWait OBJECT-TYPE
            SYNTAX      INTEGER (0..255)
            ACCESS      read-write
            STATUS      mandatory
            DESCRIPTION
                "Page Wait.
                Specifies the number of lines to be transmitted, after
                which the MegaPAC will wait until instructed by the user to
                continue sending data (by entering <CTRL >Q). A value of
                0 disables the page wait facility.
                Applicable: X25, HDLC, CONS, ILAN, XLAN, SDLC, QLLC,
                IP, DLC and TERM controller types"
            REFERENCE
                "CONS IP TIP TERM X25 XFRM XLAN"
            ::={ chanParamEntry 34 }

        chanParamForce OBJECT-TYPE
            SYNTAX      INTEGER (0..255)
            ACCESS      read-write
            STATUS      mandatory
            DESCRIPTION
                "Force.
                The ASCII character which will force data forwarding,
                0 disables forced data forwarding.
                Applicable: X25, HDLC, CONS, ILAN, XLAN, SDLC, QLLC,
                IP, DLC and TERM controller types"
            REFERENCE
                "CONS IP TIP TERM X25 XFRM XLAN"
            ::={ chanParamEntry 35 }

        chanParamBreakChar OBJECT-TYPE
            SYNTAX      INTEGER (0..32)
            ACCESS      read-write
            STATUS      mandatory
            DESCRIPTION
                "Break Character.
                The ASCII character in decimal which is used to
                simulate a BREAK signal.
                Applicable: X25, HDLC, CONS, ILAN, XLAN, SDLC, QLLC,
                IP, DLC and TERM controller types"
            REFERENCE
                "CONS IP TIP TERM X25 XFRM XLAN"
            ::={ chanParamEntry 36 }

        chanParamNetworkParity OBJECT-TYPE
            SYNTAX      INTEGER { even(1), odd(2), mark(4), spac(8), none(0) }
            ACCESS      read-write
            STATUS      mandatory
            DESCRIPTION
                "Network Parity.
                With the Terminal type set to ASYN+X28, the parity can
                be forced onto the network side by selecting the approriate
                value.
                Applicable: X25, HDLC, CONS, ILAN, XLAN, SDLC, QLLC,
                DLC and TERM controller types"
            REFERENCE
                "CONS IP TIP TERM X25 XFRM XLAN"
            ::={ chanParamEntry 37 }

        chanParamEscapeDelay OBJECT-TYPE
            SYNTAX      INTEGER (0..15)
            ACCESS      read-write
            STATUS      mandatory
            DESCRIPTION
                "Escape Delay.
                Specifies the time in tenths of a second, that after
                receiving an ESC character, all characters are buffered
                before being forwarded. During this time the ECHO facility
                is turned off, and is only restored when the delay timer has
                expired.
                Applicable: X25, HDLC, CONS, ILAN, XLAN, SDLC, QLLC,
                DLC and TERM controller types"
            REFERENCE
                "CONS IP TIP TERM X25 XFRM XLAN"
            ::={ chanParamEntry 38 }

        chanParamStationAddress OBJECT-TYPE
            SYNTAX      INTEGER (0..255)
            ACCESS      read-write
            STATUS      mandatory
            DESCRIPTION
                "Station Address.
                Physical Unit Address of the Cluster Controller.
                Applicable: SDLC, QLLC and DLC controller types"
            REFERENCE
                "SDLC QLLC DLC"
            ::={ chanParamEntry 39 }

        chanParamProvideXID OBJECT-TYPE
            SYNTAX      INTEGER { yes(1), no(2) }
            ACCESS      read-write
            STATUS      mandatory
            DESCRIPTION
                "Provide XID.
                ????
                Applicable: SDLC, QLLC and DLC controller types"
            REFERENCE
                "SDLC QLLC DLC"
            ::={ chanParamEntry 40 }

        chanParamMode OBJECT-TYPE
            SYNTAX  INTEGER { none(1),  path(2),   push(3), pull(5), stop(9),
                              auto(17), auto-pull-path-push-stop(32),
                              sym(33),  data(65),  wait(81),
                              hub(97),  resp(129), sat(193) }
            ACCESS      read-write
            STATUS      mandatory
            DESCRIPTION
                "Mode.
                This parameter provides a number of additional connection
                facilities for channels on virtual controllers. The options
                available are of an additive nature, the valid options and
                their integer values are:
                Option                  Integer Value
                DATA                    ??
                RESP                    ??
                SYM                     ??
                AUTO                    ??
                PATH                    ??
                PUSH                    ??
                PULL                    ??
                STOP                    ??
                NONE                    ??
                Applicable: NMS, V25B, MULT, MAP and SRU controller types"
            REFERENCE
                "MAP MULT NMS SRU V25B"
            ::={ chanParamEntry 41 }

        chanParamPortMatch OBJECT-TYPE
            SYNTAX      INTEGER { no(1), source(2), destination(129), wild(137) }
            ACCESS      read-write
            STATUS      mandatory
            DESCRIPTION
                "Port Match.
                This parameter optionally allows the Source
                and Destination ports to be used in conjunction
                with the IP address for routing.
                Applicable: IP controller type only"
            REFERENCE
                "IP TIP"
            ::={ chanParamEntry 42 }

        chanParamReverseTelnetPort OBJECT-TYPE
            SYNTAX      INTEGER (0..32767)
            ACCESS      read-write
            STATUS      mandatory
            DESCRIPTION
                "Reverse Telnet Port.
                The port number which will respond to TELNET
                open requests. The default value for TELNET
                ports is '23'.
                Applicable: IP controller type only"
            REFERENCE
                "IP TIP"
            ::={ chanParamEntry 43 }

        chanParamBroadcastFilterTimer OBJECT-TYPE
            SYNTAX      INTEGER (0..12000)
            ACCESS      read-write
            STATUS      mandatory
            DESCRIPTION
                "Broadcast Filter Timer.
                ?????
                Applicable: LAN and TLAN controller types"
            REFERENCE
                "ESIS IPX TIPX LAN TLAN"
            ::={ chanParamEntry 44 }

        chanParamInhibitLearning OBJECT-TYPE
            SYNTAX      INTEGER { yes(1), no(2) }
            ACCESS      read-write
            STATUS      mandatory
            DESCRIPTION
                "Inhibit Learning.
                This parameter determines whether the 'bridge'
                will work in Directed or Learning mode. If
                InhibitLearning is set to 'Yes' then the bridge
                will only forward frames whose addresses are fixed in
                the forwarding table.
                Applicable: LAN and TLAN controller types"
            REFERENCE
                "ESIS IPX TIPX LAN TLAN"
            ::={ chanParamEntry 45 }

        chanParamRetainSession OBJECT-TYPE
            SYNTAX      INTEGER { notify(1), yes(2), no(3) }
            ACCESS      read-write
            STATUS      mandatory
            DESCRIPTION
                "Retain Session.
                This parameter determines if and how a session will be
                cleared down when the call is cleared. The parameter is
                only applicable to channels (2) to (n). If set to NOTIFY
                or NO the session will be cleared when the call disconnects
                , NOTIFY will cause a NOTIFY RU to be sent indicating the
                disconnection. If this parameter is set to YES then the
                session will be retained on channel disconnection, this
                is used to provide a hot key switching facility.
                Applicable: CLUS controller type only"
            REFERENCE
                "CLUS"
            ::={ chanParamEntry 46 }

        chanParamPrinterType OBJECT-TYPE
            SYNTAX      INTEGER { ibm(1), none(2) }
            ACCESS      read-write
            STATUS      mandatory
            DESCRIPTION
                "Printer Type.
                If set to IBM the logical channel will act as an
                appication system printer, otherwise it operates in
                screen emulation mode. Only applicable to channels (2)
                to (n).
                Applicable: CLUS controller type only"
            REFERENCE
                "CLUS"
            ::={ chanParamEntry 47 }

        chanParamScreenPrinter OBJECT-TYPE
            SYNTAX      INTEGER { yes(1), no(2) }
            ACCESS      read-write
            STATUS      mandatory
            DESCRIPTION
                "Screen Printer.
                If set to YES, screen printer requests are to be processed
                and sent to this LU address (in this mode, the terminal
                attaching to this channel MUST have a printer attached). If
                set to NO, screen printing is supported via the LOCAL PRINTER
                or the DEFAULT LOCAL PRINTER parameters.
                Applicable: CLUS controller type only"
            REFERENCE
                "CLUS"
            ::={ chanParamEntry 48 }

        chanParamLocalPrinter OBJECT-TYPE
            SYNTAX      INTEGER (0..128)
            ACCESS      read-write
            STATUS      mandatory
            DESCRIPTION
                "Local Printer.
                This parameter specifies the channel to which screen printing
                should be directed. It takes precedence over the value defined
                by the DEFAULT LOCAL PRINTER at controller level. This parameter
                may only be applied to channels (2) to (n).
                Applicable: CLUS controller type only"
            REFERENCE
                "CLUS"
            ::={ chanParamEntry 49 }

        chanParamBnnDsap OBJECT-TYPE
            SYNTAX      INTEGER (0..254)
            ACCESS      read-write
            STATUS      mandatory
            DESCRIPTION
                "DSAP.
                The Destination Service Access Point.
                Applicable: NFRM controller type with SNA protocol encapsulation."
            REFERENCE
                " NFRM "
            ::={ chanParamEntry 50 }

        chanParamBnnSsap OBJECT-TYPE
            SYNTAX      INTEGER (0..254)
            ACCESS      read-write
            STATUS      mandatory
            DESCRIPTION
                "SSAP.
                The Source Service Access Point.
                Applicable: NFRM controller type with SNA protocol encapsulation."
            REFERENCE
                " NFRM "
            ::={ chanParamEntry 51 }

        chanParamBnnPuTyp OBJECT-TYPE
            SYNTAX      INTEGER { none(0),    pu2-0(130),
                                  pu2-1(131)  }
            ACCESS      read-write
            STATUS      mandatory
            DESCRIPTION
                "PU TYPE.
                IBM PU type.
                Applicable: NFRM controller type with SNA protocol encapsulation."
            REFERENCE
                "NFRM"
            ::={ chanParamEntry 52 }

        chanParamPriority OBJECT-TYPE
            SYNTAX      INTEGER (0..7)
            ACCESS      read-write
            STATUS      mandatory
            DESCRIPTION
                "Channel Priority.
                The internal priority which will be assigned to
                the channel. Data from the channel with the highest priority i.e. 1
                will overtake data of from less priority channels on the same DLCI.
                Applicable: NFRM controller type."
            REFERENCE
                "NFRM"
            ::={ chanParamEntry 53 }

-- The X.25 File
-- The X.25 File defines the X.25 address file used for switching /
-- translation of X.25 call packets.  This file applies to controller
-- types ; X25 and XFRM.  Note, where complex decision making
-- routines are required for switching, translating and or alternate
-- routing, this file can be complemented (or replaced) by the
-- MegaPAC MACro file.

        x25FileSize OBJECT-TYPE
            SYNTAX      INTEGER
            ACCESS      read-only
            STATUS      mandatory
            DESCRIPTION
                "X25 file size.
                The number of entries configured into the X25 file."
            ::= { x25File 1 }

        x25Table OBJECT-TYPE
            SYNTAX      SEQUENCE OF X25Entry
            ACCESS      not-accessible
            STATUS      mandatory
            DESCRIPTION
                "A table of X.25 routing entries"
            ::= { x25File 2 }

        x25Entry OBJECT-TYPE
            SYNTAX      X25Entry
            ACCESS      not-accessible
            STATUS      mandatory
            INDEX       { x25Index }
            ::= { x25Table 1 }

        X25Entry ::= SEQUENCE { x25Index         INTEGER,
                                x25Name          DisplayString,
                                x25AddressGroup  INTEGER,
                                x25Address       DisplayString,
                                x25UserData      DisplayString }

        x25Index OBJECT-TYPE
            SYNTAX      INTEGER
            ACCESS      read-only
            STATUS      mandatory
            DESCRIPTION
                "Index.
                The index to an individual X.25 entry"
            ::={ x25Entry 1 }

        x25Name OBJECT-TYPE
            SYNTAX      DisplayString (SIZE(4))
            ACCESS      read-write
            STATUS      mandatory
            DESCRIPTION
                "Name.
                A 4 character name which is used to match on the 'NAME'
                parameter of the channel on which a call will be routed
                over the X.25 network."
            ::={ x25Entry 2 }

        x25AddressGroup OBJECT-TYPE
            SYNTAX      INTEGER (0..15)
            ACCESS      read-write
            STATUS      mandatory
            DESCRIPTION
                "Addr Grp.
                An integer used to partition the X.25 routing tables.
                Any match on a channel name will only take effect if
                the channel 'AddressGroup' parameter is set to the same
                value."
            ::={ x25Entry 3 }

        x25Address OBJECT-TYPE
            SYNTAX      DisplayString (SIZE(0..16))
            ACCESS      read-write
            STATUS      mandatory
            DESCRIPTION
                "Address.
                The numeric address which is used to match on the
                incoming X.25 address in a call request packet."
            ::={ x25Entry 4 }

        x25UserData OBJECT-TYPE
            SYNTAX      DisplayString (SIZE(0..30))
            ACCESS      read-write
            STATUS      mandatory
            DESCRIPTION
                "User Data
                A text field in which Call User Data or Facilities may
                be placed. The user data will be inserted into call
                request packets generated by the MegaPAC."
            ::={ x25Entry 5 }

-- The Name File
-- The Name File is used to associate up to 8 characters service
-- names (known as to the ASCII user) with 2 character resource names
-- used by the MegaPAC for internal routing. The Name File can also
-- be used to invoke terminal gateway emulation, such as,
-- IBM 3270, ICL 7561, TCP-IP Telnet etc.

        nameFileSize OBJECT-TYPE
            SYNTAX      INTEGER
            ACCESS      read-only
            STATUS      mandatory
            DESCRIPTION
                "Name File Size.
                The number of entries configured into the NAME file."
            ::= { nameFile 1 }

        nameTable OBJECT-TYPE
            SYNTAX      SEQUENCE OF NameEntry
            ACCESS      not-accessible
            STATUS      mandatory
            DESCRIPTION
                "A table of 'Name' entries."
            ::= { nameFile 2 }

        nameEntry OBJECT-TYPE
            SYNTAX      NameEntry
            ACCESS      not-accessible
            STATUS      mandatory
            INDEX       { nameIndex }
            ::= { nameTable 1 }

        NameEntry ::= SEQUENCE { nameIndex            INTEGER,
                                 nameName             DisplayString,
                                 nameDRCMask          DisplayString,
                                 nameCallPriority     INTEGER,
                                 nameBilling          INTEGER,
                                 nameOptions          INTEGER }

        nameIndex OBJECT-TYPE
            SYNTAX      INTEGER
            ACCESS      read-only
            STATUS      mandatory
            DESCRIPTION
                "Index.
                The index into the name table."
            ::={ nameEntry 1 }

        nameName OBJECT-TYPE
            SYNTAX      DisplayString (SIZE(0..8))
            ACCESS      read-write
            STATUS      mandatory
            DESCRIPTION
                "Name.
                A string of up to 8 characters in length which is
                typed in by the network user in order to establish
                a connection to a specific resource."
            ::={ nameEntry 2 }

        nameDRCMask OBJECT-TYPE
            SYNTAX      DisplayString (SIZE(4))
            ACCESS      read-write
            STATUS      mandatory
            DESCRIPTION
                "DRC Mask.
                The four character resource (channel) name to which
                the call will be directed."
            ::={ nameEntry 3 }

        nameCallPriority OBJECT-TYPE
            SYNTAX      INTEGER (0..15)
            ACCESS      read-write
            STATUS      mandatory
            DESCRIPTION
                "Call Priority.
                The internal call priority which will be assigned to
                the call."
            ::={ nameEntry 4 }

        nameBilling OBJECT-TYPE
            SYNTAX      INTEGER { enabled(1), disabled(2) }
            ACCESS      read-write
            STATUS      mandatory
            DESCRIPTION
                "Billing
                If enabled, statistics relating to the call will be
                sent to the billing file."
            ::={ nameEntry 5 }

        nameOptions OBJECT-TYPE
            SYNTAX      INTEGER { none(1),     iso(2), prof(5),  icl7561(9),
                                  teln(65), rev-teln(129), ppp(33), ppp-pap(49) }
            ACCESS      read-write
            STATUS      mandatory
            DESCRIPTION
                "Options
                Enables the appropriate terminal emulation options."
            ::={ nameEntry 6 }

-- The Password File (NOT IMPLEMENTED CURRENTLY)
-- The Password File is used to password protect ASCII resources
-- i.e. either on input to a switched network, or as a outbound
-- security gateway.  For security reasons, only the size of the
-- Password File can be displayed.  In order to display or modify
-- this file the MegaPAC's VCP must be accessed directly.

        passFileSize OBJECT-TYPE
            SYNTAX      INTEGER
            ACCESS      read-only
            STATUS      mandatory
            DESCRIPTION
                "Pass File Size.
                The number of entries configured into the PASSWORD
                file."
            ::= { passFile 1 }

-- The Macro File
-- The Macro File is a general purpose file that is used to define
-- complex routing, filtering functions, and or emulation functions.

        macFileSize OBJECT-TYPE
            SYNTAX      INTEGER
            ACCESS      read-only
            STATUS      mandatory
            DESCRIPTION
                "Mac File Size.
                The number of entries configured into the MAC file."
            ::= { macFile 1 }

        macTable OBJECT-TYPE
            SYNTAX      SEQUENCE OF MacEntry
            ACCESS      not-accessible
            STATUS      mandatory
            DESCRIPTION
                "A table of MAC entries"
            ::= { macFile 2 }

        macEntry OBJECT-TYPE
            SYNTAX      MacEntry
            ACCESS      not-accessible
            STATUS      mandatory
            INDEX       { macIndex }
            ::= { macTable 1 }

        MacEntry ::= SEQUENCE { macIndex         INTEGER,
                                macName          DisplayString,
                                macFunction      INTEGER,
                                macOptions       INTEGER,
                                macSelector      DisplayString,
                                macGenerator     DisplayString }

        macIndex OBJECT-TYPE
            SYNTAX      INTEGER
            ACCESS      read-only
            STATUS      mandatory
            DESCRIPTION
                "Index.
                An index to an individual entry in the MAC table."
            ::={ macEntry 1 }

        macName OBJECT-TYPE
            SYNTAX      DisplayString (SIZE(4))
            ACCESS      read-write
            STATUS      mandatory
            DESCRIPTION
                "Name.
                The level 2 controller name to which this entry
                applies."
            ::={ macEntry 2 }

        macFunction OBJECT-TYPE
            SYNTAX      INTEGER { nop(1),      cad(2),      dad(3),      cud(4),
                                  else(5),     fac(6),      inse(16386), dele(16387),
                                  copy(16388), posn(16389), mark(16390), data(16391),
                                  eof(16392),  ibeg(32769), iend(32770), obeg(32771),
                                  oend(32772), pu(32773),   xid(32774),  list(32775),
                                  mask(32776), sync(32777), tab(32778),  rout(32781),
                                  nvmt(32782), add(32783),  bar(32784),  dhcp(32786),
                                  time(32785), dpr(8),      cpr(7) }
            ACCESS      read-write
            STATUS      mandatory
            DESCRIPTION
                "Function.
                The function field determines what action should be
                taken if their is a match on this entry."
            ::={ macEntry 3 }

        macOptions OBJECT-TYPE
            SYNTAX      INTEGER { tlat(99),     rej (2),   tcal(3),  iso (4),
                                  cad (5),      thru(6),   talk(7),  bill(8),
                                  ccit-1980(9), expe(10),  jump(11), copy(12),
                                  none(1),      wipx(161), sap(133), y13(65),
                                  disc(8193),   not(129)}
            ACCESS      read-write
            STATUS      mandatory
            DESCRIPTION
                "Options.
                Specific actions that may be envoked in conjunction
                with the function field."
            ::={ macEntry 4 }

        macSelector OBJECT-TYPE
            SYNTAX      DisplayString (SIZE(0..32))
            ACCESS      read-write
            STATUS      mandatory
            DESCRIPTION
                "Selector.
                This field can contain a string of between 0 and 32
                Hexadecimal characters, that must be matched by the
                Function DAD, CAD, CUD or FAC."
            ::={ macEntry 5 }

        macGenerator OBJECT-TYPE
            SYNTAX      DisplayString (SIZE(0..32))
            ACCESS      read-write
            STATUS      mandatory
            DESCRIPTION
                "Generator.
                This field can contain a string of between 0 and 32
                Hexadecimal characters, and can have different purposes
                depending on the Function or Options fields."
            ::={ macEntry 6 }

-- The ILAN File
-- The ILAN File is used OSI TP0,2,3,4 applications where address
-- mapping of TSAPs (Transport Service Access Points) is required
-- e.g. mapping between TP4 to X25 or IBM 3270 LU sessions etc.

        ilanFileSize OBJECT-TYPE
            SYNTAX      INTEGER
            ACCESS      read-only
            STATUS      mandatory
            DESCRIPTION
                "Ilan File Size.
                The number of entries configured into the ILAN file."
            ::= { ilanFile 1 }

        ilanTable OBJECT-TYPE
            SYNTAX      SEQUENCE OF IlanEntry
            ACCESS      not-accessible
            STATUS      mandatory
            DESCRIPTION
                "A table of ILAN entries"
            ::= { ilanFile 2 }

        ilanEntry OBJECT-TYPE
            SYNTAX      IlanEntry
            ACCESS      not-accessible
            STATUS      mandatory
            INDEX       { ilanIndex }
            ::= { ilanTable 1 }

        IlanEntry ::= SEQUENCE { ilanIndex           INTEGER,
                                 ilanName            DisplayString,
                                 ilanOptions         INTEGER,
                                 ilanEthernetAddress DisplayString,
                                 ilanTSAP            DisplayString }

        ilanIndex OBJECT-TYPE
            SYNTAX      INTEGER
            ACCESS      read-only
            STATUS      mandatory
            DESCRIPTION
                "Index.
                An index to an individual entry in the ILAN table."
            ::={ ilanEntry 1 }

        ilanName OBJECT-TYPE
            SYNTAX      DisplayString (SIZE(4))
            ACCESS      read-write
            STATUS      mandatory
            DESCRIPTION
                "Name.
                The Resource which this entry applies to."
            ::={ ilanEntry 2 }

        ilanOptions OBJECT-TYPE
            SYNTAX      INTEGER { iso(1), expe(2), none(3), y13(16), dbit(4), talk(8) }
            ACCESS      read-write
            STATUS      mandatory
            DESCRIPTION
                "Options
                ISO     Allows transport calls to be set up on the outgoing
                        channel.
                EXPE    Allows expedited data to be sent."
            ::={ ilanEntry 3 }

        ilanEthernetAddress OBJECT-TYPE
            SYNTAX      DisplayString (SIZE(12))
            ACCESS      read-write
            STATUS      mandatory
            DESCRIPTION
                "Ethernet Address.
                The destination MAC address of the named host."
            ::={ ilanEntry 4 }

        ilanTSAP OBJECT-TYPE
            SYNTAX      DisplayString (SIZE(0..20))
            ACCESS      read-write
            STATUS      mandatory
            DESCRIPTION
                "TSAP.
                The Transport Service Access Point required on the
                destination Host."
            ::={ ilanEntry 5 }

-- The Error Log File
-- The Error Log File is used to store any error conditions detected
-- by the MegaPAC.

        elogFileSize OBJECT-TYPE
            SYNTAX      INTEGER
            ACCESS      read-only
            STATUS      mandatory
            DESCRIPTION
                "Elog File Size.
                The size of the error log file."
            ::= { elogFile 1 }

        elogTable OBJECT-TYPE
            SYNTAX      SEQUENCE OF ElogEntry
            ACCESS      not-accessible
            STATUS      mandatory
            DESCRIPTION
                "A table of Error Log entries."
            ::= { elogFile 2 }

        elogEntry OBJECT-TYPE
            SYNTAX      ElogEntry
            ACCESS      not-accessible
            STATUS      mandatory
            INDEX       { elogIndex }
            ::= { elogTable 1 }

        ElogEntry ::= SEQUENCE { elogIndex  INTEGER,
                                 elogRecord DisplayString }

        elogIndex OBJECT-TYPE
            SYNTAX      INTEGER
            ACCESS      read-only
            STATUS      mandatory
            DESCRIPTION
                "Index.
                The index to an Error Log entry."
            ::={ elogEntry 1 }

        elogRecord OBJECT-TYPE
            SYNTAX      DisplayString (SIZE(128))
            ACCESS      read-only
            STATUS      mandatory
            DESCRIPTION
                "Record.
                The Error Log entry in ascii format."
            ::={ elogEntry 2 }

-- TRAPS
             errorLogReport TRAP-TYPE
                      ENTERPRISE  sat
--                    VARIABLES   { elogRecord }
                      DESCRIPTION
                      "Record.
                The Error Log entry in ascii format"
                      ::= 0
-- The Bill File
-- 
-- 
-- 
-- 
-- 

        billFileSize OBJECT-TYPE
            SYNTAX      INTEGER
            ACCESS      read-only
            STATUS      mandatory
            DESCRIPTION
                "Bill File Size.
                The number of entries configured into the BILL file."
            ::= { billFile 1 }

        billTable OBJECT-TYPE
            SYNTAX      SEQUENCE OF BillEntry
            ACCESS      not-accessible
            STATUS      mandatory
            DESCRIPTION
                "A table of 'Bill' entries."
            ::= { billFile 2 }

        billEntry OBJECT-TYPE
            SYNTAX      BillEntry
            ACCESS      not-accessible
            STATUS      mandatory
            INDEX       { billIndex }
            ::= { billTable 1 }

        BillEntry ::= SEQUENCE { billIndex            INTEGER,
                                 billPass             DisplayString,
                                 billDay              INTEGER,
                                 billMonth            INTEGER,
                                 billYear             INTEGER,
                                 billHour             INTEGER,
                                 billMins             INTEGER,
                                 billCause            INTEGER,
                                 billDiagn            INTEGER,
                                 billRev              INTEGER,
                                 billCallm            INTEGER,
                                 billCalls            INTEGER,
                                 billCname            DisplayString,
                                 billRname            DisplayString,
                                 billPrx              DisplayString,
                                 billPtx              DisplayString,
                                 billCrx              DisplayString,
                                 billCtx              DisplayString }

        billIndex OBJECT-TYPE
            SYNTAX      INTEGER
            ACCESS      read-only
            STATUS      mandatory
            DESCRIPTION
                "Index.
                The index into the bill table."
            ::={ billEntry 1 }

        billPass OBJECT-TYPE
            SYNTAX      DisplayString
            ACCESS      read-write
            STATUS      mandatory
            DESCRIPTION
                "Password 
                A string of up to 8 characters in length which is
                typed in by the network user in order to establish
                a connection to a specific resource."
            ::={ billEntry 2 }

        billDay OBJECT-TYPE
            SYNTAX      INTEGER (0..31)
            ACCESS      read-write
            STATUS      mandatory
            DESCRIPTION
                "DAY"     
            ::={ billEntry 3 }

        billMonth OBJECT-TYPE
            SYNTAX      INTEGER (0..12)
            ACCESS      read-write
            STATUS      mandatory
            DESCRIPTION
                "Month "
            ::={ billEntry 4 }

        billYear OBJECT-TYPE
            SYNTAX      INTEGER 
            ACCESS      read-write
            STATUS      mandatory
            DESCRIPTION
                "YEAR"  
            ::={ billEntry 5 }

        billHour OBJECT-TYPE
            SYNTAX      INTEGER 
            ACCESS      read-write
            STATUS      mandatory
            DESCRIPTION
                "Hour"
            ::={ billEntry 6 }

        billMins OBJECT-TYPE
            SYNTAX      INTEGER 
            ACCESS      read-write
            STATUS      mandatory
            DESCRIPTION
                "Mins"
            ::={ billEntry 7 }

        billCause OBJECT-TYPE
            SYNTAX      INTEGER 
            ACCESS      read-write
            STATUS      mandatory
            DESCRIPTION
                "Cause"
            ::={ billEntry 8 }

        billDiagn OBJECT-TYPE
            SYNTAX      INTEGER 
            ACCESS      read-write
            STATUS      mandatory
            DESCRIPTION
                "Diagn"
            ::={ billEntry 9 }

        billRev OBJECT-TYPE
            SYNTAX      INTEGER 
            ACCESS      read-write
            STATUS      mandatory
            DESCRIPTION
                "Rev"
            ::={ billEntry 10}

        billCallm OBJECT-TYPE
            SYNTAX      INTEGER 
            ACCESS      read-write
            STATUS      mandatory
            DESCRIPTION
                "Callm"
            ::={ billEntry 11}

        billCalls OBJECT-TYPE
            SYNTAX      INTEGER 
            ACCESS      read-write
            STATUS      mandatory
            DESCRIPTION
                "Calls"
            ::={ billEntry 12}

        billCname OBJECT-TYPE
            SYNTAX      DisplayString (SIZE(4))
            ACCESS      read-write
            STATUS      mandatory
            DESCRIPTION
                "Cname"
            ::={ billEntry 13}

        billRname OBJECT-TYPE
            SYNTAX      DisplayString (SIZE(4))
            ACCESS      read-write
            STATUS      mandatory
            DESCRIPTION
                "Rname"
            ::={ billEntry 14}

        billPrx OBJECT-TYPE
            SYNTAX      DisplayString (SIZE(4))
            ACCESS      read-write
            STATUS      mandatory
            DESCRIPTION
                "Prx"
            ::={ billEntry 15}

        billPtx OBJECT-TYPE
            SYNTAX      DisplayString (SIZE(4))
            ACCESS      read-write
            STATUS      mandatory
            DESCRIPTION
                "Ptx"
            ::={ billEntry 16}

        billCrx OBJECT-TYPE
            SYNTAX      DisplayString (SIZE(4))
            ACCESS      read-write
            STATUS      mandatory
            DESCRIPTION
                "Crx"
            ::={ billEntry 17}

        billCtx OBJECT-TYPE
            SYNTAX      DisplayString (SIZE(4))
            ACCESS      read-write
            STATUS      mandatory
            DESCRIPTION
                "Ctx"
            ::={ billEntry 18}

END
