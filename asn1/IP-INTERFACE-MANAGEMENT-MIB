IP-INTERFACE-MANAGEMENT-MIB DEFINITIONS ::= BEGIN

-- Referencing the parent branch.

IMPORTS
            MODULE-IDENTITY, OBJECT-TYPE, IpAddress     FROM SNMPv2-SMI
            RowStatus                                   FROM SNMPv2-TC
            cjnMgmt                                     FROM Cajun-ROOT; 

cjnIpIfMgmt MODULE-IDENTITY
        LAST-UPDATED "9902110000Z" -- Friday July 30, 1999"
        ORGANIZATION "Lucent's Concord Technology Center (CTC)"
        CONTACT-INFO
                "Erick Crowell -- ecrowell@lucent.com
                 Ira Steckler -- isteckler@lucent.com"
        DESCRIPTION
                "Cajun Private IP Interface Management MIB"
        ::= { cjnMgmt 1 }


-- IP Interface Extension Group
--
        cjnIpIfGroup            OBJECT IDENTIFIER ::= { cjnIpIfMgmt 1 }

        cjnIpIfNextIndex OBJECT-TYPE
              SYNTAX  INTEGER   
              MAX-ACCESS  read-only
              STATUS  current
              DESCRIPTION
                     "The next available IfIndex. This number should be used to 
        create new rows in the IpIfTable"
              ::= { cjnIpIfGroup 1 }    

        cjnIpIfTable OBJECT-TYPE
              SYNTAX  SEQUENCE OF CjnIpIfEntry
              MAX-ACCESS  not-accessible
              STATUS  current
              DESCRIPTION
                      "A list of Cajun IP interface entries.  The number of
        entries is given by the value of cjnIpIfNumber."
              ::= { cjnIpIfGroup 2 }

        cjnIpIfEntry OBJECT-TYPE
              SYNTAX  CjnIpIfEntry
              MAX-ACCESS  not-accessible
              STATUS  current
              DESCRIPTION
                      "An cajun IP Interface instance "
              INDEX   { cjnIpIfIndex }
              ::= { cjnIpIfTable 1 }

        CjnIpIfEntry ::=
              SEQUENCE {
                cjnIpIfIndex
                        INTEGER,
                cjnIpIfRowStatus
                        RowStatus,      
                cjnIpIfIpAddress
                        IpAddress,
                cjnIpIfIpSubnetMask
                        IpAddress,
                cjnIpIfMacFormat
                        INTEGER,
                cjnIpIfVlanIfIndex
                        INTEGER,
                cjnIpIfName
                        OCTET STRING,
                cjnIpIfIpRouting
                        INTEGER,
                cjnIpIfSpoofCheckEnabled
                        INTEGER,
                cjnIpIfProxyArpEnabled
                        INTEGER,
                cjnIpIfIcmpRedirEnabled
                        INTEGER,
                cjnIpIfUdpRbcastMode
                        INTEGER,
                cjnIpIfAdminStatus
                        INTEGER,
                cjnIpIfStatus
                        INTEGER,
                cjnIpIfBootpDhcpGateway
                        INTEGER
                }
        
        cjnIpIfIndex OBJECT-TYPE
              SYNTAX  INTEGER   
              MAX-ACCESS  read-only
              STATUS  current
              DESCRIPTION
                      "The globally unique identifier for this interface. This number
        MUST correlate with the IfTable's IfIndex in MIB-II or RFC2233"
              ::= { cjnIpIfEntry 1 } 

        cjnIpIfRowStatus OBJECT-TYPE
              SYNTAX  RowStatus 
              MAX-ACCESS  read-create
              STATUS  current
              DESCRIPTION
                      "The Status of this entry in the table.  Note the
        available states: 
        active(1), -- Obviously Active.
        notInService(2) -- Interface configured but disabled.
        notReady(3), -- Interface NOT configured.
        createAndGo(4), 
        createAndWait(5)  
        or destroy(6) "
              ::= { cjnIpIfEntry 2 }

        cjnIpIfIpAddress OBJECT-TYPE
              SYNTAX  IpAddress
              MAX-ACCESS  read-create
              STATUS  current
              DESCRIPTION
                      "The IP Address associated with this IP interface."
              ::= { cjnIpIfEntry 3 } 

        cjnIpIfIpSubnetMask OBJECT-TYPE
              SYNTAX  IpAddress
              MAX-ACCESS  read-create
              STATUS  current
              DESCRIPTION
                      "The IP Subnet Mask associated with this IP interface."
              ::= { cjnIpIfEntry 4 } 

        cjnIpIfMacFormat OBJECT-TYPE
              SYNTAX  INTEGER {
                ethernetV2(0),
                snap(1)
                }       
              MAX-ACCESS  read-create
              STATUS  current
              DESCRIPTION
                      "The ethernet framing type used on this IP interface."
              DEFVAL {0}
              ::= { cjnIpIfEntry 5 }

        cjnIpIfVlanIfIndex OBJECT-TYPE
              SYNTAX      INTEGER   
              MAX-ACCESS  read-create
              STATUS      current
              DESCRIPTION
                      "The interface index of the VLAN or Ethernet or Serial 
        console for this interface.  This number MUST correlate with the 
        IfTable's IfIndex in MIB-II or RFC2233."
              ::= { cjnIpIfEntry 6 }
    
        cjnIpIfName OBJECT-TYPE
              SYNTAX  OCTET STRING (SIZE(0..31))
              MAX-ACCESS  read-create
              STATUS  current
              DESCRIPTION
                      "The protocol Unique name associated with this interface. This
        name is limited to 32 characters and may appear in other protocol interface
        entry such as IPX, Appletalk but MAY NOT be duplicated within the
        cjnIpIfTable.  In otherwords other protocols can use this interface name but
        IP may only have this name associated with one interface."
              ::= { cjnIpIfEntry 7 }

        cjnIpIfIpRouting  OBJECT-TYPE
              SYNTAX INTEGER {
                routingAndMgmt(0),
                mgmtOnly(1),
                routingOnly(2)
                }
              MAX-ACCESS read-create
              STATUS current
              DESCRIPTION
              "The Consumption / Forwarding mode assocated with this IP Interface. 
        The RoutingAndMgmt mode enables IP Routing and local Packet consumption. 
        The MgmtOnly mode disables IP Forwarding but continues to allow local 
        Packet consumption on this interface. The routingOnly mode is disables 
        Local Packet consumption but continues to allow IP Forwarding on this
        interface"
              DEFVAL {2}
              ::= { cjnIpIfEntry 8 }

        cjnIpIfSpoofCheckEnabled OBJECT-TYPE
              SYNTAX  INTEGER {
                enable(1),
                disable(2)
                }       
              MAX-ACCESS  read-create
              STATUS  current
              DESCRIPTION
                      "This feature is not supported at this time."
              ::= { cjnIpIfEntry 9 }

        cjnIpIfProxyArpEnabled OBJECT-TYPE
              SYNTAX  INTEGER {
                enabled(1),
                disabled(2)
                }       
              MAX-ACCESS  read-create
              STATUS  current
              DESCRIPTION
                      "enables / disables Proxy Arp functionality on this interface."
              DEFVAL {2}
              ::= { cjnIpIfEntry 10 }
        
        cjnIpIfIcmpRedirEnabled OBJECT-TYPE
              SYNTAX  INTEGER {
                enabled(1),
                disabled(2)
                }       
              MAX-ACCESS  read-create
              STATUS  current
              DESCRIPTION
                      "enables / disables Icmp Redirect messages from originating from 
        this interface."
              DEFVAL {1}
              ::= { cjnIpIfEntry 11 }

        cjnIpIfUdpRbcastMode OBJECT-TYPE
              SYNTAX  INTEGER {
                disable(0),
                inbound(1),
                outbound(2),
                both(3)
                }       
              MAX-ACCESS  read-create
              STATUS  current
              DESCRIPTION
                      "configures the NetBIOS UDP Rebroadcast mode on this interface."
              DEFVAL {0}
              ::= { cjnIpIfEntry 12 }

        cjnIpIfAdminStatus OBJECT-TYPE
              SYNTAX  INTEGER {
                up(1),
                down(2),
                testing(3)
                }       
              MAX-ACCESS  read-create
              STATUS  current
              DESCRIPTION
                      "The administrative state of this interface."
              ::= { cjnIpIfEntry 13 }

        cjnIpIfStatus OBJECT-TYPE
              SYNTAX  INTEGER {
                up(1),
                down(2)
                }       
              MAX-ACCESS  read-only
              STATUS  current
              DESCRIPTION
                      "The current state of this interface."
              ::= { cjnIpIfEntry 14 }

        cjnIpIfBootpDhcpGateway OBJECT-TYPE
              SYNTAX  INTEGER {
                enable(1),
                disable(2)
                }       
              MAX-ACCESS  read-create
              STATUS  current
              DESCRIPTION
                      "Enable or disable the designation of this interface
                      as that which will 'receive' BOOTP/DHCP requests with a
                      source IP address of 0.0.0.0.  This is used on a multinetted
                      interface when it is otherwise ambiguous as to which interface
                      'receives' the request, and is important because the IP
                      address of the receiving interface is inserted into the giaddr
                      field of the request before the request is relayed to the
                      BOOTP/DHCP server.

                      If this attribute is disabled, then:
                           - if only one IP interface exists on a VLAN, that IP address
                             is inserted into the request
                           - if more than one IP address exists on a VLAN, the router will
                             choose an interface

                      If more than one IP interface on a given VLAN has this attribute enabled,
                      the router will choose an interface among those with the attribute
                      enabled."
              ::= { cjnIpIfEntry 15 }

END
