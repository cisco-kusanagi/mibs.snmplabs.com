-- 
-- Copyright 1999 by Fore Systems, Inc. 
-- Converted to SMIv2 rfc 2578,2579,2580 - STD 58
--
--This mib defines objects for the  FORE proprietary frame Relay extensions.
--Some of the following tables have references to the FORE proprietary
--profiles mibs.



  Fore-frs-MIB  DEFINITIONS ::= BEGIN

      IMPORTS
	   Integer32,
	   TimeTicks,
	   Counter32,
	   Gauge32,
	   OBJECT-TYPE,
	   MODULE-IDENTITY         FROM SNMPv2-SMI
           DisplayString           FROM SNMPv2-TC
           frameInternetworking	   FROM Fore-Common-MIB
	   InterfaceIndex          FROM IF-MIB;

   foreFrameRelayModule MODULE-IDENTITY
     LAST-UPDATED    "9705011044-0400"
     ORGANIZATION    "FORE"
     CONTACT-INFO    "
             Postal: FORE Systems Inc.
                     1000 FORE Drive
                     Warrendale, PA 15086-7502
             Tel:    +1 724 742 6900
             Email:  nm_mibs@fore.com
             Web:    http://www.fore.com"
     DESCRIPTION
             " This MIB is considered as being required in 
             addition to the standard mibs RFC1604 and RFC1315.
             It provides configuration and statistics information 
             at  frame relay service and connection level."
     ::= {frameInternetworking 1}


------------------------------------------------------------------------

-- This table defines entries containing configuration and statistics
-- objects at a frame relay service level

 
       frextDlcmiTable    OBJECT-TYPE
                SYNTAX  SEQUENCE OF FrextDlcmiEntry
                MAX-ACCESS  not-accessible
                STATUS  current
                DESCRIPTION
                        "The Parameters for the Data Link Connection Management
                        Interface corresponding to any given ifEntry.
                        These parameters are logical extensions to those in
                        contained within the object frDlcmiTable in RFC1315."
                ::= { foreFrameRelayModule 1 }

        frextDlcmiEntry    OBJECT-TYPE
                SYNTAX  FrextDlcmiEntry
                MAX-ACCESS  not-accessible
                STATUS  current
                DESCRIPTION
                        "The Parameters for the  Data  Link  Connection
                        Management Interface."
                INDEX   { frextDlcmiServiceIfIndex }
                ::= { frextDlcmiTable 1 }

        FrextDlcmiEntry ::= SEQUENCE {
                        frextDlcmiServiceIfIndex
                                InterfaceIndex,
                        frextDlcmiProfileLmiIndex
                                Integer32,
                        frextDlcmiProfileServiceIndex
                                Integer32,
                        frextDlcmiStatsMonitor
                                INTEGER,
                        frextDlcmiStatsEnabledTimeStamp
                                TimeTicks,
                        frextDlcmiLmiDlci
                                Integer32,
                        frextDlcmiLmiFlowControl
                                INTEGER,
                        frextDlcmiRAControl
                                INTEGER,
                        frextDlcmiLmiBandwidthControl
                                INTEGER,
                        frextDlcmiRxAbortedFrames
                                Counter32,
                        frextDlcmiRcvCrcErrors
                                Counter32,
                        frextDlcmiRcvShortFrames
                                Counter32,
                        frextDlcmiRcvLongFrames
                                Counter32,
                        frextDlcmiRcvInvalidDLCI
                                Counter32,
                        frextDlcmiRcvUnknownErrs
                                Counter32,
                        frextDlcmiLmiTxStatusResponses
                                Counter32,
                        frextDlcmiLmiTxFullStatusResponses
                                Counter32,
                        frextDlcmiLmiTxStatusEnquiries
                                Counter32,
                        frextDlcmiLmiTxFullStatusEnquiries
                                Counter32,
                        frextDlcmiLmiRxStatusResponses
                                Counter32,
                        frextDlcmiLmiRxFullStatusResponses
                                Counter32,
                        frextDlcmiLmiRxStatusEnquiries
                                Counter32,
                        frextDlcmiLmiRxFullStatusEnquiries
                                Counter32,
                        frextDlcmiLmiUnknownMessagesRcvd
                                Counter32,
                        frextDlcmiLmiStatusLostSequences
                                Counter32,
                        frextDlcmiLmiStatusEnqLostSequences
                                Counter32,
                        frextDlcmiLmiMissingStatEnquiries
                                 Counter32,
                        frextDlcmiLmiUnexpectedPVCStatMsg
                                 Counter32,
                        frextDlcmiLmiUnexpectedDLCI
                                 Counter32,
                        frextDlcmiLmiStatEnqRatePlus
                                 Counter32,
                        frextDlcmiLmiInvInfoFrame 
                                 Counter32,
                        frextDlcmiLmiInvFrameHdr
                                 Counter32,
                        frextDlcmiLmiNoIERepType
                                 Counter32,
                        frextDlcmiLmiNoIEKeepAlive
                                 Counter32,
                        frextDlcmiLmiMissingResponses
                                 Counter32,
                        frextDlcmiLmiUnsuppIERcvd
                                 Counter32,
                        frextDlcmiPvccs
                                 Gauge32
                        }


          frextDlcmiServiceIfIndex  OBJECT-TYPE
                SYNTAX  InterfaceIndex
                MAX-ACCESS  read-only
                STATUS  current
                DESCRIPTION
                "The Service/FR-UNI identifier ifIndex value of the  
                corresponding ifEntry."
                ::= { frextDlcmiEntry 1 }

          frextDlcmiProfileLmiIndex   OBJECT-TYPE
                SYNTAX  Integer32     
                MAX-ACCESS  read-write
                STATUS  current
                DESCRIPTION
                "Index  for the LMI profile for this FR service."
                DEFVAL { 0 }
                ::= { frextDlcmiEntry 2 }


          frextDlcmiProfileServiceIndex OBJECT-TYPE
                SYNTAX  Integer32     
                MAX-ACCESS  read-write
                STATUS  current
                DESCRIPTION
                "Index  of the  Service  profile for this FR service."
                DEFVAL { 0 }
                ::= { frextDlcmiEntry 3 }

 

          frextDlcmiStatsMonitor   OBJECT-TYPE
                SYNTAX  INTEGER {
                                enabled (1),
                                disabled (2)
                                }
                MAX-ACCESS  read-write
                STATUS  current
                DESCRIPTION
                "This object specifies whether statistics are to be counted at
                a service level, this includes service and connection
                statistics. When the state changes from enabled to disabled 
                all the related statistics will be frozen at their current 
                value. When the state changes from disabled to enabled then 
                all related statistics will be reset (zeroised). Note that 
                this Monitor is overriden by the netmod level 
                nmFramStatsMonitor. Refer to fore-fram.mib for more details."
                DEFVAL { disabled }
                ::= { frextDlcmiEntry 4 }

          frextDlcmiStatsEnabledTimeStamp  OBJECT-TYPE
                SYNTAX  TimeTicks
                MAX-ACCESS  read-only
                STATUS  current
                DESCRIPTION
                "This object reflects the point in time, with reference to 
                sysUpTime, either when frextDlcmiStatsMonitor is set to 
                enabled or when nmFramStatsMonitor is set to enabled. The
                time will reflect the last StatsMonitor to be enabled. The 
                timestamp provides a starting timestamp for the current 
                statistics that are being counted." 
                ::=  { frextDlcmiEntry 5 }

          frextDlcmiLmiDlci  OBJECT-TYPE
                SYNTAX  Integer32
                MAX-ACCESS  read-only
                STATUS  current
                DESCRIPTION
                " the dlci upon which LMI traffic will be broadcast.
                If Q933-AnnexA=0, otherwise STRATACOM=1023."
                ::= { frextDlcmiEntry  6 }


          frextDlcmiLmiFlowControl   OBJECT-TYPE
                SYNTAX  INTEGER {
                                enabled(1),
                                disabled(2)
                                }
                MAX-ACCESS  read-write
                STATUS  current
                DESCRIPTION
                "Specifies whether STRATACOM LMI based (R-bit) 
                notification performs flow control for the 
                Circuits on this interface."
                DEFVAL {disabled}
                ::= { frextDlcmiEntry 7 }

          frextDlcmiRAControl  OBJECT-TYPE
                SYNTAX  INTEGER {
                                enabled(1),
                                disabled(2)
                                }
                MAX-ACCESS  read-write
                STATUS  current
                DESCRIPTION
                "Specifies whether Rate Adaptation-RA performs
                flow control for the Circuits on this interface."
                DEFVAL{disabled}
                ::= { frextDlcmiEntry 8 }

          frextDlcmiLmiBandwidthControl   OBJECT-TYPE
                SYNTAX  INTEGER {
                                enabled(1),
                                disabled(2)
                                }
                MAX-ACCESS  read-write
                STATUS  current
                DESCRIPTION
                "Specifies whether STRATACOM LMI based CIR
                notification affects the CIR flow control
                parameters for the connections on this interface."
                DEFVAL{disabled}
                ::= { frextDlcmiEntry 9 }

          frextDlcmiRxAbortedFrames  OBJECT-TYPE
                SYNTAX    Counter32
                MAX-ACCESS    read-only
                STATUS    current
                DESCRIPTION
                "The number of aborted frames received on this
                Frame Relay logical interface.A frame is considered
                aborted after receiving 7 or more continuous ones."
                ::= {frextDlcmiEntry 10 }


          frextDlcmiRcvCrcErrors   OBJECT-TYPE
                SYNTAX   Counter32
                MAX-ACCESS   read-only
                STATUS   current
                DESCRIPTION
                "Specifies the number of frames receive with CRC errors on 
                this interface."
                ::= { frextDlcmiEntry 11 }


          frextDlcmiRcvShortFrames OBJECT-TYPE
                SYNTAX   Counter32
                MAX-ACCESS   read-only
                STATUS   current
                DESCRIPTION
                "The number of frames containing less than 5
                octets received on this interface."
                ::= { frextDlcmiEntry  12 }

          frextDlcmiRcvLongFrames OBJECT-TYPE
                SYNTAX   Counter32
                MAX-ACCESS   read-only
                STATUS   current
                DESCRIPTION
                "The number of frames containing greater than 8191
                octets received on this interface."
                ::= { frextDlcmiEntry 13 }

          frextDlcmiRcvInvalidDLCI OBJECT-TYPE
                SYNTAX   Counter32
                MAX-ACCESS   read-only
                STATUS   current
                DESCRIPTION
                "The number of frames with an invalid DLCI received
                on this interface."
                ::= { frextDlcmiEntry 14 }

  
         frextDlcmiRcvUnknownErrs OBJECT-TYPE
               SYNTAX   Counter32
               MAX-ACCESS   read-only
               STATUS   current
               DESCRIPTION
               "The number of frames with other errors received
               on this interface."
               ::= { frextDlcmiEntry 15 }


          frextDlcmiLmiTxStatusResponses OBJECT-TYPE
                SYNTAX  Counter32
                MAX-ACCESS  read-only
                STATUS  current
                DESCRIPTION   
                "Number of STATUS messages transmited on this interface."
                ::= { frextDlcmiEntry  16 }

          frextDlcmiLmiTxFullStatusResponses   OBJECT-TYPE
                SYNTAX  Counter32
                MAX-ACCESS  read-only
                STATUS  current
                DESCRIPTION   
                "Number of  STATUS  messages with full status IE transmited 
                on this interface."
                ::= { frextDlcmiEntry  17 }


          frextDlcmiLmiTxStatusEnquiries OBJECT-TYPE
                SYNTAX  Counter32
                MAX-ACCESS  read-only
                STATUS  current
                DESCRIPTION   
                "Number of STATUS ENQUIRY messages transmited on this 
                interface."
                ::= { frextDlcmiEntry 18 }


          frextDlcmiLmiTxFullStatusEnquiries     OBJECT-TYPE
                SYNTAX  Counter32
                MAX-ACCESS  read-only
                STATUS  current
                DESCRIPTION   
                "Number of STATUS ENQUIRY  messages with full status IE 
                transmited on this interface."
                ::= { frextDlcmiEntry 19 }

          frextDlcmiLmiRxStatusResponses       OBJECT-TYPE
                SYNTAX  Counter32
                MAX-ACCESS  read-only
                STATUS  current
                DESCRIPTION   
                "Number of STATUS  messages received on this interface."
                ::= { frextDlcmiEntry 20 }

          frextDlcmiLmiRxFullStatusResponses        OBJECT-TYPE
                SYNTAX  Counter32
                MAX-ACCESS  read-only
                STATUS  current
                DESCRIPTION   
                " Number of STATUS messages with full status IE received 
                on this interface."
                ::= { frextDlcmiEntry 21 }

          frextDlcmiLmiRxStatusEnquiries   OBJECT-TYPE
                SYNTAX  Counter32
                MAX-ACCESS  read-only
                STATUS  current
                DESCRIPTION   
                "Number of STATUS messages received on this interface."
                ::= { frextDlcmiEntry 22 }

          frextDlcmiLmiRxFullStatusEnquiries OBJECT-TYPE
                SYNTAX  Counter32
                MAX-ACCESS  read-only
                STATUS  current
                DESCRIPTION   
                " Number of STATUS ENQUIRY  messages with full status IE
                (Information Element) receive on this interface."
                ::= { frextDlcmiEntry 23 }

   
          frextDlcmiLmiUnknownMessagesRcvd  OBJECT-TYPE
               SYNTAX  Counter32
               MAX-ACCESS  read-only
               STATUS  current
               DESCRIPTION   
               "Number of Unknown LMI messages received on this interface."
               ::= { frextDlcmiEntry  24 }


         frextDlcmiLmiStatusLostSequences OBJECT-TYPE
              SYNTAX   Counter32
              MAX-ACCESS   read-only
              STATUS   current
              DESCRIPTION
              "The total number of times a loss of sequencing in received 
              STATUS  messages was detected on this interface."
              ::= { frextDlcmiEntry  25 }


        frextDlcmiLmiStatusEnqLostSequences OBJECT-TYPE
              SYNTAX   Counter32
              MAX-ACCESS   read-only
              STATUS   current
              DESCRIPTION
              "The total number of times a loss of sequencing in received 
              STATUS ENQUIRY  messages was detected on this interface."
              ::= { frextDlcmiEntry  26 }


        frextDlcmiLmiMissingStatEnquiries  OBJECT-TYPE
              SYNTAX   Counter32
              MAX-ACCESS   read-only
              STATUS   current
              DESCRIPTION
              "The number of times an expected STATUS ENQUIRY message
              was not received within the expected time on this interface."
              ::= { frextDlcmiEntry 27 }


        frextDlcmiLmiUnexpectedPVCStatMsg OBJECT-TYPE
              SYNTAX   Counter32
              MAX-ACCESS   read-only
              STATUS   current
              DESCRIPTION
              "The number of LMI messages that were received with unexpected 
              PVC STATUS IE on this interface."
              ::= { frextDlcmiEntry 28 }


       frextDlcmiLmiUnexpectedDLCI  OBJECT-TYPE
             SYNTAX   Counter32
             MAX-ACCESS   read-only
             STATUS   current
             DESCRIPTION
             "The number of STATUS messages received with unconfigured 
             DLCI"
             ::= { frextDlcmiEntry 29 }

       frextDlcmiLmiStatEnqRatePlus  OBJECT-TYPE
             SYNTAX   Counter32
             MAX-ACCESS   read-only
             STATUS   current
             DESCRIPTION
             "The number of times the STATUS ENQUIRY message was received
             more frequently than expected. For STRATACOM only"
            ::= { frextDlcmiEntry 30 }

       frextDlcmiLmiInvInfoFrame OBJECT-TYPE
             SYNTAX   Counter32
             MAX-ACCESS   read-only
             STATUS   current
             DESCRIPTION
             "The number of times an LMI message was received with 
             information type not equal to unnumbered information type."
             ::= { frextDlcmiEntry 31 }


       frextDlcmiLmiInvFrameHdr  OBJECT-TYPE
             SYNTAX   Counter32
             MAX-ACCESS   read-only
             STATUS   current
             DESCRIPTION
             "The number of LMI frames received with error in the header
             bits."
             ::= { frextDlcmiEntry 32 }


       frextDlcmiLmiNoIERepType  OBJECT-TYPE
             SYNTAX   Counter32
             MAX-ACCESS   read-only
             STATUS   current
             DESCRIPTION
             "The number of times an LMI frame was received with missing 
             Report Type IE"
             ::= { frextDlcmiEntry 33 }


       frextDlcmiLmiNoIEKeepAlive OBJECT-TYPE
             SYNTAX   Counter32
             MAX-ACCESS   read-only
             STATUS   current
             DESCRIPTION
             "The number of times an LMI frame was received with missing 
             Link Integrity Verification IE."
             ::= { frextDlcmiEntry 34 }


       frextDlcmiLmiMissingResponses OBJECT-TYPE
             SYNTAX   Counter32
             MAX-ACCESS   read-only
             STATUS   current
             DESCRIPTION
             "The total number of times a timeout occurred without 
             receiving a response to an LMI request by this interface."
             ::= { frextDlcmiEntry 35}

       frextDlcmiLmiUnsuppIERcvd  OBJECT-TYPE  
             SYNTAX  Counter32
             MAX-ACCESS  read-only
             STATUS  current
             DESCRIPTION
             "The number of LMI messages received with unknown Information
             Element."
             ::= { frextDlcmiEntry 36 }

       frextDlcmiPvccs  OBJECT-TYPE  
             SYNTAX  Gauge32
             MAX-ACCESS  read-only
             STATUS  current
             DESCRIPTION
             "The number of permanent VCCs established on this Frame Relay
             logical interface"
             ::= { frextDlcmiEntry 37 }


----------------------------------------------------------------------------

-- This table defines entries containing configuration and statistics
-- objects at frame relay connection level


         frextCircuitTable  OBJECT-TYPE
             SYNTAX   SEQUENCE OF FrextCircuitEntry
             MAX-ACCESS   not-accessible
             STATUS   current
             DESCRIPTION
             "A table containing information about specific Data
              Link Connection Identifiers and corresponding 
              connections."
                ::= { foreFrameRelayModule 2 }

         frextCircuitEntry OBJECT-TYPE
             SYNTAX   FrextCircuitEntry
             MAX-ACCESS   not-accessible
             STATUS   current
             DESCRIPTION
             "The information regarding a single  Data  Link
             Connection Identifier."
             INDEX   {frextCircuitServiceIfIndex, frextCircuitDlci }
                ::= { frextCircuitTable 1 }

        FrextCircuitEntry ::=
                SEQUENCE {
                        frextCircuitServiceIfIndex
                                InterfaceIndex,
                        frextCircuitDlci
                                Integer32,
                        frextCircuitName
                                DisplayString,
                        frextCircuitProfileFrRateIndex
                                Integer32,
                        frextCircuitREMonitor
                                INTEGER,
                        frextCircuitRateFallbacks
                                Counter32,
                        frextCircuitRateFallforwards
                                Counter32,
                        frextCircuitEgFramesDroppedQueueFull
                                Counter32,
                        frextCircuitNormalSentFrames
                                Counter32,
                        frextCircuitNormalSentOctets 
                                Counter32,
                        frextCircuitExcessSentOctets
                                Counter32,
                        frextCircuitHeldBuffers
                                Counter32,
                        frextCircuitOctetsOnQueue
                                Counter32,
                        frextCircuitBuffersOnQueue
                                Counter32,
                        frextCircuitRxMonNormalFrames
                                Counter32,
                        frextCircuitRxMonNormalOctets 
                                Counter32,
                        frextCircuitRxMonExcessOctets
                                Counter32,
                        frextCircuitRxMonDroppedOctets
                                Counter32,
                        frextCircuitRxMonDroppedDEFrames
                                Counter32,
                        frextCircuitRxMonDroppedDEOctets
                                Counter32,
                        frextCircuitRxMonDEOctets
                                Counter32,
                        frextCircuitRxMonSetDEFrames
                                Counter32,
                        frextCircuitRxMonSetDEOctets
                                Counter32,
                        frextCircuitRecvdBECNS
                                Counter32,
                        frextCircuitRecvdFECNS
                                Counter32
                        }

        frextCircuitServiceIfIndex OBJECT-TYPE
                SYNTAX  InterfaceIndex
                MAX-ACCESS  read-only
                STATUS  current
                DESCRIPTION
                "IfIndex of the Frame Relay Interface,UNI, to which 
                 data received from ATM is forwarded.The index generated
                 by the agent for Frame Relay service identification. 
                 This index is volatile over power down "
                ::= { frextCircuitEntry 1 }

        frextCircuitDlci       OBJECT-TYPE
                SYNTAX  Integer32
                MAX-ACCESS  read-only
                STATUS  current
                DESCRIPTION
                "The connections' Frame Relay DLCI."
                ::= {frextCircuitEntry  2 }


        frextCircuitName        OBJECT-TYPE
                SYNTAX  DisplayString
                MAX-ACCESS  read-write
                STATUS  current
                DESCRIPTION
                "The user-defined name for the connection."
                ::= { frextCircuitEntry 3 }


        frextCircuitProfileFrRateIndex   OBJECT-TYPE
                SYNTAX   Integer32
                MAX-ACCESS   read-write
                STATUS   current
                DESCRIPTION
                "Index  of the ProfileFRRateTable  (rate enforcement/rate
                adaptation configuration for this FR/ATM interworking
                connection"
                DEFVAL { 0 }
                ::= {frextCircuitEntry 4 }

        frextCircuitREMonitor  OBJECT-TYPE
            SYNTAX INTEGER {
                        none(1),
                        standard(2) 
                        }
                MAX-ACCESS   read-write
                STATUS   current
                DESCRIPTION
                "This object enables or disables the monitoring
                of Bc, Be and CIR on the Rx side of the connection,
                called Rate Enforcement.If set to none, no
                monitoring will be performed.
                If set to standard, Rx monitoring will drop any 
                frames received in excess of Be, and will tag 
                frames received in between Bc and Be"
                DEFVAL { none }
                ::= { frextCircuitEntry 5 }
                                
        frextCircuitRateFallbacks OBJECT-TYPE
                SYNTAX  Counter32
                MAX-ACCESS  read-only
                STATUS  current
                DESCRIPTION
                "The number of times that the insertion rate was
                lowered (due to network congestion reports) since
                the connection was created."
                ::= { frextCircuitEntry 6 }

        frextCircuitRateFallforwards OBJECT-TYPE
                SYNTAX  Counter32
                MAX-ACCESS  read-only
                STATUS  current
                DESCRIPTION
                "The number of times that the insertion rate was
                increased  (due to lack of network congestion reports) 
                since the connection was created."
                ::= { frextCircuitEntry 7 }

 
        frextCircuitEgFramesDroppedQueueFull OBJECT-TYPE
                SYNTAX  Counter32
                MAX-ACCESS  read-only
                STATUS  current
                DESCRIPTION
                "Number of frames which were dropped on this connection
                because the hold queue was full."
                ::= { frextCircuitEntry 8 }


        frextCircuitNormalSentFrames    OBJECT-TYPE
                SYNTAX  Counter32
                MAX-ACCESS  read-only
                STATUS  current
                DESCRIPTION
                "Number of frames sent on this connection 
                within the Commited Information Rate since the
                connection was created."
                  ::= { frextCircuitEntry 9 }

        frextCircuitNormalSentOctets OBJECT-TYPE
                SYNTAX  Counter32
                MAX-ACCESS  read-only
                STATUS  current
                DESCRIPTION
                "Number of octets sent on this  connection
                within the Commited Information Rate since the
                connection was created."
                ::= { frextCircuitEntry 10 }

        frextCircuitExcessSentOctets OBJECT-TYPE
                SYNTAX  Counter32
                MAX-ACCESS  read-only
                STATUS  current
                DESCRIPTION
                "Number of octets sent on this  connection above the 
                Commited Information Rate, but below the Excess Information 
                Rate since the connection was created."
                ::= { frextCircuitEntry 11 }

        frextCircuitHeldBuffers OBJECT-TYPE
                SYNTAX  Counter32
                MAX-ACCESS  read-only
                STATUS  current
                DESCRIPTION
                "Number of buffers which were used  by the connection
                for enqueueing frames in preference to exceeding the  
                allowed burst rate on this connection since the connection 
                was created."
                ::= { frextCircuitEntry 12 }

        frextCircuitOctetsOnQueue OBJECT-TYPE
                SYNTAX  Counter32
                MAX-ACCESS  read-only
                STATUS  current
                DESCRIPTION
                "Number of octets currently  being used for enqueueing
                frames in order to be transmited."
                ::= { frextCircuitEntry 13 }

        frextCircuitBuffersOnQueue OBJECT-TYPE
                SYNTAX  Counter32
                MAX-ACCESS  read-only
                STATUS  current
                DESCRIPTION
                "Number of buffers currently  being used for enqueueing
                frames in order to be transmited."
                ::= { frextCircuitEntry 14 }

        frextCircuitRxMonNormalFrames OBJECT-TYPE
                SYNTAX  Counter32
                MAX-ACCESS  read-only
                STATUS  current
                DESCRIPTION
                "The number of frames received on the connection
                 within the committed burst (Bc)."
                ::= { frextCircuitEntry 15 }

        frextCircuitRxMonNormalOctets OBJECT-TYPE
                SYNTAX  Counter32
                MAX-ACCESS  read-only
                STATUS  current
                DESCRIPTION
                "The number of octets received on the connection
                 within the committed burst (Bc)."
                ::= { frextCircuitEntry 16 }


        frextCircuitRxMonExcessOctets OBJECT-TYPE
                SYNTAX  Counter32
                MAX-ACCESS  read-only
                STATUS  current
                DESCRIPTION
                "The number of octets received on the connection
                 within the excess burst (Be)."
                ::= { frextCircuitEntry 17 }


        frextCircuitRxMonDroppedOctets OBJECT-TYPE
                SYNTAX  Counter32
                MAX-ACCESS  read-only
                STATUS  current
                DESCRIPTION
                "The number of octets received on the connection
                that were dropped because they were in excess
                Bc+Be."
                ::= { frextCircuitEntry 18}
 

        frextCircuitRxMonDroppedDEFrames  OBJECT-TYPE
                SYNTAX  Counter32
                MAX-ACCESS  read-only
                STATUS  current
                DESCRIPTION
                "The number of  frames with the DE bit set received 
                on the connection that were dropped."
                ::= { frextCircuitEntry 19}


        frextCircuitRxMonDroppedDEOctets OBJECT-TYPE
                SYNTAX  Counter32
                MAX-ACCESS  read-only
                STATUS  current
                DESCRIPTION
                "The number of octets in frames with the DE bit
                 set received on the connection that were dropped."
                ::= { frextCircuitEntry 20 }

        frextCircuitRxMonDEOctets OBJECT-TYPE
                SYNTAX  Counter32
                MAX-ACCESS  read-only
                STATUS  current
                DESCRIPTION
                "The number of octets with the DE bit set that
                 were received on the connection."
                ::= { frextCircuitEntry 21 }

        frextCircuitRxMonSetDEFrames OBJECT-TYPE
                SYNTAX  Counter32
                MAX-ACCESS  read-only
                STATUS  current
                DESCRIPTION
                "The number of frames received on the connection
                 in which the Rx monitor set the DE bit."
                ::= { frextCircuitEntry 22 }

        frextCircuitRxMonSetDEOctets OBJECT-TYPE
                SYNTAX  Counter32
                MAX-ACCESS  read-only
                STATUS  current
                DESCRIPTION
                "The number of octets in frames received on the
                 connection in which the Rx monitor set the DE bit."
                ::= { frextCircuitEntry 23 }


        frextCircuitRecvdBECNS  OBJECT-TYPE
                SYNTAX  Counter32
                MAX-ACCESS  read-only
                STATUS  current
                DESCRIPTION
                "Number of frames received from the network in-
                dicating  forward  congestion since the connection was 
                created. This object is defined in this table to provide
                the same object as defined in RFC 1315, while the interface 
                is defined as a DCE."
                ::= { frextCircuitEntry 24}


        frextCircuitRecvdFECNS  OBJECT-TYPE
                SYNTAX  Counter32
                MAX-ACCESS  read-only
                STATUS  current
                DESCRIPTION
                "Number of frames received from the network in-
                dicating  backward congestion since the connection was 
                created.This object is defined in this table to provide 
                the same object as defined in RFC 1315, while the interface 
                is defined as a DCE."
                ::= { frextCircuitEntry 25}

          
---------------------------------------------------------------
--
-- OAM F5 for FR/ATM
--
-- This table provides information on a per VCC basis
-- keeping the statistics of the OAM F5 end-to-end
-- cells

frsOamF5Table    OBJECT-TYPE
	       SYNTAX    SEQUENCE OF FrsOamF5Entry
	       MAX-ACCESS    not-accessible
	       STATUS    current
	       DESCRIPTION
	       "The OAM statistics table on a VCC basis"
	       ::= { foreFrameRelayModule 3 }


frsOamF5Entry    OBJECT-TYPE
	       SYNTAX    FrsOamF5Entry
	       MAX-ACCESS    not-accessible
	       STATUS    current
	       DESCRIPTION
	       "An Entry in the OAM F5 statistics table on a VCC basis"
	       INDEX {frsOamF5AtmIf, frsOamF5AtmVpi, frsOamF5AtmVci}
	       ::={ frsOamF5Table 1}


FrsOamF5Entry ::= SEQUENCE {
	       frsOamF5AtmIf
		    Integer32,
	       frsOamF5AtmVpi
		    Integer32,
	       frsOamF5AtmVci
		    Integer32,
	       frsOamF5AISRxCounter
		    Counter32,
	       frsOamF5AISTxCounter
		    Counter32,
	       frsOamF5RDIRxCounter
		    Counter32,
	       frsOamF5RDITxCounter
		    Counter32
		}


frsOamF5AtmIf OBJECT-TYPE
		SYNTAX  Integer32
		MAX-ACCESS  read-only
		STATUS  current
		DESCRIPTION
		"The Atm interface index corresponds to the port.
		 This is also the index of the portTable."
		::= { frsOamF5Entry 1 }

frsOamF5AtmVpi  OBJECT-TYPE
		SYNTAX  Integer32
		MAX-ACCESS  read-only
		STATUS  current
		DESCRIPTION
		"VPI of the ATM VCC on which FR DLCI maps onto"
		::= { frsOamF5Entry 2 }

frsOamF5AtmVci  OBJECT-TYPE
		SYNTAX  Integer32
		MAX-ACCESS  read-only
		STATUS  current
		DESCRIPTION
		"VCI of the ATM VCC on which FR DLCI maps onto"
		::= { frsOamF5Entry 3 }

frsOamF5AISRxCounter    OBJECT-TYPE
	       SYNTAX    Counter32
	       MAX-ACCESS    read-only
	       STATUS    current
	       DESCRIPTION
	       "Number of VC-AIS cells received since the PVC was
	       brought into service."
	       ::={frsOamF5Entry 4}


frsOamF5AISTxCounter    OBJECT-TYPE
	       SYNTAX    Counter32
	       MAX-ACCESS    read-only
	       STATUS    current
	       DESCRIPTION
	       "Number of VC-AIS cells transmited since the PVC was
	       brought into service."
	       ::={frsOamF5Entry 5}

frsOamF5RDIRxCounter    OBJECT-TYPE
	       SYNTAX    Counter32
	       MAX-ACCESS    read-only
	       STATUS    current
	       DESCRIPTION
	       "Number of VC-RDI cells received since the PVC was
	       brought into service."
	       ::={frsOamF5Entry 6}


frsOamF5RDITxCounter    OBJECT-TYPE
	       SYNTAX    Counter32
	       MAX-ACCESS    read-only
	       STATUS    current
	       DESCRIPTION
	       "Number of VC-RDI cells transmited since the PVC was
	       brought into service."
	       ::={frsOamF5Entry 7}




     END
