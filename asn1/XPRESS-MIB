--
--                           RAC-MIB
--
--                      Gandalf Division of 
--                      Mitel Corproration.
--
--                      3026 Solandt Rd.
--                      Kanata, Ontario,
--                      Canada, K2K 1X3
--                      (613) 592-3636
--
--                      Questions?
--                         1-800-GANDALF (N.A. only)
--
--                      Jan 15, 1999
--
--                      Version 4.4.0
--
--
--
--                         Introduction
--
-- The RAC SNMP agent supports three separate management
-- information base (MIB) definitions.
--
-- An SNMP MIB has been defined for the XpressWay RLAN and the XpressStack;
-- the "RAC MIB". In addition to this MIB, the RAC SNMP agent also 
-- supports most of the groups from MIB-II (reference rfc 1158 and 1213) and
-- the ganEventLogTable from the Gandalf Generic MIB.
--
-- The "RAC MIB" consists of many attributes which are divided
-- into groups that can be read or configured by an SNMP Manager.
-- The "RAC MIB" is largely a proprietary implementation.
--
-- The RAC SNMP agent supports GETs, GET_NEXTs and SETs commands
-- for most attributes contained in the MIBs the agent supports.
--
-- The following document describes, in ASN.1, the RAC MIB.
--
--
--
--                      MIB Description
--
--        MIB-II groups supported by the RAC SNMP agent
--
-- Gandalf's implementation of MIB-II  follows  recommendations
-- from  RFC  1158.  This  has subsequently been updated to RFC
-- 1213.  RFC 1213 identifies ten groups that can optionally be
-- supported.   Gandalf chose to support the following 8 groups
-- for the RAC SNMP agent:
--
--
-- 1.   The System Group:
--        This group provides  contact,  administrative,
--        location,  and  service information regarding the 
--        managed device.
--
--
-- 2.   The Interface Group:
--        This group provides information  about  the  device's
--        interfaces.  Currently, only 1 interface is defined
--        for MIB II's Interface Group. It is :
--
--        a)   The Local LAN port.
--
--
-- 3.   The Address Translation Group:
--        This group contains a table  which  permits  mappings
--        from network addresses (e.g., IP addresses) to physi-
--        cal addresses (e.g., MAC addresses).  This  table  is
--        maintained by the system's Protocol Stack.
--
--
-- 4.   The IP Group:
--        This table provides information about the  system's
--        Protocol  Stack  IP layer.  Note that the ipRoutingT-
--        able is not supported by the system's SNMP agent.
--
--
-- 5.   The ICMP Group:
--        This table provides information  about  ICMP  traffic
--        addressed  to the system's Protocol Stack.  An exam-
--        ple would be PING packets.
--
--
-- 6.   The TCP Group:
--        This group provides information about the system's
--        Protocol  Stack TCP layer.  The TCP table can be use-
--        ful to monitor the amount  of  traffic  generated  by
--        operators  remotely  connecting  to the console.  The
--        tcpConn table can be useful to see who  is  currently
--        remotely connected to the console.
--
--
-- 7.   The UDP Group:
--        This group provides information about the system's
--        Protocol  Stack  UDP  layer.  The udpConn table shows
--        what protocols sitting on top of  UDP  are  listening
--        for packets (for example SNMP (port 161) or RIP (port
--        57)).
--
--
-- 8.   The SNMP Group:
--        This group provides information about the  system's
--        Protocol Stack SNMP layer.  It will give indications,
--        for example, on how much traffic or  how  many  TRAPs
--        the device's SNMP agent generates.
--
--      The RAC SNMP agent supports the following from the 
--      Gandalf Generic Group:
--      The  Event Log Group:
--        This group provides information about the system's
--        Event Log Messages. Along with the description, it also
--        provides information such as the time, date and severity of the
--        event.
-- 
--
--      RAC MIB groups supported by the RAC SNMP agent
--
-- 1.   The System Group.
--        This group is a complement to MIB II's System group.
--        It  contains  detailed information at the Box level e.g.,
--        diagnostics, eeprom rev, etc...
--
--
-- 2.   The Card Group.
--        This group is responsible for giving detailed  infor-
--        mation  for  each  of the possible I/O cards in the
--        system. This group defines a table,  indexed
--        by card numbers relative to the P2 backplane.
--
--        The RAC SNMP agent will let the Manager create and
--        delete cards through SNMP SETS. If a SET request is received with 
--        a valid rCardType and the rCardRowStatus attribute set to 
--        'createAndGo', the agent will CREATE a new card object.
--
--        If a SET request is received with the attribute rCardRowStatus
--        having the value of 'destroy', the card will be deleted from 
--        the system's database, only if no calls are currently
--        active on the card.If calls are active, a BAD_VALUE_ERROR will 
--        be returned to the Manager.
--
--        If the Manager SETs the rCardStatus attribute  to  the
--        OFFLINE  value, then all active calls will be dropped
--        and the card will be put into an OFFLINE state.
--
--
-- 3.   The D Channels group.
--        This group contains attributes used to configure D Channels 
--        and to monitor their statistics. The  group  defines two 
--        tables, both indexed by card number relative to P2 backplane and
--        by the 'S'interface on the I/O card.
--
--
-- 4.   The Channel group.
--        This group contains tables used to configure data-bearing 
--        channels and to monitor their statistics. These tables are indexed 
--        by card number relative  to  the  P2 backplane, 'S' interface on 
--        the I/O card  and one of the possible B Channels on the S Interface 
--        (except for the rlanChannelGroupTable).
--
--        It will not be possible to create or delete data-bearing Channels
--        through SNMP  SETs.
--
--        The read-only attributes will contain cumulative statistics 
--        of the particular data-bearing Channel since the last system reset.
--
--        In order to find out the CURRENT  statistics  of  a  particular  
--        data-bearing Channel,  you have  to  use the rSyncChanWanIndex
--        attribute,  which  indicates  the  logical WAN index this Channel is 
--        currently using to index into the WAN Statistic group. 
--
--        The rlanChannelGroupTable contains a list of channel groups available
--        to assign to the various channels. This table is indexed numerically.
--        The first index, being 1, corresponds to the default channel group 
--        which cannot be modified or deleted. If a SET request is received with
--        a valid rChannelGroupName and the rChannelGroupStatus attribute  set
--        to 'createAndGo', the agent will CREATE a new channel group object.
--
--        If a SET request is received with the attribute rChannelGroupStatus
--        having the value of 'destroy', the channel group will be deleted 
--        from the system's database, only if this group is not currently
--        assigned to a port or a Remote Lan. If so, BAD_VALUE_ERROR will 
--        be returned to the Manager.
--
--
-- 5.   The WAN Statistics group
--        This group will be indexed by an integer from 1..128. This value
--        will be used to index any particular WAN link. The statistics 
--        associated with  each  WAN  link are zeroed every time the WAN is 
--        disconnected.
--
--        It will also be possible to find out which data-bearing Channel
--        is  currently  using  this  WAN link  by accessing these 3
--        attributes given with each individual WAN link:
--        rWANStatsCardID, rWANStatsPortID, rWANStatsChanID.
--
--        With the help of rWANStatsRemLANID and rWANStatsRemLANName,
--        it is possible to find out which Remote LAN is actually
--        using this WAN link.
--
--
-- 6.   The WAN Summation Group
--        This group defines a set of  scalars  reflecting  the
--        statistics  summation of all the WAN link statistics on
--        the system since the system last reset.
--
--
-- 7.   The Remote LAN group
--        This group is indexed by an integer between 0 and 1000 which
--        corresponds to the Remote LAN ID, where 0 is the Default Remote
--        LAN configuration.
--
--        A Remote LAN can be created if the Manager sends  out
--        a  SET request with rRemLANStatus set to 'createAndGo',
--        and the rRemLANSerialNumber(if using SL/ML).
--
--        A Remote LAN will be deleted from the system's data-
--        base  if  the  rRemLANStatus attribute  is  SET  to
--        'destroy' and if the Remote LAN  is  currently  inac-
--        tive.  If  the Remote LAN is active a BAD_VALUE_ERROR
--        will be returned to the Manager.
--
--        The default Remote LAN can only be modified.
--
--        A total of 1000 Remote LANs can be configured or moni-
--        tored through SNMP SETs and GETs.
--
--        The rlanDestAddrTable contains the phone numbers, CLIDS,
--        channel groups and dial prefixes associated with the Remote LAN.
-- 
--        The rlanAddressPrefixConfigTable contains the dial prefixes 
--        available to be assigned to the Remote LAN. A dial prefix can be
--        created if the Manager sends out a SET request with rAddrPrefixStatus
--        set to 'createAndGo' and a valid rAddrPrefixName.
-- 
--        Also given in this group are all the  filtering statistics
--        associated with the Remote LANs.
--
--
-- 8.   The Local LAN group.
--        This group defines the  configuration  parameters  of the  Local LAN 
--        such as the type of connector used by the Local LAN ( AUI or P2 
--        backplane) and its Administrative State. You have to be careful
--        when configuring the Local LAN through SNMP. If the LAN is disabled 
--        by a community on the Local LAN, then the community will no longer be
--        able to talk to the system until the Local LAN is  re-enabled by the
--        console or another community defined on the system.  LAN Protocol
--        Filtering/Forwarding is defined here.  This enables the system to filter
--        or forward specific LAN protocols to and from the Local LAN.
--
--        It also defines all the statistics given by the LAN contoller chip.
--
--
-- 9.   The Local LAN Filter group.
--        This group gives  filtering  statistical  information
--        for the LAN port.
--
--
-- 10.  The Filter Configuration group.
--        This group defines the configeration parameters of the filters such as 
--        the aging time of Local and  Remote MAC addresses and if the system 
--        should age out MAC addresses or not.
--
--
-- 11.  The MAC Filter group
--        This group is roughly based on the dot1dStatic  group defined  in
--        RFC1286. It defines a table that could possibly go up to 4000 entries
--        deep and it is indexed by a MAC address. It contains information on
--        the MAC address type (static, dynamic  or  blocked)  and  its
--        Home Port.
--
--        It is possible to create a MAC address in the table by adding a row
--        to the table.
--
--        NOTE:  Because Dynamic addresses are subject to  age out and the table
--               can be quite big, it is recommended that if the Manager wants
--               to  traverse the table  with GET_NEXTs, that he does it with 
--               GET-NEXTs on all the attributes in this group.
--
-- 12.  The TCP/IP group
--        This group lets the communities configure the subnet mask, 
--        the network accessibility, the default gateway and the IP address 
--        for the system.
--
--        The Telnet group allows you to set security measures by configuring
--        the telnet access, IP address and Subnet Mask.
--
--        It is possible to lose contact with the system if the above mentioned 
--        groups are misconfigured. Be careful when setting these attributes.

--       The FTP group allows you to configure and initiate file transfers 
--       involving code, database or audit records.
--
-- 13.  The Blacklist group
--        This group contains a table that can be 64 entries deep. 
--        The table is indexed by an integer and contains the CLIDs (calling 
--        line IDs) that were black-listed by the system. Blacklisted CLIDs
--        can be created by sending a rBlacklistCLID and the rBlacklistStatus 
--        to 'createAndGo'. 
-- 
--        To delete a Blacklist entry, set the rBlacklistStatus to 'destroy'.
--
--
-- 14.  The Protocol group
--        This group contains a table indexed by a Network Address 
--        (IPAddress). All the entries define a triggering mechanism to make 
--        outgoing calls to Remote LANs based on Ip addresses. An entry can be
--        created by sending a rProtocolMask, a valid rProtocolRemLANID and the 
--        rProtocolStatus set to 'createAndGo'. 
--
--        To delete an entry, set the rProtocolStatus to 'destroy'. 
--
--        The table can go up to 510 entries deep.
--
--
-- 15.  The Pri Port group
--        This group will allow configuration and give statistical information
--        for the defined  ports on a PRI card. The switch type for the
--        PRI cards is configured in this group.
--
--        The  group  defines  a table, indexed by card number relative to the 
--        P2  backplane  and the port interface on the card.
--
--        The port cannot be created or deleted. It can modified, but only if
--        the card type is of type PRI. 
--
--
-- 16.  The IPX group
--        This group allows you to configure the Watchdog spoofing
--        and the timer on a system-wide basis. SAP learning can be
--        controlled by this group although the system has to  be disabled
--        (no bridging and no active calls) to enable SAP learning.
--        Learning can be enable with two options:
--          saving the static SAPs already learnt or deleting them.
--
-- 17.  The SAP Group
--        The rlanSAPTable contains the IPX Service Advertising Protocol table
--        entries and all the information that is included in the SAP frames.
--
--        During SAP learning, the user can delete or modify SAP entries in
--        the SAP table. This includes deleting entries or changing them from
--        static to dynamic. 
--
--        Creating entries is possible if the network that this SAP resides on
--        is already in the RIP table. All read-write attributes and the
--        rSAPStatus set to 'createAndGo' must be sent in a create. 
--
--        To delete an entry, set the rSAPStatus to 'destroy'.
--
--        These entries are indexed by SAPServiceType and SAPServerName.
--
--        The rlanSAPGroupTable contains a list of sap groups available to 
--        assign to the various saps. This table is indexed numerically. 
--        The first index, being 1 corresponds to the ALL sap group which cannot
--        be modified or deleted. The second index corresponds to the default  
--        sap group which also cannot be modified or deleted.
--
--        To create a sap group, send a SET request with a valid rSAPGroupName 
--        and the rSAPGroupStatus attribute set to 'createAndGo'.
--
--        If a SET request is received with the attribute rSAPGroupStatus
--        having the value of 'destroy', the sap group will be deleted 
--        from the sytem's database, only if this group is not currently
--        assigned to a Remote Lan. If so, BAD_VALUE_ERROR will be returned to 
--        the Manager.
--
--
-- 18.  The RIP Group
--        This table contains read-only information from the IPX Routing
--        Information Protocol frames received from the Local Lan.
--
--
-- 19. The SnmpGroup 
--       This group contain tables to allow configuration of communities, trap 
--       communities, trap profiles and mib views.
--
--       The rlanSnmpSetStatus attribute gives more information as to why 
--       the last set attempt failed.
--
--       The rlanSnmpCommunityTable allows configuration of Snmp Communites 
--       and to set the corresponding view.
--
--       To create an Snmp Community, send a SET request with a valid 
--       rSnmpCommunityName and rSnmpCommunityRowStatus set to 'createAndGo'.
--       The view will be defaulted to the default view unless specified.
--  
--       To delete an Snmp Community, set the rSnmpCommunityRowStatus to 
--       'destroy'.
--
--       The rlanSnmpTrapCommunityTable allows configuration of Snmp Trap 
--       Communities.
--
--       To create an Snmp Trap Community, send a SET request with a valid 
--       rSnmpTrapCommunityName, a valid rSnmpTrapIP and rSnmpTrapStatus set 
--       to 'createAndGo'.
--  
--       To delete an Snmp Trap Community, set the rSnmpTrapStatus to 'destroy'.
--       
--       The rlanSnmpViewTable allows configuration of Snmp Mib Views entries.
--       Two available preconfigured views are the ALL and Default views.
--       These two views are not modifiable and cannot be deleted.
--       This table is indexed by integers.
--
--       To create an Snmp Mib View, send a SET request with a valid 
--       rSnmpViewName, and rSnmpViewNameStatus set to 'createAndGo'.
--       The new View's subtrees are the default subtrees upon creation.
--  
--       To delete an Snmp Mib View Community, set the rSnmpViewNameStatus to
--       'destroy'. A bad value error will be returned if the view is assigned
--       to a valid Snmp Community. 
--
--       The rlanSnmpViewTable allows configuration of Snmp Mib Views subtree 
--       entries. The preconfigured subtrees for the views, ALL and Default,
--       are not modifiable and cannot be deleted. This table is indexed by
--       the corresponding rSnmpViewNameIndex, and the subtree's object 
--       identifier.
--
--       To create an Snmp View Subtree, send a SET request indexed with a
--       valid rSnmpViewNameIndex and the attribute rSnmpViewStatus set to 
--       'createAndGo'.
--  
--       To delete an Snmp View Subtree, set the rSnmpViewStatus to 'destroy'.
--
--
-- 20. The Audit Group
--       This group contains configurable information on the maintenance and
--       ways of triggering audit record transfers.
--     
--     
-- 21. The Flash Group 
--       This group lists the files stored in Flash memory and gives additional 
--       information on each listing.
--
--
-- 22. The LAN Protocol ID Group
--        The rlanLANProtocolIDTable contains a list of protocol IDs available to 
--        select for filtering/forwarding. This table is indexed numerically. 
--        The following index are predefined entries:
--           122 Novell IPX/SPX  8137
--           123 AppleTalk ARP   80F3
--           124 AppleTalk       809B
--           125 Reverse ARP     8035
--           126 ARP             0806
--           127 TCP/IP          0800
--
--        Indexes 1-121 are reserved for future predefined entry expansion.
--        Predefined entries cannot be modified or deleted.
--
--        Indexes 128-149 are for user defined LAN protocol ID entries.  To create
--        a LAN protocol ID entry, send a SET request with a valid
--        rLANProtocolIDName and rLANProtocolID, and the rLANProtocolIDStatus
--        attribute set to 'createAndGo'.
--
--        If a SET request is received with the attribute rSAPGroupStatus
--        having the value of 'destroy', the sap group will be deleted 
--        from the sytem's database, only if this group is not currently
--        assigned to a Remote Lan. If so, BAD_VALUE_ERROR will be returned to 
--        the Manager.


XPRESS-MIB DEFINITIONS ::= BEGIN

IMPORTS
    enterprises, Counter, Gauge, NetworkAddress, IpAddress, TimeTicks
 FROM RFC1155-SMI
    OBJECT-TYPE
 FROM RFC-1212
    PhysAddress, DisplayString
 FROM RFC1213-MIB
    TRAP-TYPE
 FROM RFC-1215;
 

--
--    Textual Conventions
--

-- To manage the creation and deletion of conceptual rows the textual
-- convention'RowStatus' from RFC 1443 is used and is defined as
-- follows:

   RowStatus ::= INTEGER
		 {
		 active(1),
		 notInService(2),
		 notReady(3),
		 createAndGo(4),
		 createAndWait(5),
		 destroy(6)
		 }
		 
-- unless otherwise stated only the states active(1), createAndGo(4) and
-- destroy(6) are currently supported by the RAC SNMP agent
-- implementation.                 


gandalf                            OBJECT IDENTIFIER ::=  { enterprises 64 }
gandalf-rlanisdn                   OBJECT IDENTIFIER ::=  { gandalf 9 }

-- groups for XpressWay RLAN and XpressStack products

rlanSystemGroup                    OBJECT IDENTIFIER ::= { gandalf-rlanisdn 1 }
rlanCardGroup                      OBJECT IDENTIFIER ::= { gandalf-rlanisdn 2 }
rlanDChanGroup                     OBJECT IDENTIFIER ::= { gandalf-rlanisdn 3 }
rlanChannelGroup                   OBJECT IDENTIFIER ::= { gandalf-rlanisdn 4 }
rlanWANStatsGroup                  OBJECT IDENTIFIER ::= { gandalf-rlanisdn 5 }
rlanWANSummationGroup              OBJECT IDENTIFIER ::= { gandalf-rlanisdn 6 }
rlanRemLANGroup                    OBJECT IDENTIFIER ::= { gandalf-rlanisdn 7 }
rlanLocLANGroup                    OBJECT IDENTIFIER ::= { gandalf-rlanisdn 8 }
rlanLocLANFilterGroup              OBJECT IDENTIFIER ::= { gandalf-rlanisdn 9 }
rlanFilterCfgGroup                 OBJECT IDENTIFIER ::= { gandalf-rlanisdn 10 }
rlanMACFilterGroup                 OBJECT IDENTIFIER ::= { gandalf-rlanisdn 11 }
rlanTCPIPGroup                     OBJECT IDENTIFIER ::= { gandalf-rlanisdn 12 }
rlanBlacklistGroup                 OBJECT IDENTIFIER ::= { gandalf-rlanisdn 13 }
rlanProtocolGroup                  OBJECT IDENTIFIER ::= { gandalf-rlanisdn 14 }
rlanPriPortGroup                   OBJECT IDENTIFIER ::= { gandalf-rlanisdn 15 }
rlanIPXGroup                       OBJECT IDENTIFIER ::= { gandalf-rlanisdn 16 }
rlanSAPGroup                       OBJECT IDENTIFIER ::= { gandalf-rlanisdn 17 }
rlanRIPGroup                       OBJECT IDENTIFIER ::= { gandalf-rlanisdn 18 }
rlanSnmpGroup                      OBJECT IDENTIFIER ::= { gandalf-rlanisdn 19 }
rlanAuditGroup                     OBJECT IDENTIFIER ::= { gandalf-rlanisdn 20 }
rlanFlashGroup                     OBJECT IDENTIFIER ::= { gandalf-rlanisdn 21 }
rlanLANProtocolIDGroup             OBJECT IDENTIFIER ::= { gandalf-rlanisdn 22 }
rlanModemGroup                     OBJECT IDENTIFIER ::= { gandalf-rlanisdn 23 }
rlanPppGroup                       OBJECT IDENTIFIER ::= { gandalf-rlanisdn 24 }
rlanRemExtGroup                    OBJECT IDENTIFIER ::= { gandalf-rlanisdn 25 }
rlanTimeOfDayGroup                 OBJECT IDENTIFIER ::= { gandalf-rlanisdn 26 }
rlanDpnssBchGroup                  OBJECT IDENTIFIER ::= { gandalf-rlanisdn 27 }
rlanCallRoutingGroup               OBJECT IDENTIFIER ::= { gandalf-rlanisdn 28 }
rlanSecurityGroup                  OBJECT IDENTIFIER ::= { gandalf-rlanisdn 29 }
rlanIpRoutingGroup                 OBJECT IDENTIFIER ::= { gandalf-rlanisdn 30 }

--
-- Definition of the rlanSystemGroup
--


rSysName OBJECT-TYPE
     SYNTAX  DisplayString (SIZE(1..16))
     ACCESS  read-write
     STATUS  mandatory
     DESCRIPTION
	     "Tells you the name allocated to this system."
     ::= { rlanSystemGroup 1 }


rSysAdminState OBJECT-TYPE
     SYNTAX  INTEGER {
		 disabled(1),
		 enabled(2)
	     }
     ACCESS  read-write
     STATUS  mandatory
     DESCRIPTION
	     "Select this option when you want the system to process
	     new calls. If you disable this option, the system
	     will not accept or generate new calls, but existing calls will 
	     remain connected. NOTE: Disable during SAP learning mode.
	     Disabling or enabling call processing will not affect the LAN."
     ::= { rlanSystemGroup 2 }


--   { rlanSystemGroup 3 } obsoleted


rSysTransDelay OBJECT-TYPE
     SYNTAX  INTEGER (1..400)
     ACCESS  read-write
     STATUS  mandatory
     DESCRIPTION
	     "Enter the maximum frame age (in tenths of a second)."
     ::= { rlanSystemGroup 4 }


--   { rlanSystemGroup 5 } obsoleted


rSysCallTeardown OBJECT-TYPE
     SYNTAX  INTEGER {
		 noTeardown(1),
		 teardown(2)
	     }
     ACCESS  read-write
     STATUS  mandatory
     DESCRIPTION
	     "Select this option when you want the system
	     to tear down all currently active calls."
     ::= { rlanSystemGroup 6 }


rSysNVRAMDiag OBJECT-TYPE
     SYNTAX  INTEGER {
		 failed(1),
		 passed(2)
	     }
     ACCESS  read-only
     STATUS  mandatory
     DESCRIPTION
	     "Tells you whether the system has passed the NVRAM diagnostics. 
	     If it failed, the read/write test passed, but at least one of the 
	     NVRAM objects failed the startup checksum. If
	     it passed, all the NVRAM objects passed the startup checksum."
     ::= { rlanSystemGroup 7 }


rSysRTCDiag OBJECT-TYPE
     SYNTAX  INTEGER {
		 failed(1),
		 passed(2)
	     }
     ACCESS  read-only
     STATUS  mandatory
     DESCRIPTION
	     "Tells you whether the system's real-time clock
	     is reliable. If the real-time clock has failed the diagnostics, the 
	     system is using inaccurate time and date information."
     ::= { rlanSystemGroup 8 }


rSysLANDiag OBJECT-TYPE
     SYNTAX  INTEGER {
		 failed(1),
		 passed(2)
	     }
     ACCESS  read-only
     STATUS  mandatory
     DESCRIPTION
	     "Tells you whether the 82596 LAN controller chip
	     passed or failed the LAN diagnostics."
     ::= { rlanSystemGroup 9 }


rSysPromRev OBJECT-TYPE
     SYNTAX  DisplayString (SIZE(1..16))
     ACCESS  read-only
     STATUS  mandatory
     DESCRIPTION
	     "Tells you the revision number of
	     the boot PROM."
     ::= { rlanSystemGroup 10 }


rSysOpState OBJECT-TYPE
     SYNTAX  INTEGER {
		 disabled(1),
		 enabled(2),
		 faulty(3)
	     }
     ACCESS  read-only
     STATUS  mandatory
     DESCRIPTION
	     "Tells you whether the system is operational (enabled),
	     not operational (disabled) or faulty."
::= { rlanSystemGroup 11 }


rSysUpTime OBJECT-TYPE
     SYNTAX  TimeTicks
     ACCESS  read-only
     STATUS  mandatory
     DESCRIPTION
	     "Tells you how long (in hundredths of a
	     second) the system has been
	     running since the last reset."
     ::= { rlanSystemGroup 12 }


rSysTotalRAM OBJECT-TYPE
    SYNTAX   INTEGER
    ACCESS   read-only
    STATUS   mandatory
    DESCRIPTION
	    "Tells you how much RAM has been allocated to 
	   the System Controller."
     ::= { rlanSystemGroup 13 }


rSysRSCSlot OBJECT-TYPE
    SYNTAX  INTEGER
    ACCESS  read-only
    STATUS  mandatory
    DESCRIPTION
	    "Tells you the slot position of the RSC 9000 card
	    (System Controller) with respect to the P2 backplane."
     ::= { rlanSystemGroup 14 }


rSysCompressionAdminState OBJECT-TYPE
    SYNTAX  INTEGER {
		disabled(1),
		enabled(2)
	    }
    ACCESS  read-write
    STATUS  mandatory
    DESCRIPTION
	    "Select this option when you want the system to use data compression."
     ::= { rlanSystemGroup 15 }


rSysCompressionOpState OBJECT-TYPE
    SYNTAX  INTEGER {
		disabled(1),
		enabled(2),
		faulty(3)
	    }
    ACCESS  read-only
    STATUS  mandatory
    DESCRIPTION
	    "Tells you whether data compression for the system
	    is disabled, enabled, or faulty."
     ::= { rlanSystemGroup 16 }


rSysCLIDSecurity OBJECT-TYPE
    SYNTAX  INTEGER {
		disabled(1),
		enabled(2)
	    }
    ACCESS  read-write
    STATUS  mandatory
    DESCRIPTION
	    "Select this option when you want the system to use
	    CLID security."
     ::= { rlanSystemGroup 17 }


rSysCLIDEnforced OBJECT-TYPE
    SYNTAX  INTEGER {
		disabled(1),
		enabled(2)
	    }
    ACCESS  read-write
    STATUS  mandatory
    DESCRIPTION
	    "Select this option when you want the system to
	    accept only incoming calls with a CLID."
     ::= { rlanSystemGroup 18 }


rSysIncomingMinBearer OBJECT-TYPE
    SYNTAX  INTEGER {
		kbps64Unrestrict(1),
		kbps56Dig(2),
		audio3100Hz(3),
		speech(4)
	    }
    ACCESS  read-write
    STATUS  mandatory
    DESCRIPTION
	    "Select the minimum bearer capability allowed during an
	    incoming call: 64 Kbps Unrestricted, 56 Kbps Digital, 3100 Hz Audio, or Speech."
    ::= { rlanSystemGroup 19 }


rSysRLANLearningAdminState OBJECT-TYPE
    SYNTAX  INTEGER {
		disabled(1),
		enabled(2)
	    }
    ACCESS  read-write
    STATUS  mandatory
    DESCRIPTION
	    "Select this option when you want the system to learn
	    remote LANs that use the Gandalf proprietary link protocol
	    and configure them in the database. The system will not learn
	    remote LANs that use PPP as their WAN protocol. Any LANs
	    calling in while this attribute is enabled will be learned
	    and named with Learnt_lanx, where x is the index into the
	    remote LAN list. Most of the information will be taken
	    from a default remote LAN set up in the database.
	    NOTE: Security is at a minimum when this option is enabled."
    ::= { rlanSystemGroup 20 }


rSysDateAndTime OBJECT-TYPE
    SYNTAX  OCTET STRING (SIZE(11))
    ACCESS  read-write
    STATUS  mandatory
    DESCRIPTION
	    "Enter the current date and time, using the format specified in RFC 1443."
    ::= { rlanSystemGroup 21 }


rSysReset OBJECT-TYPE
    SYNTAX  INTEGER {
		noReset(1),
		hardReset(2)
	    }
    ACCESS  read-write
    STATUS  mandatory
    DESCRIPTION
	    "Select hardReset when you want the System Controller to reset."
::= { rlanSystemGroup 22 }


rSysPassword OBJECT-TYPE
    SYNTAX  DisplayString (SIZE(0..8))
    ACCESS  read-write
    STATUS  mandatory
    DESCRIPTION
	    "Enter the system password for the system's embedded console."
    ::= { rlanSystemGroup 23 }
 
rSysHubType OBJECT-TYPE
    SYNTAX  INTEGER {
		xpressstack(24),
		hub48(48),
		hub132(132)
	    }
    ACCESS  read-only
    STATUS  mandatory
    DESCRIPTION
	    "Tells you the hub type for this system installation."
    ::= { rlanSystemGroup 24 }
  
 
rSysRscSoftwareRev OBJECT-TYPE
    SYNTAX  DisplayString (SIZE(1..16))
    ACCESS  read-only
    STATUS  mandatory
    DESCRIPTION
	    "Tells you the software revision for the
	    System Controller."
    ::= { rlanSystemGroup 25 }
  
 
rSysRscHardwareRev OBJECT-TYPE
    SYNTAX  DisplayString (SIZE(1..16))
    ACCESS  read-only
    STATUS  mandatory
    DESCRIPTION
	    "Tells you the hardware revision for the
	    System Controller."
    ::= { rlanSystemGroup 26 }
  
 
rSysCompressionSoftwareRev OBJECT-TYPE
    SYNTAX  DisplayString (SIZE(1..16))
    ACCESS  read-only
    STATUS  mandatory
    DESCRIPTION
	    "Tells you the software revision for the
	    System-Controller compression card."
    ::= { rlanSystemGroup 27 }
  
 
rSysCompressionHardwareRev OBJECT-TYPE
    SYNTAX  DisplayString (SIZE(1..16))
    ACCESS  read-only
    STATUS  mandatory
    DESCRIPTION
	    "Tells you the hardware revision for the
	    System-Controller compression card."
    ::= { rlanSystemGroup 28 }
 
 
rSysCompressionPromRev OBJECT-TYPE
     SYNTAX  DisplayString (SIZE(1..16))
     ACCESS  read-only
     STATUS  mandatory
     DESCRIPTION
	     "Tells you the revision number of the boot PROM for
	     the System-Controller compression card."
     ::= { rlanSystemGroup 29 }
 
 
rSysLongCallThreshold OBJECT-TYPE
     SYNTAX  INTEGER (120..86340)
     ACCESS  read-write
     STATUS  mandatory
     DESCRIPTION
	     "Enter the threshold an active call must exceed (120 - 86340 seconds) 
	     before the system generates a potential trap and event alarm.
	     The range is from 2 mins to 23hrs 59 mins. The setting is in seconds 
	     so they are in increments of 60."
     DEFVAL { 1800 }
     ::= { rlanSystemGroup 30 }
 
 
rSysLongCallEvents OBJECT-TYPE
    SYNTAX  INTEGER {
		disabled(1),
		enabled(2)
	    }
    ACCESS  read-write
    STATUS  mandatory
    DESCRIPTION
	    "Select this option when you want the system to generate alarms to the event log
	    when a call to a remote LAN exceeds the call threshold 
	    you've set (rSysLongCallThreshold)."
    ::= { rlanSystemGroup 31 }

rSysP1BckPlSize OBJECT-TYPE
    SYNTAX  INTEGER (2..5)
    ACCESS  read-only
    STATUS  mandatory
    DESCRIPTION
            "Tells you the size of the P1 backplane that the system is
            attached to."
    ::= { rlanSystemGroup 32 }

rSysRipForwarding OBJECT-TYPE
    SYNTAX  INTEGER {
                disabled(1),
                enabled(2)
            }
    ACCESS  read-write
    STATUS  mandatory
    DESCRIPTION
            "Select this option when you want the system to forward the rips
            learned from its active remote LANs that are doing PPP IPCP.
            These rips will be forwarded onto the local LAN when enabled."
    ::= { rlanSystemGroup 33 }

rSysOverDOSBS OBJECT-TYPE
     SYNTAX  INTEGER {
		 disabled(1),
		 enabled(2)
	     }
     ACCESS  read-write
     STATUS  mandatory
     DESCRIPTION
	     "Select this option when you want the system to override the DOSBS
	     (Data Over Speech Bearer Services), enabled at IO card ports."
     ::= { rlanSystemGroup 34 }


rSysARPProxy OBJECT-TYPE
    SYNTAX  INTEGER {
		disabled(1),
		enabled(2)
	    }
    ACCESS  read-write
    STATUS  mandatory
    DESCRIPTION
	    "Select this option when you want the system to answer
	    ARP request on behalf of a remote address configuered on 
	    the protocol list table."
     ::= { rlanSystemGroup 35 }


rSysIdByCLID OBJECT-TYPE
    SYNTAX  INTEGER {
		disabled(1),
		enabled(2)
	    }
    ACCESS  read-write
    STATUS  mandatory
    DESCRIPTION
	    "Select this option when you want the system to identify
       a caller from its Calling Line ID (CLID) before the call
       is answered.  This is useful when the remote is to be
       called back, so the system will reject the call without
       the caller being charged for the call."
     ::= { rlanSystemGroup 36 }


rSysDialBackHoldoff OBJECT-TYPE
    SYNTAX  INTEGER (0..30)
    ACCESS  read-write
    STATUS  mandatory
    DESCRIPTION
       "Time delay the system will observe between the time it determines
       a dialback call is to be placed and the actual outgoing call
       request.  This allows the remote to turn around and be prepared
       to receive the call back."
     ::= { rlanSystemGroup 37 }


rSysFailedCallRetryHoldoff OBJECT-TYPE
    SYNTAX  INTEGER (0..120)
    ACCESS  read-write
    STATUS  mandatory
    DESCRIPTION
       "Period of time after a failed outgoing call attempt the system will 
       ignore request to place a call to the same remote.  In Japan, 
       this is used to meet regulatory approvals where no more than 2 
       failed calls can be placed in a 3 minute time span.  Can also 
       be used with dialback to guarantee that the system will not retry 
       an outgoing call if the remote is due to call back.  If a switch 
       type is changed to Japanese, then this value will be changed to 
       61 seconds if it set to a lower value.  When a Japanese switch is
       defined, the minimum acceptable value is 61 seconds."
     ::= { rlanSystemGroup 38 }


rSysCLIDBlacklistAfterAttempts OBJECT-TYPE
    SYNTAX  INTEGER (0..9)
    ACCESS  read-write
    STATUS  mandatory
    DESCRIPTION
       "The number of times that a CLID will be allowed to
        fail until it is blacklisted. The default is one,
	that is, the first time that a CLID fails, it will
        be blacklisted. If set to 0, this feature is disabled."
     ::= { rlanSystemGroup 39 }

--
-- Definition of the rlanCardGroup
--

rlanCardTable OBJECT-TYPE
    SYNTAX  SEQUENCE OF RlanCardEntry
    ACCESS  not-accessible
    STATUS  mandatory
    DESCRIPTION
	    "Lets you view and manage how the
	    system configures individual cards."
    ::= { rlanCardGroup 1 }

rlanCardEntry OBJECT-TYPE
    SYNTAX  RlanCardEntry
    ACCESS  not-accessible
    STATUS  mandatory
    INDEX   { rCardID }
    ::= { rlanCardTable 1 }

RlanCardEntry ::=
    SEQUENCE {
	rCardID          INTEGER,
	rCardType        INTEGER,
	rCardAdmst       INTEGER,
	rCardStatus      INTEGER,
	rCardDiag        INTEGER,
	rCardOpState     INTEGER,
	rCardSWRev       DisplayString,
	rCardHWRev       DisplayString,
	rCardTotalRAM    INTEGER,
	rCardBRISwitch   INTEGER,
	rCardBootProm    DisplayString,
	rCardReset       INTEGER,
	rCardTearDown    INTEGER,
	rCardRowStatus   RowStatus,
	rCardPriActivate INTEGER
    }


rCardID OBJECT-TYPE
    SYNTAX  INTEGER (1..10)
    ACCESS  read-only
    STATUS  mandatory
    DESCRIPTION
	    "Tells you the position of a card (1-10) within the hub with respect to
	    the P2 backplane."
    ::= { rlanCardEntry 1 }


rCardType OBJECT-TYPE
    SYNTAX  INTEGER {
                mrm9430 (36),
		vrm9630 (40),
		bri9308 (148),
		xsm9516RS232V11 (152),
		xsm9516RS232V35 (156),
		pri9360DB15 (180),
		pri9346DB15 (184),
	 	pri9346eDB15(188),
		pri9330BNC (192),
		pri9330DB15 (196),
		pri9323DB15 (200),
	 	pri9360eDB15(204),
		briU9308 (208)
	    }
    ACCESS  read-write
    STATUS  mandatory
    DESCRIPTION
	    "Select the card type for this particular card: mrm9430, bri9308,
	    xsm9516RS232V11, xsm9516RS232V35, pri9360DB15, pri9346DB15, 
	    pri9330BNC, pri9330DB15, pri9323DB15, briU9308."
    ::= { rlanCardEntry 2 }



rCardAdmst OBJECT-TYPE
    SYNTAX  INTEGER {
		disabled(1),
		enabled(2)
	    }
    ACCESS  read-write
    STATUS  mandatory
    DESCRIPTION
	    "Select this option when you want the system to accept and
             generate new calls on a card. If you disable this option, 
             existing calls on the card will remain connected, but the system
	     will not accept or generate new calls on the card.
	    DEFAULT = selected"
    DEFVAL { enabled }        
    ::= { rlanCardEntry 3 }


rCardStatus OBJECT-TYPE
    SYNTAX  INTEGER {
		offline(1),
		online(2)
	    }
    ACCESS  read-write
    STATUS  mandatory
    DESCRIPTION
	    "Specify whether a card is online or offline.
	    NOTE: If a card is ONLINE and you set it to OFFLINE, all
	    calls on the card will be torn down.
	    DEFAULT = online"
  DEFVAL { online }
    ::= { rlanCardEntry 4 }


rCardDiag OBJECT-TYPE
    SYNTAX  INTEGER {
		failed(1),
		passed(2)
	    }
    ACCESS  read-only
    STATUS  mandatory
    DESCRIPTION
	    "Tells you whether this card has passed or failed diagnostics."
    ::= { rlanCardEntry 5 }


rCardOpState OBJECT-TYPE
    SYNTAX  INTEGER {
		cardOffline(1),
		cardOnline(2),
		cardGone(3),
		cardFaulty(4),
		cardDetected(5),
		cardWaitDownReq(6),
		cardDownloading(7),
		cardWaitDownAck(8),
		cardWaitOpCode(9),
		cardMismatch(10),
		cardEmpty(11),
		cardRejected(12)
	    }
    ACCESS  read-only
    STATUS  mandatory
    DESCRIPTION
	    "Tells you the operational state of a card, which can be one of:

	      OFFLINE -  you've pressed the OFFLINE button on the card
			 or you've set the status of the card (rCardStatus)
			 to OFFLINE.
	      ONLINE  -  the card is functioning.
	      GONE    -  the card is not in its slot, but the slot is still
                         configured.
	      FAULTY  -  the link to the card has been lost, or the card is defective.
	      DETECTED - the card has been detected, but its link to
		         the System Controller has not yet been established.
	      WAITDOWNREQ - the System Controller is waiting for a Download Request to 
                            come from the card.
	      DOWNLOADING - the System Controller is downloading the op code to the card.
	      WAITDOWNACK - the download has been completed, and the System Controller is
                            now waiting for an acknowledgement from the card.
	      WAITOPCODE  - the card is currently starting up.
	      MISMATCH    - the card does not match the definition for it that is stored
                            in the database.
	     CARDEMPTY    - the card has been removed from the slot, which is no longer
                            configured.
	     CARDREJECTED - the card has been rejected because it caused the number of 
                            channels to exceed the maximum allowed."
    ::= { rlanCardEntry 6 }


rCardSWRev OBJECT-TYPE
    SYNTAX  DisplayString (SIZE(1..16))
    ACCESS  read-only
    STATUS  mandatory
    DESCRIPTION
	    "Tells you the software revision for the card."
    ::= { rlanCardEntry 7 }


rCardHWRev OBJECT-TYPE
    SYNTAX  DisplayString (SIZE(1..16))
    ACCESS  read-only
    STATUS  mandatory
    DESCRIPTION
	    " Tells you the hardware revision for the card."
    ::= { rlanCardEntry 8 }


rCardTotalRAM OBJECT-TYPE
    SYNTAX  INTEGER
    ACCESS  read-only
    STATUS  mandatory
    DESCRIPTION
	    "Tells you how much RAM (in bytes) has been allocated to the card."
    ::= { rlanCardEntry 9 }


rCardBRISwitch OBJECT-TYPE
    SYNTAX  INTEGER  {
		ni1(1),
		nt(2),
		attPointToPoint(3),
		attMultiPoint(4),
		net3(5),
		ins64(6),
		other(7)
	    }
    ACCESS  read-write
    STATUS  mandatory
    DESCRIPTION
	    "If this is a BRI9308 card, select the BRI switch type you want it to use:
	    ni1, nt, attPointToPoint, attMultiPoint, net3, or other.
	    If you try to select a BRI switch type for card types other than BRI,
            you'll see the following error message: noSuchName.
	    DEFAULT = ni 1"
    DEFVAL  { ni1 }
    ::= { rlanCardEntry 10 }
 
 
rCardBootProm OBJECT-TYPE
    SYNTAX  DisplayString (SIZE(1..16))
    ACCESS  read-only
    STATUS  mandatory
    DESCRIPTION
	    "Tells you the software revision id of the boot PROM for this card."
    ::= { rlanCardEntry 11 }


rCardReset OBJECT-TYPE
    SYNTAX  INTEGER  {
		noReset(1),
		hardReset(2)
	    }
    ACCESS  read-write
    STATUS  mandatory
    DESCRIPTION
	    "Select hardReset to reset the card.
	    NOTE: The card must be offline to be reset.
	     DEFAULT = noReset"
    DEFVAL  { noReset }
    ::= { rlanCardEntry 12 }


rCardTearDown OBJECT-TYPE
    SYNTAX  INTEGER  {
		noTearDown(1),
		tearDown(2)
	    }
    ACCESS  read-write
    STATUS  mandatory
    DESCRIPTION
	    "Select this option when you want the system to disconnect
	    all active calls on the card.
	     DEFAULT = noTear Down"
    DEFVAL  { noTearDown }
    ::= { rlanCardEntry 13 }


rCardRowStatus OBJECT-TYPE
    SYNTAX  RowStatus
    ACCESS  read-write
    STATUS  mandatory
    DESCRIPTION
	    "The current status of this entry. If the row status is
	    set to destroy(6), the card will be removed from the 
	    database only if the card is offline (see the rCardStatus 
	    attribute).  If the card is not OFFLINE, a BAD_VALUE_ERROR 
	    will be returned to the Manager."
    ::= { rlanCardEntry 14 }

rCardPriActivate OBJECT-TYPE
    SYNTAX  INTEGER  {
	       noChangesPending(0),
               activate(1),
	       changesPending(2)
	    }
    ACCESS  read-write
    STATUS  mandatory
    DESCRIPTION
	    "Setting this object to 1 will activate the
	     changes of a PRI card. A read from this object
	     will return a 0 for no action needed, or a 2 for
	     changes pending. 0 and 2 cannot be set."
    ::= { rlanCardEntry 15 }


-- End Of rlanCardGroup
--
--
-- Definition of rlanDChanGroup
--

rlanDChanStatsTable OBJECT-TYPE
     SYNTAX  SEQUENCE OF RlanDChanStatsEntry
     ACCESS  not-accessible
     STATUS  mandatory
     DESCRIPTION
	     "This table provides a management view of the
	     statistics specific to individual D Channels. The
	     port ID is the D-channel ID. "
     ::= { rlanDChanGroup 1 }

rlanDChanStatsEntry OBJECT-TYPE
     SYNTAX  RlanDChanStatsEntry
     ACCESS  not-accessible
     STATUS  mandatory
     INDEX   { rDChanCardID, rDChanPortID }
     ::= { rlanDChanStatsTable 1 }

RlanDChanStatsEntry   ::=
     SEQUENCE {
	 rDChanCardID              INTEGER,
	 rDChanPortID              INTEGER,
	 rDChanState               INTEGER,
	 rDChanRxFrames            Counter,
	 rDChanRxCRCErrs           Counter,
	 rDChanRxOverErrs          Counter,
	 rDChanRxOverflows         Counter,
	 rDChanRxAborts            Counter,
	 rDChanRxCalls             Counter,
	 rDChanTxFrames            Counter,
	 rDChanTxUnderErrs         Counter,
	 rDChanTxCalls             Counter,
	 rDChanLostDSLs            Counter,
	 rDChanColls               Counter,
	 rDChanFrameSlips          Counter,
	 rDChanLinkFaults          Counter
     }


rDChanCardID OBJECT-TYPE
     SYNTAX  INTEGER (1..10)
     ACCESS  read-only
     STATUS  mandatory
     DESCRIPTION
	     "Tells you the position of this card (from 1 to 10)
	     within the hub with respect to the P2 backplane."
     ::= { rlanDChanStatsEntry 1 }


rDChanPortID OBJECT-TYPE
     SYNTAX  INTEGER (1..8)
     ACCESS  read-only
     STATUS  mandatory
     DESCRIPTION
	     "Tells you the Port ID of this D Channel."
::= { rlanDChanStatsEntry 2 }


rDChanState OBJECT-TYPE
    SYNTAX   INTEGER {
		 linkDown(1),
		 linkUp(2),
		 linkFaulty(3),
		 outOfService1(4),
		 outOfService2(5),
		 outOfService3(6),
		 outOfService4(7),
		 outOfService5(8),
		 modemNotInstalled(9)
	     }
    ACCESS   read-only
    STATUS   mandatory
    DESCRIPTION
	    "Tells you  the administrative status of the Channel 
	    or Modem on this I/O card."
    ::= { rlanDChanStatsEntry 3 }


rDChanRxFrames OBJECT-TYPE
    SYNTAX  Counter
    ACCESS  read-only
    STATUS  mandatory
    DESCRIPTION
	    "Tells you  how many LAPD frames have been received on
	    this D Channel."
    ::= { rlanDChanStatsEntry 4 }


rDChanRxCRCErrs OBJECT-TYPE
    SYNTAX  Counter
    ACCESS  read-only
    STATUS  mandatory
    DESCRIPTION
	    "Tells you how many LAPD frames with CRC errors have been
             received on this D Channel."
    ::= { rlanDChanStatsEntry 5 }


rDChanRxOverErrs OBJECT-TYPE
    SYNTAX  Counter
    ACCESS  read-only
    STATUS  mandatory
    DESCRIPTION
	    "Tells you how many frames have been received on this
	     D Channel but discarded because there was not enough memory
             to store them."
    ::= { rlanDChanStatsEntry 6 }


rDChanRxOverflows OBJECT-TYPE
    SYNTAX  Counter
    ACCESS  read-only
    STATUS  mandatory
    DESCRIPTION
	    "Tells you the how many LAPD frames with
	    overflow errors have been received on this D Channel."
    ::= { rlanDChanStatsEntry 7 }


rDChanRxAborts OBJECT-TYPE
    SYNTAX  Counter
    ACCESS  read-only
    STATUS  mandatory
    DESCRIPTION
	    "Tells you how many  LAPD frames have been received on
	    this D Channel."
    ::= { rlanDChanStatsEntry 8 }


rDChanRxCalls OBJECT-TYPE
    SYNTAX  Counter
    ACCESS  read-only
    STATUS  mandatory
    DESCRIPTION
	    "Tells you  how many calls have been received on this
	     D Channel."
    ::= { rlanDChanStatsEntry 9 }


rDChanTxFrames OBJECT-TYPE
    SYNTAX  Counter
    ACCESS  read-only
    STATUS  mandatory
    DESCRIPTION
	    "Tells you the how many LAPD frames have been transmitted on
	    this D Channel."
    ::= { rlanDChanStatsEntry 10 }

rDChanTxUnderErrs OBJECT-TYPE
    SYNTAX  Counter
    ACCESS  read-only
    STATUS  mandatory
    DESCRIPTION
	    "Tells you how many LAPD frames with underrun errors have been
             transmitted on this D Channel."
    ::= { rlanDChanStatsEntry 11 }


rDChanTxCalls OBJECT-TYPE
    SYNTAX  Counter
    ACCESS  read-only
    STATUS  mandatory
    DESCRIPTION
	    "Tells you the how many calls have been transmitted on this
	    D Channel."
    ::= { rlanDChanStatsEntry 12 }


rDChanLostDSLs OBJECT-TYPE
    SYNTAX  Counter
    ACCESS  read-only
    STATUS  mandatory
    DESCRIPTION
	    "Tells you how many DSL (digital subscriber loop link) losses
	    have occurred on this D Channel (i.e., how many ISDN
	    connections have been dropped)."
    ::= { rlanDChanStatsEntry 13 }


rDChanColls OBJECT-TYPE
    SYNTAX  Counter
    ACCESS  read-only
    STATUS  mandatory
    DESCRIPTION
	    "Tells you how many LAPD frames have collided on this D Channel."
    ::= { rlanDChanStatsEntry 14 }


rDChanFrameSlips OBJECT-TYPE
    SYNTAX  Counter
    ACCESS  read-only
    STATUS  mandatory
    DESCRIPTION
	    "Tells you how many LAPD frames have slipped on
	    this D Channel."
    ::= { rlanDChanStatsEntry 15 }


rDChanLinkFaults OBJECT-TYPE
    SYNTAX  Counter
    ACCESS  read-only
    STATUS  mandatory
    DESCRIPTION
	    "Tells you how many link faults (timeouts) have occurred on
             this D Channel."
    ::= { rlanDChanStatsEntry 16 }


--     Basic Rate ISDN D-channel Configuration Table

rlanDChanConfigTable OBJECT-TYPE
     SYNTAX  SEQUENCE OF RlanDChanConfigEntry
     ACCESS  not-accessible
     STATUS  mandatory
     DESCRIPTION
             "This table provides a management view of the system
             configuration specific to individual D-channels. The
             port ID is nothing else than the D-channel ID. "
     ::= { rlanDChanGroup 2 }
 
rlanDChanConfigEntry OBJECT-TYPE
     SYNTAX  RlanDChanConfigEntry
     ACCESS  not-accessible
     STATUS  mandatory
     INDEX   { rDChanCardID, rDChanPortID }
     ::= { rlanDChanConfigTable 1 }
 
RlanDChanConfigEntry   ::=
     SEQUENCE {
         rDChanStatus          INTEGER,
         rDChanFaultThreshold  INTEGER,
	 rDChanDOSBS	       INTEGER,
	 rDChanBriNetSync      INTEGER
     }

rDChanStatus OBJECT-TYPE
    SYNTAX  INTEGER {
                offline(1),
                online(2)
            }
    ACCESS  read-write
    STATUS  mandatory
    DESCRIPTION
            "Specify whether a port should be put OFFLINE
            or ONLINE. Reading this object always returns online(2)
            regardless of the card's current operational state.
 
            If the port is ONLINE and the attribute is set OFFLINE,
            all calls on this port will be torn down and the port will
            be put in the OFFLINE state.
 
            To set a port  back to ONLINE, select ONLINE from the list of options.
            DEFAULT = online"
    DEFVAL { online }
    ::= { rlanDChanConfigEntry 1 }
 
 
rDChanFaultThreshold OBJECT-TYPE
     SYNTAX  INTEGER (0..10000)
     ACCESS  read-write
     STATUS  mandatory
     DESCRIPTION
             "Enter the threshold (1-10000 seconds) that the number of port 
             faults must exceed before the port is taken offline and a potential 
             trap and event alarm is generated.  A value of zero disables this function.
             DEFAULT = 0"
     DEFVAL { 0 }
     ::= { rlanDChanConfigEntry 2 }

rDChanDOSBS OBJECT-TYPE
     SYNTAX  INTEGER {
               disabled(1),
               enabled(2)
             }
     ACCESS  read-write
     STATUS  mandatory
     DESCRIPTION
             "Select this option to enable digital over speech bearer for BRI D-channels."
      DEFVAL  { disabled }
     ::= { rlanDChanConfigEntry 3 }
  

rDChanBriNetSync OBJECT-TYPE
     SYNTAX  INTEGER {
               primary(1),
               secondary(2),
	       none(3)
             }
     ACCESS  read-write
     STATUS  mandatory
     DESCRIPTION
             "Select whether to source the system clock 
	      from this network connection."
      DEFVAL  { primary }
     ::= { rlanDChanConfigEntry 4 }


-- End of rDChanGroup
--


--
-- Definitions of rlanChannelGroup
--

--
--   { rlanChannelGroup 1 } obsoleted
--

--
--     Generic Channel Management Configuration Table
--     

rlanChannelConfigTable OBJECT-TYPE
     SYNTAX  SEQUENCE OF RlanChannelConfigEntry
     ACCESS  not-accessible
     STATUS  mandatory
     DESCRIPTION
	     "This table provides a management view of the
	     system configuration generic parameters specific
	     to individual data-bearing channels (i.e., ISDN B Channels and XSM sync
	     channels, but NOT ISDN D Channels)."
     ::= { rlanChannelGroup 2 }


rlanChannelConfigEntry OBJECT-TYPE
     SYNTAX  RlanChannelConfigEntry
     ACCESS  not-accessible
     STATUS  mandatory
     INDEX   { rChanCardID, rChanPortID, rChanID }
     ::= { rlanChannelConfigTable 1 }


RlanChannelConfigEntry ::=
     SEQUENCE {
	 rChanCardID          INTEGER,
	 rChanPortID          INTEGER,
	 rChanID              INTEGER,
	 rChanOpMode          INTEGER,
	 rChanChannelGroup    INTEGER,
	 rChanHuntGroup       INTEGER,
	 rChanOtherChan       INTEGER
     }


rChanCardID OBJECT-TYPE
     SYNTAX  INTEGER (1..10)
     ACCESS  read-only
     STATUS  mandatory
     DESCRIPTION
	     "Tells you the  position of this card within the hub with respect
	     to the P2 backplane."
     ::= { rlanChannelConfigEntry 1 }


rChanPortID OBJECT-TYPE
     SYNTAX  INTEGER (1..16)
     ACCESS  read-only
     STATUS  mandatory
     DESCRIPTION
	     "Tells you which port this channel
	     belongs to on this specific card."
     ::= { rlanChannelConfigEntry 2 }


rChanID OBJECT-TYPE
     SYNTAX  INTEGER (1..31)
     ACCESS  read-only
     STATUS  mandatory
     DESCRIPTION
	     "Tells you the channel ID within the port."
     ::= { rlanChannelConfigEntry 3 }


rChanOpMode OBJECT-TYPE
     SYNTAX  INTEGER {
		 disabled(1),
		 answerCallsOnly(2),
		 answerAndOrignateCalls(3),
		 originateCallsOnly(4),
		 leased(5),
                 dropAndInsert(6),
                 dropAndInsertRobbedBit(7)
	     }
     ACCESS  read-write
     STATUS  mandatory
     DESCRIPTION
	     "Select the mode of operation for this channel,
	      which can be one of: Disabled, AnswerCallsOnly;
	      AnswerAndOriginateCalls; OriginateCallsOnly,
	      Leased (PRI port only).

	     If this channel belongs to a BRI port (but not a PRI port),
	     it will set the other B Channel on the BRI port as well,
	     even if this attribute is set for a unique B Channel.

	     A B Channel that belongs to a BRI port supports
	     only the first four values. A badValue error will
	     be returned if a SET request with a value of 'leased' is
	     received on a B Channel that belongs to a BRI port.

	     A B Channel that belongs to a PRI port supports all values
	     from 1 to 5.
             A B Channel that belongs to a card of type pri9360DB15 or
	     pri9346DB15 supports all values. 
	     NOTE: A leased PRI will support only a disabled or
	     leased mode.

	     All values from 1 to 5 are supported on XSM channels.

DEFAULT = AnswerAndOriginateCalls"
     DEFVAL {answerAndOrignateCalls }           
     ::= { rlanChannelConfigEntry 4 }


rChanChannelGroup OBJECT-TYPE
     SYNTAX  INTEGER (1..65)
     ACCESS  read-write
     STATUS  mandatory
     DESCRIPTION
	     "Enter the index for the Channel group
	     this channel belongs to. Setting this value on any
	     channel updates all channels that belong to the
	     same port.
	     DEFAULT = 1"
     DEFVAL { 1 }
     ::= { rlanChannelConfigEntry 5 }

rChanHuntGroup OBJECT-TYPE
     SYNTAX  INTEGER (1..16)
     ACCESS  read-write
     STATUS  mandatory
     DESCRIPTION
             "Enter the index for the Hunt group this channel
             belongs to. Setting this value on any channel
             updates all channels that belong to the same
             port.
             DEFAULT = 1"
     DEFVAL { 1 }
     ::= { rlanChannelConfigEntry 6 }

rChanOtherChan OBJECT-TYPE
     SYNTAX  INTEGER (0..256)
     ACCESS  read-only
     STATUS  mandatory
     DESCRIPTION
             "Tells you the corresponding channel that is used if a 
              resource module connection is up. If this is indexed 
	      by a Resource Module it will return the ISDN channel 
	      used or the Resource Module used if this is a BRI or 
	      PRI/DUAL Pri.
              Note: A return of 0 means that any active call does not 
                    include a resource module. Also, there is the 
		    possiblility of 64 channels on a card, therefore 
		    to find the corresponding channel on numbers 
		    returned that are greater than 64, use the 
		    following logic:
                    channel is on card X / 64 and is channel X mod 64."
     ::= { rlanChannelConfigEntry 7 }
 

--
--
--     Basic Rate ISDN B-Channel Configuration Table
--

rlanBriChanConfigTable OBJECT-TYPE
     SYNTAX  SEQUENCE OF RlanBriChanConfigEntry
     ACCESS  not-accessible
     STATUS  mandatory
     DESCRIPTION
	     "This table provides a management view of the
	     system configuration generic parameters specific
	     to Basic Rate ISDN B Channels."
     ::= { rlanChannelGroup 3 }


rlanBriChanConfigEntry OBJECT-TYPE
     SYNTAX  RlanBriChanConfigEntry
     ACCESS  not-accessible
     STATUS  mandatory
     INDEX   { rChanCardID, rChanPortID, rChanID }
     ::= { rlanBriChanConfigTable 1 }


RlanBriChanConfigEntry   ::=
     SEQUENCE {
	 rBChanPhoneNum        DisplayString,
	 rBChanSPID            DisplayString
     }


rBChanPhoneNum OBJECT-TYPE
     SYNTAX  DisplayString (SIZE(0..16))
     ACCESS  read-write
     STATUS  mandatory
     DESCRIPTION
	     "Enter the telephone number that this B Channel responds to."
     ::= { rlanBriChanConfigEntry 1 }


rBChanSPID OBJECT-TYPE
     SYNTAX  DisplayString (SIZE(0..20))
     ACCESS  read-write
     STATUS  mandatory
     DESCRIPTION
	     "Enter the service-profile ID that the Central Office
	     is providing for the B Channel."
     ::= { rlanBriChanConfigEntry 2 }
     
--


--
--      Serial Channel Configuration Table
--

rlanSerialChanConfigTable OBJECT-TYPE
     SYNTAX  SEQUENCE OF RlanSerialChanConfigEntry
     ACCESS  not-accessible
     STATUS  mandatory
     DESCRIPTION
	     "This table provides a management view of the
	     system configuration parameters specific
	     to serial channels."
     ::= { rlanChannelGroup 4 }


rlanSerialChanConfigEntry OBJECT-TYPE
     SYNTAX  RlanSerialChanConfigEntry
     ACCESS  not-accessible
     STATUS  mandatory
     INDEX   { rChanCardID, rChanPortID, rChanID }
     ::= { rlanSerialChanConfigTable 1 }


RlanSerialChanConfigEntry   ::=
     SEQUENCE {
	 rChanCallCtrl        INTEGER,
	 rChanHoldOff         INTEGER,
	 rChanCallSetupTO     INTEGER
     }


rChanCallCtrl OBJECT-TYPE
     SYNTAX  INTEGER {
		 controlSignal(1),
		 v25bis(2)
	     }
     ACCESS  read-write
     STATUS  mandatory
     DESCRIPTION
	     "Select the call-setup/teardown signalling to be used with
              the attached device, which can be one of:
	       controlSignal or v25bis.
              If rChanOpMode is set to 'leased', this option is forced to
	      controlSignal (setting it to any other value will generate 
              a bad value error).
	     DEFAULT =  v25bis" 
     DEFVAL { v25bis }        
     ::= { rlanSerialChanConfigEntry 1 }


rChanHoldOff OBJECT-TYPE
     SYNTAX  INTEGER (0..30)
     ACCESS  read-write
     STATUS  mandatory
     DESCRIPTION
	     "Enter the time (in seconds) between a disconnect and the 
              channel's availability to support an outbound call.
	     DEFAULT = 10"
     DEFVAL { 10 }        
     ::= { rlanSerialChanConfigEntry 2 }


rChanCallSetupTO OBJECT-TYPE
     SYNTAX  INTEGER (2..120)
     ACCESS  read-write
     STATUS  mandatory
     DESCRIPTION
	     "Enter the time (in seconds) for completing call setup that the 
              system allows before timing out.
	     DEFAULT = 30."
     DEFVAL { 30 }        
     ::= { rlanSerialChanConfigEntry 3 }
     
--


--
--         Channel Statistics Table
--


rlanSyncChanStatsTable OBJECT-TYPE
     SYNTAX  SEQUENCE OF RlanSyncChanStatsEntry
     ACCESS  not-accessible
     STATUS  mandatory
     DESCRIPTION
	     "This table provides a management view of the
	     generic statistics for individual, synchronous, data bearing 
	     channels (e.g., PRI, BRI and XSM channels)."
     ::= { rlanChannelGroup 5 }


rlanSyncChanStatsEntry OBJECT-TYPE
     SYNTAX  RlanSyncChanStatsEntry
     ACCESS  not-accessible
     STATUS  mandatory
     INDEX   { rChanCardID, rChanPortID, rChanID }
     ::= { rlanSyncChanStatsTable 1 }


RlanSyncChanStatsEntry ::=
     SEQUENCE {
	 rSyncChanWANStatsIndex   INTEGER,
	 rSyncChanLinkState       INTEGER,
	 rSyncChanRxFrames        Counter,
	 rSyncChanRxOctets        Counter,
	 rSyncChanRxFrameErrs     Counter,
	 rSyncChanRxCRCErrs       Counter,
	 rSyncChanRxOverErrs      Counter,
	 rSyncChanRxAborts        Counter,
	 rSyncChanRxShortFrames   Counter,
	 rSyncChanRxLongFrames    Counter,
	 rSyncChanTxFrames        Counter,
	 rSyncChanTxOctets        Counter,
	 rSyncChanTxFrameErrs     Counter,
	 rSyncChanTxUnderErrs     Counter,
	 rSyncChanTxAborts        Counter,
	 rSyncChanLinkFaults      Counter,
	 rSyncChanResourceShorts  Counter,
	 rSyncChanLastResultCode  INTEGER,
	 rSyncChanConnectedPhnum  DisplayString,
	 rSyncChanConnectedName	  DisplayString
     }


rSyncChanWANStatsIndex OBJECT-TYPE
     SYNTAX  INTEGER  (1..128)
     ACCESS  read-only
     STATUS  mandatory
     DESCRIPTION
	     "Tells you  the WAN link that's associated with
	     this channel. If this channel is not currently connected,
	      you'll see a value of -1."
     ::= { rlanSyncChanStatsEntry 1 }


rSyncChanLinkState OBJECT-TYPE
     SYNTAX  INTEGER {
		 linkDown(1),
		 linkUp(2),
		 linkFaulty(3),
		 linkMdm(9),
		 linkLoading(10),
 		 linkLost(11),
	 	 linkRemoved(12),
		 linkVoice(13),
		 linkPbxPassthru(14)
	     }
     ACCESS  read-only
     STATUS  mandatory
     DESCRIPTION
	     "Tells you the status of the channel's
	      connection, which can be one of: linkDown,
	      LinkUp, or linkFaulty."
     ::= { rlanSyncChanStatsEntry 2 }


rSyncChanRxFrames OBJECT-TYPE
    SYNTAX   Counter
    ACCESS   read-only
    STATUS   mandatory
    DESCRIPTION
	    "Tells you how many HDLC frames this channel has received since
             the last system reset."
    ::= { rlanSyncChanStatsEntry 3 }


rSyncChanRxOctets OBJECT-TYPE
    SYNTAX  Counter
    ACCESS  read-only
    STATUS  mandatory
    DESCRIPTION
	    "Tells you how many octets this channel has received since the 
             last system reset."
    ::= { rlanSyncChanStatsEntry 4 }


rSyncChanRxFrameErrs OBJECT-TYPE
    SYNTAX  Counter
    ACCESS  read-only
    STATUS  mandatory
    DESCRIPTION
	    "Tells you how many HDLC frames this channel has detected but not
             successfully received for one of the following reasons:
		1) Rxed with Bad CRC
		2) Rxed with Overrun errors
		3) Rxed aborted frames "
    ::= { rlanSyncChanStatsEntry 5 }


rSyncChanRxCRCErrs OBJECT-TYPE
    SYNTAX  Counter
    ACCESS  read-only
    STATUS  mandatory
    DESCRIPTION
	    "Tells you how many HDLC frames this channel has
	    received but discarded because of a CRC mismatch."
    ::= { rlanSyncChanStatsEntry 6 }


rSyncChanRxOverErrs OBJECT-TYPE
    SYNTAX  Counter
    ACCESS  read-only
    STATUS  mandatory
    DESCRIPTION
	    "Tells you how many HDLC frames this channel has
	    received but discarded because there was not enough memory in
	    the system to store them."
    ::= { rlanSyncChanStatsEntry 7 }


rSyncChanRxAborts OBJECT-TYPE
    SYNTAX  Counter
    ACCESS  read-only
    STATUS  mandatory
    DESCRIPTION
	    "Tells you how many HDLC frames this channel has
	    received but discarded because the frame had been aborted."
    ::= { rlanSyncChanStatsEntry 8 }


rSyncChanRxShortFrames OBJECT-TYPE
     SYNTAX  Counter
     ACCESS  read-only
     STATUS  mandatory
     DESCRIPTION
	     "Tells you how many HDLC frames this channel has 
	     received that were shorter than 4 bytes in length."
     ::= { rlanSyncChanStatsEntry 9 }              


rSyncChanRxLongFrames OBJECT-TYPE
     SYNTAX  Counter
     ACCESS  read-only
     STATUS  mandatory
     DESCRIPTION
	     "Tells you how many HDLC frames this channel has
	     received that were longer than 4096 bytes in length."
     ::= { rlanSyncChanStatsEntry 10 }              


rSyncChanTxFrames OBJECT-TYPE
    SYNTAX  Counter
    ACCESS  read-only
    STATUS  mandatory
    DESCRIPTION
	    "Tells you how many HDLC frames have been
	    transmitted on this channel since the last system reset."
    ::= { rlanSyncChanStatsEntry 11 }


rSyncChanTxOctets OBJECT-TYPE
    SYNTAX  Counter
    ACCESS  read-only
    STATUS  mandatory
    DESCRIPTION
	    "Tells you  how many octets have been
	    transmitted on this channel since the last
	    system reset."
    ::= { rlanSyncChanStatsEntry 12 }


rSyncChanTxFrameErrs OBJECT-TYPE
    SYNTAX  Counter
    ACCESS  read-only
    STATUS  mandatory
    DESCRIPTION
	    "Tells you how many HDLC frames this channel tried to 
            transmit unsuccessfully since the last system reset for
            one of the following reasons:
		1) TXed underrun
		2) TXed aborted frames "
::= { rlanSyncChanStatsEntry 13 }


rSyncChanTxUnderErrs OBJECT-TYPE
    SYNTAX  Counter
    ACCESS  read-only
    STATUS  mandatory
    DESCRIPTION
	    "Tells you how many HDLC frames this channel
	    tried to transmit unsuccessfully since the last system reset
	    because there was not enough data in memory to transmit."
::= { rlanSyncChanStatsEntry 14 }


rSyncChanTxAborts OBJECT-TYPE
    SYNTAX  Counter
    ACCESS  read-only
    STATUS  mandatory
    DESCRIPTION
	    "Tells you how many  HDLC frames this channel
	    tried to transmit unsuccessfully since the last system reset
	    because the frame had been aborted."
    ::= { rlanSyncChanStatsEntry 15 }


rSyncChanLinkFaults OBJECT-TYPE
    SYNTAX  Counter
    ACCESS  read-only
    STATUS  mandatory
    DESCRIPTION
	    "Tells you how many times the WAN protocol has failed since the 
             last system reset."
    ::= { rlanSyncChanStatsEntry 16 }
 
 
rSyncChanResourceShorts OBJECT-TYPE
    SYNTAX  Counter
    ACCESS  read-only
    STATUS  mandatory
    DESCRIPTION
	    "Tells you how many resource shortages this channel has experienced 
            since the last system reset. 
	    A resource shortage is a condition that occurs when the
	    channel driver runs out of receive buffers."
    ::= { rlanSyncChanStatsEntry 17 }


rSyncChanLastResultCode OBJECT-TYPE
    SYNTAX  INTEGER
    ACCESS  read-only
    STATUS  mandatory
    DESCRIPTION
	    "Tells you the result code from the last call on 
	    this channel."
    ::= { rlanSyncChanStatsEntry 18 }


rSyncChanConnectedPhnum OBJECT-TYPE
    SYNTAX  DisplayString (SIZE(0..16))
    ACCESS  read-only
    STATUS  mandatory
    DESCRIPTION
    	     "This is the phone number (or extension number) of the 
             connected party, i.e. at the far end of this B-channel."
    ::= { rlanSyncChanStatsEntry 19 }


rSyncChanConnectedName OBJECT-TYPE
    SYNTAX  DisplayString (SIZE(0..16))
    ACCESS  read-only
    STATUS  mandatory
    DESCRIPTION
    	     "This is the name of the connected party, i.e. at the 
	     far end of this B-channel. This information is sometimes 
	     passed over the signalling channel of the network when
	     a call is generated or received, and on these occasions
	     the information is captured and stored here."
    ::= { rlanSyncChanStatsEntry 20 }


--
--   { rlanChannelGroup 6 } obsoleted
--
--   ISDN B-channel 
--

rlanIsdnBChanTable OBJECT-TYPE
     SYNTAX  SEQUENCE OF RlanIsdnBChanEntry
     ACCESS  not-accessible
     STATUS  mandatory
     DESCRIPTION
	     "This table provides a management view of the ISDN 
             statistics and configeration for individual B Channels."
     ::= { rlanChannelGroup 6 }


rlanIsdnBChanEntry OBJECT-TYPE
     SYNTAX  RlanIsdnBChanEntry
     ACCESS  not-accessible
     STATUS  mandatory
     INDEX   { rChanCardID, rChanPortID, rChanID }
     ::= { rlanIsdnBChanTable 1 }


RlanIsdnBChanEntry ::=
     SEQUENCE {
	 rIsdnBChanBearer          INTEGER,
	 rIsdnBChanLlSpeed         INTEGER
     }


rIsdnBChanBearer OBJECT-TYPE
     SYNTAX  INTEGER {
		 kbps64Unrestrict(1),
		 kbps56Dig(2),
		 audio3100Hz(3),
		 speech(4),
		 idle(5)
}
     ACCESS  read-only
     STATUS  mandatory
     DESCRIPTION
	     "Tells you what bearer capability is used
	     for this B Channel."
     ::= { rlanIsdnBChanEntry 1 }
--
rIsdnBChanLlSpeed OBJECT-TYPE
     SYNTAX  INTEGER {
		 kbps64Unrestrict(1),
		 kbps56Dig(2)
}
     ACCESS  read-write
     STATUS  mandatory
     DESCRIPTION
	     "Allows configeration of the leased line speed
	     for this B Channel (only valid on leased lines)."
     ::= { rlanIsdnBChanEntry 2 }
--
--

--
--   Serial channel statistics
--

rlanSerialChanStatsTable OBJECT-TYPE
     SYNTAX  SEQUENCE OF RlanSerialChanStatsEntry
     ACCESS  not-accessible
     STATUS  mandatory
     DESCRIPTION
	     "This table provides a management view of the
	     statistics for individual serial channels."
     ::= { rlanChannelGroup 7 }


rlanSerialChanStatsEntry OBJECT-TYPE
     SYNTAX  RlanSerialChanStatsEntry
     ACCESS  not-accessible
     STATUS  mandatory
     INDEX   { rChanCardID, rChanPortID, rChanID }
     ::= { rlanSerialChanStatsTable 1 }


RlanSerialChanStatsEntry ::=
     SEQUENCE {
	 rSerialChanIfType          INTEGER,
	 rSerialChanRole            INTEGER,
	 rSerialChanCtlSignals      INTEGER,
	 rSerialChanLoopBack        INTEGER,
	 rSerialChanInConnects      Counter,
	 rSerialChanOutConnects     Counter,
	 rSerialChanOutConnectFails Counter
     }

rSerialChanIfType OBJECT-TYPE
     SYNTAX  INTEGER {
		 invalidHW(1),
		 rs232(2),
		 v35(3),
		 v11(4)
     }
     ACCESS  read-only
     STATUS  mandatory
     DESCRIPTION
	     "Tells you the type of physical interface
	     signalling that is used for the attached device, which can be one of:
	      invalidHW, rs232, v35,or v11."
     ::= { rlanSerialChanStatsEntry 1 }


rSerialChanRole OBJECT-TYPE
     SYNTAX  INTEGER {
		 unknown(1),
		 dce(2),
		 dte(3)
	     }
     ACCESS  read-only
     STATUS  mandatory
     DESCRIPTION
	     "Tells you what role the device that's using this
	     channel is performing:
		dte - the device is acting as data terminal equipment
		dce - the device is acting as data circuit-terminating equipment."
     ::= { rlanSerialChanStatsEntry 2 }


rSerialChanCtlSignals OBJECT-TYPE
     SYNTAX  INTEGER
     ACCESS  read-only
     STATUS  mandatory
     DESCRIPTION
	     "Tells you the control signal state at the interface, which is bit-
	     mapped as follows:
		     Bit    RS232    V.35    V.11
		     ---    -----    ----    ----
		      0      RTS     RTS     CTRL
		      1      CTS     CTS     IND
		      2      DSR     DSR     n/a
		      3      DCD     DCD     n/a
		      4      DTR     DTR     n/a
		      5      RI      n/a     n/a
		      6      TM      n/a     n/a
		      7      LL      n/a     n/a
		      8      RL      n/a     n/a
		      9      n/a     n/a     n/a
		      10     n/a     n/a     n/a
	     NOTE:  Bit zero (0) is the least significant bit."
     ::= { rlanSerialChanStatsEntry 3 }


rSerialChanLoopBack OBJECT-TYPE
     SYNTAX  INTEGER {
		 noLoopBack(1),
		 localDigLoopBack(2),
		 localAnalogueLoopBack(3),
		 remoteDigitalLoopBack(4)
	      }
     ACCESS  read-only
     STATUS  deprecated
     DESCRIPTION
	     "Tells you the type of loopback test the system is running.
	      NOTE: Applies only to rs232 channels."
     ::= { rlanSerialChanStatsEntry 4 }


rSerialChanInConnects OBJECT-TYPE
     SYNTAX  Counter
     ACCESS  read-only
     STATUS  mandatory
     DESCRIPTION
	     "Tells you how many attempted inbound connects the 
	     signalling protocol in effect for this
	     channel has detected since the last system reset."
     ::= { rlanSerialChanStatsEntry 5 }


rSerialChanOutConnects OBJECT-TYPE
     SYNTAX  Counter
     ACCESS  read-only
     STATUS  mandatory
     DESCRIPTION
	     "Tells you how many outbound connects have been attempted on this
	     channel since the last system reset."
::= { rlanSerialChanStatsEntry 6 }              


rSerialChanOutConnectFails OBJECT-TYPE
     SYNTAX  Counter
     ACCESS  read-only
     STATUS  mandatory
     DESCRIPTION
	     "Tells you how many outbound connects attempted on this
	     channel were not successfully established since the last system reset."
::= { rlanSerialChanStatsEntry 7 }              
		   
--


--
--   Channel Group definition table
--

rChannelGroupIdUnused OBJECT-TYPE
     SYNTAX  INTEGER (0..65)
     ACCESS  read-only
     STATUS  mandatory
     DESCRIPTION
	     "This object is used to identify a potentially unused index
	     that can be used as the rChannelGroupId instance when 
	     creating new entries in the rlanChannelGroupTable. A returned
	     value of zero indicates that the table is full."
     ::= { rlanChannelGroup 8 }
 
 
rlanChannelGroupTable OBJECT-TYPE
     SYNTAX  SEQUENCE OF RlanChannelGroupEntry
     ACCESS  not-accessible
     STATUS  mandatory
     DESCRIPTION
	     "This table provides a management view of the
	     system channel groups."
     ::= { rlanChannelGroup 9 }


rlanChannelGroupEntry OBJECT-TYPE
     SYNTAX  RlanChannelGroupEntry
     ACCESS  not-accessible
     STATUS  mandatory
     DESCRIPTION
	     "The first entry (rChannelGroupId value of one) corresponds 
	     to the default entry. This entry cannot be modified or 
	     deleted."
     INDEX   { rChannelGroupId }
     ::= { rlanChannelGroupTable 1 }


RlanChannelGroupEntry ::=
     SEQUENCE {
	 rChannelGroupId        INTEGER,
	 rChannelGroupName      DisplayString,
	 rChannelGroupStatus    RowStatus
     }


rChannelGroupId OBJECT-TYPE
     SYNTAX  INTEGER (1..65)
     ACCESS  read-only
     STATUS  mandatory
     DESCRIPTION
	     "Tells you the unique identifier for this row."
     ::= { rlanChannelGroupEntry 1 }


rChannelGroupName OBJECT-TYPE
     SYNTAX  DisplayString (SIZE(1..16))
     ACCESS  read-write
     STATUS  mandatory
     DESCRIPTION
	     "Tells you the name of this channel group. Channel group
	     names must be unique and are not case sensitive.
	     You cannot modify the default entry Default."
     ::= { rlanChannelGroupEntry 2 }


rChannelGroupStatus OBJECT-TYPE
     SYNTAX  RowStatus
     ACCESS  read-write
     STATUS  mandatory
     DESCRIPTION
	     "Tells you the current status of this entry. You cannot destroy
	     currently assigned channel groups or the
	     default entry."
     ::= { rlanChannelGroupEntry 3 }

--
--
--  The channel diagnostic group
--

rlanChannelDiagnosticTable OBJECT-TYPE
     SYNTAX  SEQUENCE OF RlanChannelDiagnosticEntry
     ACCESS  not-accessible
     STATUS  mandatory
     DESCRIPTION
	     "This table is used to force connect or disconnect
	     a channel."
     ::= { rlanChannelGroup 10 }
 
 
rlanChannelDiagnosticEntry OBJECT-TYPE
     SYNTAX  RlanChannelDiagnosticEntry
     ACCESS  not-accessible
     STATUS  mandatory
     INDEX   { rChanCardID, rChanPortID, rChanID }
     ::= { rlanChannelDiagnosticTable 1 }
 
 
RlanChannelDiagnosticEntry ::=
     SEQUENCE {
	 rChanDiagRemLANID     INTEGER,
	 rChanDiagForce        INTEGER
     }
 
 
rChanDiagRemLANID OBJECT-TYPE
     SYNTAX  INTEGER (0..1000)
     ACCESS  read-write
     STATUS  mandatory
     DESCRIPTION
	     "Tells you which remote LAN this channel is to connect to.
              The remote LAN values are from 1 to 1000 but reading this 
              value will always return 0."
::= { rlanChannelDiagnosticEntry 1 }
 
 
rChanDiagForce OBJECT-TYPE
     SYNTAX  INTEGER {
		  connect(1),
		  disconnect(2),
		  statusQuo(3)
	     }
     ACCESS  read-write
     STATUS  mandatory
     DESCRIPTION
	     "To tell the system to disconnect this channel,
	     select disconnect from the available settings.
	     When you select connect, the system will try to
	     connect this channel to the remote LAN indicated by
	     rChanDiagRemLANID.
	     NOTE: The configuration for the remote LAN 
	     must be a member of this channel's channel group.
	     DEFAULT = statusQuo"
DEFVAL { statusQuo }
     ::= { rlanChannelDiagnosticEntry 2 }

rlanHuntGroupTable OBJECT-TYPE
     SYNTAX  SEQUENCE OF RlanHuntGroupEntry
     ACCESS  not-accessible
     STATUS  mandatory
     DESCRIPTION
             "This table provides a management view of
             Hunt Groups."
     ::= { rlanChannelGroup 11 }
 
rlanHuntGroupEntry OBJECT-TYPE
     SYNTAX  RlanHuntGroupEntry
     ACCESS  not-accessible
     STATUS  mandatory
     INDEX   { rHuntGroupIndex }
     ::= { rlanHuntGroupTable 1 }
 
RlanHuntGroupEntry ::=
     SEQUENCE {
	 rHuntGroupIndex         INTEGER,
	 rHuntGroupName          DisplayString,
	 rHuntGroupPhoneNum      DisplayString,
	 rHuntGroupRowStatus     RowStatus
     }

rHuntGroupIndex OBJECT-TYPE
     SYNTAX  INTEGER (1..16)
     ACCESS  read-only
     STATUS  mandatory
     DESCRIPTION
             "Tells you which hunt group you are configuring.
              The hunt group values are from 1 to 16."
::= { rlanHuntGroupEntry 1 }

rHuntGroupName OBJECT-TYPE
     SYNTAX  DisplayString (SIZE(1..16))
     ACCESS  read-write
     STATUS  mandatory
     DESCRIPTION
             "The name of this Hunt Group."
::= { rlanHuntGroupEntry 2 }

rHuntGroupPhoneNum OBJECT-TYPE
     SYNTAX  DisplayString (SIZE(0..16))
     ACCESS  read-write
     STATUS  mandatory
     DESCRIPTION
             "The Phone number of this hunt group.  Only printable
	      characters are accepted."
::= { rlanHuntGroupEntry 3 }

rHuntGroupRowStatus OBJECT-TYPE
     SYNTAX  RowStatus
     ACCESS  read-write
     STATUS  mandatory
     DESCRIPTION
             "Tells you the current status of this entry.  The only 
	      states valid for this object are createAndGo(4) and Destroy(6)."
::= { rlanHuntGroupEntry 4 }


--
-- PBX Channel table
--

rlanPBXChanGroupTable OBJECT-TYPE
     SYNTAX  SEQUENCE OF RlanPBXChanGroupEntry
     ACCESS  not-accessible
     STATUS  mandatory
     DESCRIPTION
             "This table provides a management view of
             PBX Channels."
     ::= { rlanChannelGroup 12 }
 
rlanPBXChanGroupEntry OBJECT-TYPE
     SYNTAX  RlanPBXChanGroupEntry
     ACCESS  not-accessible
     STATUS  mandatory
     INDEX   { rChanCardID, rChanPortID, rChanID }
     ::= { rlanPBXChanGroupTable 1 }
 
RlanPBXChanGroupEntry ::=
     SEQUENCE {
	 rPBXChanExtensionNumber  DisplayString,
	 rPBXChanModuleType       INTEGER,
	 rPBXChanPhoneType        INTEGER,
	 rPBXChanEncoding         INTEGER
     }

rPBXChanExtensionNumber OBJECT-TYPE
     SYNTAX  DisplayString (SIZE(1..8))
     ACCESS  read-write
     STATUS  mandatory
     DESCRIPTION
             "The extension number of this PBX channel"
::= { rlanPBXChanGroupEntry 1 }

rPBXChanModuleType OBJECT-TYPE
     SYNTAX  INTEGER {
		none(1),
		ntSwitchEnd(2),
		ntPhoneEnd(3),
		gandalfAnalogPhoneEnd(4),
		gandalfAnalogSwitchEnd(5),
		mitelVpm(6)
	     }
     ACCESS  read-write
     STATUS  mandatory
     DESCRIPTION
             "The module type of this PBX channel.
	     Cannot be set to none(1),gandalfAnalogPhoneEnd(4)'
	     or gandalfAnalogSwitchEnd(5) ."
::= { rlanPBXChanGroupEntry 2 }


rPBXChanPhoneType OBJECT-TYPE
     SYNTAX  INTEGER {
		meridian(2),
		norstar(3)
	     }
     ACCESS  read-write
     STATUS  mandatory
     DESCRIPTION
             "The phone type connected to this PBX channel"
::= { rlanPBXChanGroupEntry 3 }

rPBXChanEncoding OBJECT-TYPE
     SYNTAX  INTEGER {
		uLaw(1),
		aLaw(2)
	     }
     ACCESS  read-write
     STATUS  mandatory
     DESCRIPTION
             "The type of PCM encoding for this PBX channel"
::= { rlanPBXChanGroupEntry 4 }

rPBXChanVpmMode OBJECT-TYPE
     SYNTAX  INTEGER {
		unknown(1),
		mitelSwitchEnd(2),
		mitelPhoneEnd(3)
	     }
     ACCESS  read-write
     STATUS  mandatory
     DESCRIPTION
             "The mode of the Voice Processing Module.
	      The value of 1 is for information only and
	      cannot be set."
::= { rlanPBXChanGroupEntry 5 }

--
--     Resource Module Management and Configuration Table
--     

rlanResourceModuleTable OBJECT-TYPE
     SYNTAX  SEQUENCE OF RlanResourceModuleEntry
     ACCESS  not-accessible
     STATUS  mandatory
     DESCRIPTION
	     "This table provides a management view of the
	     parameters specific to Modem and PBX card channels 
	     (i.e., Modems and PBX Ports)."
     ::= { rlanChannelGroup 13 }


rlanResourceModuleEntry OBJECT-TYPE
     SYNTAX  RlanResourceModuleEntry
     ACCESS  not-accessible
     STATUS  mandatory
     INDEX   { rChanCardID, rChanPortID, rChanID }
     ::= { rlanResourceModuleTable 1 }

RlanResourceModuleEntry ::=
     SEQUENCE {
	 rResourceModuleOffline    INTEGER,
	 rResourceModuleLinkstate  INTEGER
     }

rResourceModuleOffline OBJECT-TYPE
     SYNTAX  INTEGER {
		offline(1),
		online(2)
	     }
     ACCESS  read-write
     STATUS  mandatory
     DESCRIPTION
             "The online state of a module. Setting offline will not
	      allow the module to go online. Setting online will enable
	      the module to send and receive calls.
	      Reading this object always returns online(2)
	      regardless of the modules's current operational state."
::= { rlanResourceModuleEntry 1 }

rResourceModuleLinkstate OBJECT-TYPE
     SYNTAX  INTEGER {
		offline(1),
		online(2),
		downloading(10),
		linklost(11),
	        notinstalled(12)
	     }
     ACCESS  read-only
     STATUS  mandatory
     DESCRIPTION
             "The current operational state of the resource module."
::= { rlanResourceModuleEntry 2 }



--
--     PBX channel statistics Table
--     

rlanPBXChanNTStatsTable OBJECT-TYPE
     SYNTAX  SEQUENCE OF RlanPBXChanNTStatsEntry
     ACCESS  not-accessible
     STATUS  mandatory
     DESCRIPTION
             "This table provides a statistical view of
             Norther Telecom type of PBX Channels."
     ::= { rlanChannelGroup 14 }
 
rlanPBXChanNTStatsEntry OBJECT-TYPE
     SYNTAX  RlanPBXChanNTStatsEntry
     ACCESS  not-accessible
     STATUS  mandatory
     INDEX   { rChanCardID, rChanPortID, rChanID }
     ::= { rlanPBXChanNTStatsTable 1 }
 
RlanPBXChanNTStatsEntry ::=
     SEQUENCE {
	rPBXChanNTVoiceTimingPackets Counter,
	rPBXChanNTSignalCrcErr       Counter,	
	rPBXChanNTInvalidAddress     Counter,
	rPBXChanNTSignalRejects      Counter,
	rPBXChanNTMaxRetryErr        Counter,
	rPBXChanNTLostSyncErr        Counter,
	rPBXChanNTNoDataSignal       Counter,
	rPBXChanNTAckTimeout         Counter,
	rPBXChanNTTransLockup        Counter,
	rPBXChanNTReinitTries        Counter,
	rPBXChanNTDiscFails          Counter,
	rPBXChanNTRetrans            Counter,
	rPBXChanNTInternalDisc       Counter,
	rPBXChanNTFatalPanics        Counter,
	rPBXChanNTLinkIntegrity      Counter,
	rPBXChanNTRxFails	     Counter,
	rPBXChanNTTxFails	     Counter,
	rPBXChanNTCallsRx	     Counter,
	rPBXChanNTCallsTx	     Counter
     }

rPBXChanNTVoiceTimingPackets OBJECT-TYPE
    SYNTAX  Counter
    ACCESS  read-only
    STATUS  mandatory
    DESCRIPTION
	    "Tells you how many Voice Timing Packets this 
	    link has processed."
    ::= { rlanPBXChanNTStatsEntry 1 }

rPBXChanNTSignalCrcErr OBJECT-TYPE
    SYNTAX  Counter
    ACCESS  read-only
    STATUS  mandatory
    DESCRIPTION
	    "Tells you how many Signal Packets with 
	     CRC errors this link has processed."
    ::= { rlanPBXChanNTStatsEntry 2 }

rPBXChanNTInvalidAddress OBJECT-TYPE
    SYNTAX  Counter
    ACCESS  read-only
    STATUS  mandatory
    DESCRIPTION
	    "Tells you how many packets that have V.42
	     address errors this link has processed."
    ::= { rlanPBXChanNTStatsEntry 3 }

rPBXChanNTSignalRejects OBJECT-TYPE
    SYNTAX  Counter
    ACCESS  read-only
    STATUS  mandatory
    DESCRIPTION
	    "Tells you how many times a voice packet
	     is received before an initialization packet 
	     is received."
    ::= { rlanPBXChanNTStatsEntry 4 }

rPBXChanNTMaxRetryErr OBJECT-TYPE
    SYNTAX  Counter
    ACCESS  read-only
    STATUS  mandatory
    DESCRIPTION
	    "Tells you how many times this link has 
	     reached maximum retries."
    ::= { rlanPBXChanNTStatsEntry 5 }

rPBXChanNTLostSyncErr OBJECT-TYPE
    SYNTAX  Counter
    ACCESS  read-only
    STATUS  mandatory
    DESCRIPTION
	    "Tells you how many times this link has 
	     received a voice packet when it shouldn't,
	     or sent a packet of one type and received
	     an unexpected type of response packet."
    ::= { rlanPBXChanNTStatsEntry 6 }

rPBXChanNTNoDataSignal OBJECT-TYPE
    SYNTAX  Counter
    ACCESS  read-only
    STATUS  mandatory
    DESCRIPTION
	    "Tells you how many No Data Signal 
	     errors this link has processed."
    ::= { rlanPBXChanNTStatsEntry 7 }

rPBXChanNTAckTimeout OBJECT-TYPE
    SYNTAX  Counter
    ACCESS  read-only
    STATUS  mandatory
    DESCRIPTION
	    "Tells you how many times a packet is 
	     sent without receiveing an acknowledgement
	     packet."
    ::= { rlanPBXChanNTStatsEntry 8 }

rPBXChanNTTransLockup OBJECT-TYPE
    SYNTAX  Counter
    ACCESS  read-only
    STATUS  mandatory
    DESCRIPTION
	    "This counter is incremented for every packet
	     that fails to be removed from the transmit
	     buffer. 
	     eg. SDS signal not received by the PBX 
 	     extender."
    ::= { rlanPBXChanNTStatsEntry 9 }

rPBXChanNTReinitTries OBJECT-TYPE
    SYNTAX  Counter
    ACCESS  read-only
    STATUS  mandatory
    DESCRIPTION
	    "Tells you the number of reinitialization 
	     attempts on this link."
    ::= { rlanPBXChanNTStatsEntry 10 }

rPBXChanNTDiscFails OBJECT-TYPE
    SYNTAX  Counter
    ACCESS  read-only
    STATUS  mandatory
    DESCRIPTION
	    "Tells you the number of disconnect  
	     failures this link has processed."
    ::= { rlanPBXChanNTStatsEntry 11 }

rPBXChanNTRetrans OBJECT-TYPE
    SYNTAX  Counter
    ACCESS  read-only
    STATUS  mandatory
    DESCRIPTION
	    "This counter increments if there are
	     three retransmission attempts in a row."
    ::= { rlanPBXChanNTStatsEntry 12 }

rPBXChanNTInternalDisc OBJECT-TYPE
    SYNTAX  Counter
    ACCESS  read-only
    STATUS  mandatory
    DESCRIPTION
	    "Tells you how many times the PBX thinks
	     that the phone is lost. Only applies to
	     the central extender."
    ::= { rlanPBXChanNTStatsEntry 13 }

rPBXChanNTFatalPanics OBJECT-TYPE
    SYNTAX  Counter
    ACCESS  read-only
    STATUS  mandatory
    DESCRIPTION
	    "Tells you how many fatal panics have 
	     occured on this port."
    ::= { rlanPBXChanNTStatsEntry 14 }

rPBXChanNTLinkIntegrity OBJECT-TYPE
    SYNTAX  Counter
    ACCESS  read-only
    STATUS  mandatory
    DESCRIPTION
	    "Tells you how many link integrity problems 
	     have occured on this port."
    ::= { rlanPBXChanNTStatsEntry 15 }

rPBXChanNTRxFails OBJECT-TYPE
    SYNTAX  Counter
    ACCESS  read-only
    STATUS  mandatory
    DESCRIPTION
	    "Tells you how many failed incoming calls
	     have occured on this port."
    ::= { rlanPBXChanNTStatsEntry 16 }

rPBXChanNTTxFails OBJECT-TYPE
    SYNTAX  Counter
    ACCESS  read-only
    STATUS  mandatory
    DESCRIPTION
	    "Tells you how many failed outgoing calls
	     have occured on this port."
    ::= { rlanPBXChanNTStatsEntry 17 }

rPBXChanNTCallsRx OBJECT-TYPE
    SYNTAX  Counter
    ACCESS  read-only
    STATUS  mandatory
    DESCRIPTION
	    "Tells you how many successful incoming calls
	     have occured on this port."
    ::= { rlanPBXChanNTStatsEntry 18 }

rPBXChanNTCallsTx OBJECT-TYPE
    SYNTAX  Counter
    ACCESS  read-only
    STATUS  mandatory
    DESCRIPTION
	    "Tells you how many successful outgoing calls
	     have occured on this port."
    ::= { rlanPBXChanNTStatsEntry 19 }

--
-- End of rlanChannelGroup
--



--
-- Definition of rlanWANStatsGroup
--

rlanWANStatsTable OBJECT-TYPE
     SYNTAX  SEQUENCE OF RlanWANStatsEntry
     ACCESS  not-accessible
     STATUS  mandatory
     DESCRIPTION
	     "This table provides a management view of the
	     system configuration specific to individual WAN links."
     ::= { rlanWANStatsGroup 1 }

rlanWANStatsEntry OBJECT-TYPE
     SYNTAX  RlanWANStatsEntry
     ACCESS  not-accessible
     STATUS  mandatory
     INDEX   { rWANStatsIndex }
     ::= { rlanWANStatsTable 1 }

RlanWANStatsEntry ::=
     SEQUENCE {
	 rWANStatsIndex           INTEGER,
	 rWANStatsCardID          INTEGER,
	 rWANStatsPortID          INTEGER,
	 rWANStatsChanID          INTEGER,
	 rWANStatsRemLANID        INTEGER,
	 rWANStatsRemLANName      DisplayString,
	 rWANStatsRxFrames        Counter,
	 rWANStatsRxOctets        Counter,
	 rWANStatsRxFrameErrs     Counter,
	 rWANStatsRxCRCErrs       Counter,
	 rWANStatsRxOverErrs      Counter,
	 rWANStatsRxAborts        Counter,
	 rWANStatsRatioErrRx      INTEGER,
	 rWANStatsTxFrames        Counter,
	 rWANStatsTxOctets        Counter,
	 rWANStatsTxFrameErrs     Counter,
	 rWANStatsTxUnderErrs     Counter,
	 rWANStatsTxAborts        Counter,
	 rWANStatsRatioErrTx      INTEGER,
	 rWANStatsDuration        TimeTicks,
	 rWANStatsChanSpeed       INTEGER,
	 rWANStatsRemExtID	  INTEGER,
	 rWANStatsRemExtName	  DisplayString,
	 rWANStatsRMCardID	  INTEGER,
	 rWANStatsRMPortID	  INTEGER,
	 rWANStatsRMChanID	  INTEGER
     }


rWANStatsIndex OBJECT-TYPE
     SYNTAX  INTEGER (1..128)
     ACCESS  read-only
     STATUS  mandatory
     DESCRIPTION
	     "Tells you which one of the possible 
	     128 WAN links the current statistics apply to. 
	     This index is mapped to a specific channel.
	     To find out which WAN link to use, get the rChanWANStatsIndex
	     attribute from the channel group first."
     ::= { rlanWANStatsEntry 1 }


rWANStatsCardID OBJECT-TYPE
     SYNTAX  INTEGER (1..11)
     ACCESS  read-only
     STATUS  mandatory
     DESCRIPTION
	     "Tells you which card this WAN link is 
	     using to talk to the currently connected remote LAN."
     ::= { rlanWANStatsEntry 2 }

rWANStatsPortID OBJECT-TYPE
     SYNTAX  INTEGER (1..30)
     ACCESS  read-only
     STATUS  mandatory
     DESCRIPTION
	     "Tells you which port this WAN link is 
	     using to talk to the currently connected remote LAN."
     ::= { rlanWANStatsEntry 3 }

rWANStatsChanID OBJECT-TYPE
     SYNTAX  INTEGER (1..61)
     ACCESS  read-only
     STATUS  mandatory
     DESCRIPTION
	     "Tells you which of the 61 possible channels
	     this WAN link is using to talk to the currently connected 
	     remote LAN. The number of possible channels will vary depending on card
	     type. For example a BRI has 2 channels/port, a PRI can have
	     up to 61 channels/port (European CEPT) and an XSM has one
	     channel/port."
     ::= { rlanWANStatsEntry 4 }


rWANStatsRemLANID OBJECT-TYPE
     SYNTAX  INTEGER (1..1000)
     ACCESS   read-only
     STATUS   mandatory
     DESCRIPTION
	     "Tells you which remote LAN this WAN
	     link connects to, by providing the index to be used in the
	     rlanRemLANGroup."
     ::= { rlanWANStatsEntry 5 }


rWANStatsRemLANName OBJECT-TYPE
     SYNTAX  DisplayString (SIZE(1..16))
     ACCESS  read-only
     STATUS  mandatory
     DESCRIPTION
	     "Tells you which remote LAN this WAN
	     link connects to by providing the name of the remote LAN."
     ::= { rlanWANStatsEntry 6 }

rWANStatsRxFrames OBJECT-TYPE
    SYNTAX  Counter
    ACCESS  read-only
    STATUS  mandatory
    DESCRIPTION
	    "Tells you how many HDLC frames this WAN 
	    link received during the current call."
    ::= { rlanWANStatsEntry 7 }


rWANStatsRxOctets OBJECT-TYPE
    SYNTAX  Counter
    ACCESS  read-only
    STATUS  mandatory
    DESCRIPTION
	    "Tells you how many octets this WAN link received
	    during the current call."
    ::= { rlanWANStatsEntry 8 }


rWANStatsRxFrameErrs OBJECT-TYPE
    SYNTAX  Counter
    ACCESS  read-only
    STATUS  mandatory
    DESCRIPTION
	    "Tells you how many HDLC frames this WAN link detected
	    but did not successfully receive during the current call
            for one of the following reasons:
		1) Rxed with Bad CRC
		2) Rxed with Overrun errors
		3) Rxed aborted frames "
    ::= { rlanWANStatsEntry 9 }


rWANStatsRxCRCErrs OBJECT-TYPE
    SYNTAX  Counter
    ACCESS  read-only
    STATUS  mandatory
    DESCRIPTION
	    "Tells you how many HDLC frames this WAN link received but then discarded 
	    because of a CRC mismatch during the current call."
    ::= { rlanWANStatsEntry 10 }


rWANStatsRxOverErrs OBJECT-TYPE
    SYNTAX  Counter
    ACCESS  read-only
    STATUS  mandatory
    DESCRIPTION
	    "Tells you how many HDLC frames this WAN link received but then discarded 
	    during the current call because there wasn't enough 
	    memory in the system to store them."
    ::= { rlanWANStatsEntry 11 }


rWANStatsRxAborts OBJECT-TYPE
    SYNTAX  Counter
    ACCESS  read-only
    STATUS  mandatory
    DESCRIPTION
	    "Tells you how many HDLC frames this WANlink received but then discarded 
	    during the current call because the frame had been aborted."
    ::= { rlanWANStatsEntry 12 }


rWANStatsRatioErrRx OBJECT-TYPE
    SYNTAX  INTEGER
    ACCESS  read-only
    STATUS  mandatory
    DESCRIPTION
	    "Tells you the ratio of unsuccessfully received HDLC frames to 
	    the number of frames that this WAN link detected during the current call."
    ::= { rlanWANStatsEntry 13 }


rWANStatsTxFrames OBJECT-TYPE
    SYNTAX  Counter
    ACCESS  read-only
    STATUS  mandatory
    DESCRIPTION
	    "Tells you how many HDLC frames this WAN 
	    link transmitted during the current call."
    ::= { rlanWANStatsEntry 14 }


rWANStatsTxOctets OBJECT-TYPE
    SYNTAX  Counter
    ACCESS  read-only
    STATUS  mandatory
    DESCRIPTION
	    "Tells you how many octets this WAN link transmitted
	    during the current call."
    ::= { rlanWANStatsEntry 15 }


rWANStatsTxFrameErrs OBJECT-TYPE
    SYNTAX  Counter
    ACCESS  read-only
    STATUS  mandatory
    DESCRIPTION
	    "Tells you how many  HDLC frames this WAN link tried to transmit
             unsuccessfully during the current call for one of the following 
	     reasons:
		1) TXed underrun
		2) TXed aborted frames"
    ::= { rlanWANStatsEntry 16 }


rWANStatsTxUnderErrs OBJECT-TYPE
    SYNTAX  Counter
    ACCESS  read-only
    STATUS  mandatory
    DESCRIPTION
	    "Tells you how many HDLC frames this WAN link tried to transmit 
	    unsuccessfully during the current call because there wasn't enough 
	    data in memory to transmit."
    ::= { rlanWANStatsEntry 17 }


rWANStatsTxAborts OBJECT-TYPE
    SYNTAX  Counter
    ACCESS  read-only
    STATUS  mandatory
    DESCRIPTION
	    "Tells you how many HDLC frames this WAN link tried to transmit 
	    unsuccessfully during the current call because the frame had been aborted."
    ::= { rlanWANStatsEntry 18 }


rWANStatsRatioErrTx OBJECT-TYPE
    SYNTAX  INTEGER
    ACCESS  read-only
    STATUS  mandatory
    DESCRIPTION
	    "Tells you the ratio of unsuccessfully transmitted frames 
	    to the number of attempted frame transmissions during the current call."
    ::= { rlanWANStatsEntry 19 }


 rWANStatsDuration OBJECT-TYPE
    SYNTAX  TimeTicks
    ACCESS  read-only
    STATUS  mandatory
    DESCRIPTION
	    "Tells you how long (in hundredths of a second) the system 
            has accumulated statistics for this WAN link."
    ::= { rlanWANStatsEntry 20 }

 rWANStatsChanSpeed  OBJECT-TYPE
    SYNTAX   INTEGER
    ACCESS   read-only
    STATUS   mandatory
    DESCRIPTION
       "Tells you the current channel speed in bits per second."
    ::= { rlanWANStatsEntry 21 }

rWANStatsRemExtID OBJECT-TYPE
     SYNTAX  INTEGER (1..1000)
     ACCESS   read-only
     STATUS   mandatory
     DESCRIPTION
	     "Tells you which remote Extension this WAN
	     link connects to, by providing the index to 
	     be used in the rlanRemExtGroup."
     ::= { rlanWANStatsEntry 22 }


rWANStatsRemExtName OBJECT-TYPE
     SYNTAX  DisplayString (SIZE(1..16))
     ACCESS  read-only
     STATUS  mandatory
     DESCRIPTION
	     "Tells you which remote Extension this WAN
	     link connects to by providing the name of 
	     the remote Extension."
     ::= { rlanWANStatsEntry 23 }


rWANStatsRMCardID OBJECT-TYPE
     SYNTAX  INTEGER (1..11)
     ACCESS  read-only
     STATUS  mandatory
     DESCRIPTION
	     "Tells you which Resource Module card 
	     this WAN link is using to talk to the 
	     currently connected remote."
     ::= { rlanWANStatsEntry 24 }

rWANStatsRMPortID OBJECT-TYPE
     SYNTAX  INTEGER (1..30)
     ACCESS  read-only
     STATUS  mandatory
     DESCRIPTION
	     "Tells you which Resource Module port 
	     this WAN link is using to talk to the 
	     currently connected remote."
     ::= { rlanWANStatsEntry 25 }

rWANStatsRMChanID OBJECT-TYPE
     SYNTAX  INTEGER (1..61)
     ACCESS  read-only
     STATUS  mandatory
     DESCRIPTION
	     "Tells you which Resource Module Channel 
	     this WAN link is using to talk to the 
	     currently connected remote."
     ::= { rlanWANStatsEntry 26 }


--


rlanWANStatsRMChanTable OBJECT-TYPE
     SYNTAX  SEQUENCE OF RlanWANStatsRMChanEntry
     ACCESS  not-accessible
     STATUS  mandatory
     DESCRIPTION
	     "This table provides a management view of the
	     RM channels associated with a call at any time."
     ::= { rlanWANStatsGroup 2 }

rlanWANStatsRMChanEntry OBJECT-TYPE
     SYNTAX  RlanWANStatsRMChanEntry
     ACCESS  not-accessible
     STATUS  mandatory
     INDEX   { rWANStatsRMWanIndex, rWANStatsRMChanIndex }
     ::= { rlanWANStatsRMChanTable 1 }

RlanWANStatsRMChanEntry ::=
     SEQUENCE {
	 rWANStatsRMWanIndex	  	INTEGER,
	 rWANStatsRMChanIndex	  	INTEGER,
	 rWANStatsRMChanCardID	  	INTEGER,
	 rWANStatsRMChanPortID	  	INTEGER,
	 rWANStatsRMChanChanID	  	INTEGER,
	 rWANStatsRMChanConnectedPhnum  DisplayString,
	 rWANStatsRMChanConnectedName	DisplayString
     }

rWANStatsRMWanIndex OBJECT-TYPE
     SYNTAX  INTEGER (1..288)
     ACCESS  read-only
     STATUS  mandatory
     DESCRIPTION
	     "Tells you which one of the possible 
	     160 real WAN links or 128 virtual the current statistics apply to. 
	     This index is mapped to a specific channel.
	     To find out which WAN link to use, get the rChanWANStatsIndex
	     attribute from the channel group first."
     ::= { rlanWANStatsRMChanEntry 1 }

rWANStatsRMChanIndex OBJECT-TYPE
     SYNTAX  INTEGER (1..6)
     ACCESS  read-only
     STATUS  mandatory
     DESCRIPTION
	     "Gives the channel index for the particular channel in use
	      by the call."
     ::= { rlanWANStatsRMChanEntry 2 }

rWANStatsRMChanCardID OBJECT-TYPE
     SYNTAX  INTEGER (1..11)
     ACCESS  read-only
     STATUS  mandatory
     DESCRIPTION
	     "Tells you which Resource Module card 
	     this channel is on."
     ::= { rlanWANStatsRMChanEntry 3 }

rWANStatsRMChanPortID OBJECT-TYPE
     SYNTAX  INTEGER (1..30)
     ACCESS  read-only
     STATUS  mandatory
     DESCRIPTION
	     "Tells you which Resource Module port 
	     this channel is on."
     ::= { rlanWANStatsRMChanEntry 4 }

rWANStatsRMChanChanID OBJECT-TYPE
     SYNTAX  INTEGER (1..61)
     ACCESS  read-only
     STATUS  mandatory
     DESCRIPTION
	     "Tells you which Resource Module Channel 
	     this channel is on."
     ::= { rlanWANStatsRMChanEntry 5 }

rWANStatsRMChanConnectedPhnum OBJECT-TYPE
    SYNTAX  DisplayString (SIZE(0..16))
    ACCESS  read-only
    STATUS  mandatory
    DESCRIPTION
    	     "This is the phone number (or extension number) of the 
             connected party, i.e. at the far end of this B-channel."
     ::= { rlanWANStatsRMChanEntry 6 }

rWANStatsRMChanConnectedName OBJECT-TYPE
    SYNTAX  DisplayString (SIZE(0..16))
    ACCESS  read-only
    STATUS  mandatory
    DESCRIPTION
    	     "This is the name of the connected party, i.e. at the 
	     far end of this B-channel. This information is sometimes 
	     passed over the signalling channel of the network when
	     a call is generated or received, and on these occasions
	     the information is captured and stored here."
     ::= { rlanWANStatsRMChanEntry 7 }


--
-- Definition of the rlanWANSummation group
--


rWANSumRxFrames OBJECT-TYPE
     SYNTAX  Counter
     ACCESS  read-only
     STATUS  mandatory
     DESCRIPTION
	     "Tells you  how many frames the
	     system has received since the last reset."
     ::= { rlanWANSummationGroup 1 }


rWANSumRxOctets OBJECT-TYPE
     SYNTAX  Counter
     ACCESS  read-only
     STATUS  mandatory
     DESCRIPTION
	     "Tells you how many octets the
	     system has received since the last reset."
     ::= { rlanWANSummationGroup 2 }


rWANSumRxFrameErrs OBJECT-TYPE
    SYNTAX  Counter
    ACCESS  read-only
    STATUS  mandatory
    DESCRIPTION
	    "Tells you how many HDLC frames the system
	    detected since the last reset, but did not successfully 
	    receive for one of the following reasons:
		1) Rxed with Bad CRC
		2) Rxed with Overrun errors
		3) Rxed aborted frames "
    ::= { rlanWANSummationGroup 3 }


rWANSumRxCRCErrs OBJECT-TYPE
     SYNTAX  Counter
     ACCESS  read-only
     STATUS  mandatory
     DESCRIPTION
	     "Tells you  how many HDLC frames with CRC mismatches the
	     system has received since the last reset."
     ::= { rlanWANSummationGroup 4 }


rWANSumRxOverErrs OBJECT-TYPE
     SYNTAX  Counter
     ACCESS  read-only
     STATUS  mandatory
     DESCRIPTION
	     "Tells you how many HDLC frames with overrun errors the
	     system has received since the last reset."
     ::= { rlanWANSummationGroup 5 }

rWANSumRxAborts OBJECT-TYPE
     SYNTAX  Counter
     ACCESS  read-only
     STATUS  mandatory
     DESCRIPTION
	     "Tells you how many aborted HDLC frames the
	     system has received since the last reset."
     ::= { rlanWANSummationGroup 6 }

rWANSumTxFrames OBJECT-TYPE
     SYNTAX  Counter
     ACCESS  read-only
     STATUS  mandatory
     DESCRIPTION
	     "Tells you how many HDLC frames the
	     system has transmitted since the last reset."
     ::= { rlanWANSummationGroup 7 }

rWANSumTxOctets OBJECT-TYPE
     SYNTAX  Counter
     ACCESS  read-only
     STATUS  mandatory
     DESCRIPTION
	     "Tells you how many octets the
	     system has transmitted since the last reset."
     ::= { rlanWANSummationGroup 8 }

rWANSumTxFrameErrs OBJECT-TYPE
     SYNTAX  Counter
     ACCESS  read-only
     STATUS  mandatory
     DESCRIPTION
	     "Tells you how many  HDLC frames the system has 
	     detected since the last reset that were not successfully 
	     received for one of the following 2 reasons:
		1) Txed with underrun errors
		2) Txed aborted frames "
    ::= { rlanWANSummationGroup 9 }

rWANSumTxUnderErrs OBJECT-TYPE
     SYNTAX  Counter
     ACCESS  read-only
     STATUS  mandatory
     DESCRIPTION
	     "Tells you how many HDLC frames with underrun errors the
	     system has transmitted since the last 
	     reset."
     ::= { rlanWANSummationGroup 10 }

rWANSumTxAborts OBJECT-TYPE
     SYNTAX  Counter
     ACCESS  read-only
     STATUS  mandatory
     DESCRIPTION
	     "Tells you how many frames the
	     system has aborted during transmission
	     since the last reset."
     ::= { rlanWANSummationGroup 11 }

rWANSumLinkFaults OBJECT-TYPE
     SYNTAX  Counter
     ACCESS  read-only
     STATUS  mandatory
     DESCRIPTION
	     "Tells you how many link fault errors have occurred
	     since the last reset."
     ::= { rlanWANSummationGroup 12 }

-- End of rlanWANSummation group
-- 


--
-- Definition of rlanRemLANGroup
--

--
--   { rlanRemLANGroup 1 } obsoleted
--

rRemLANIDUnused OBJECT-TYPE
     SYNTAX  INTEGER (0..1000)
     ACCESS  read-only
     STATUS  mandatory
     DESCRIPTION
	     "This object is used to identify a potentially unused index
	     to be used as the rRemLANID when creating new entries in the 
	     rlanRemLANConfigTable. A returned value of zero indicates that
	     the table is full."
     ::= { rlanRemLANGroup 2 }
 
 
rlanRemLANConfigTable OBJECT-TYPE
     SYNTAX  SEQUENCE OF RlanRemLANConfigEntry
     ACCESS  not-accessible
     STATUS  mandatory
     DESCRIPTION
	     "This table provides a management view of the
	     system configuration specific to individual Remote 
	     LAN's."
     ::= { rlanRemLANGroup 3 }


rlanRemLANConfigEntry OBJECT-TYPE
     SYNTAX  RlanRemLANConfigEntry
     ACCESS  not-accessible
     STATUS  mandatory
     DESCRIPTION
	     "The conceptual row at instance zero is used by the
	     RSC as the default remote LAN configuration. 
	     The values defined for this entry are assigned to learned
	     LAN's when the system is in remote LAN learning mode 
	     (rSysRLANLearningAdminState is enabled(2)).  This entry is 
	     also used to change the defaults chosen when manually 
	     configuring a new remote LAN either through the embedded 
	     console or via SNMP."
     INDEX { rRemLANID }
     ::= { rlanRemLANConfigTable 1 }


RlanRemLANConfigEntry ::=
     SEQUENCE {
	 rRemLANID                     INTEGER,
	 rRemLANName                   DisplayString,
	 rRemLANOpMode                 INTEGER,
	 rRemLANOutMinBearer           INTEGER,
	 rRemLANCompression            INTEGER,
	 rRemLANWanProtocol            INTEGER,
	 rRemLANIdleTimeout            INTEGER,
	 rRemLANMaxChannels            INTEGER,
	 rRemLANFlooding               INTEGER,
	 rRemLANMCastFwd               INTEGER,
	 rRemLANBCastFwd               INTEGER,
	 rRemLANCallForce              INTEGER,
	 rRemLANWatchdogSpoofing       INTEGER,
	 rRemLANSAPandRIPSpoofingFiltering INTEGER,
	 rRemLANSAPGroups              OCTET STRING,
	 rRemLANStatus                 RowStatus,
	 rRemLANAroundCorner           INTEGER,
 	 rRemLANPPPNcpTypes            INTEGER,
    	 rRemLANHuntGroup              INTEGER,
	 rRemLANMdmAnswer              INTEGER,
	 rRemLANEncryption             INTEGER,
	 rRemLANSNASpoofing            INTEGER,
    rRemLANDialBack               INTEGER,
	 rRemLANTestPresence           DisplayString,
	 rRemLANAllAtOnce	       INTEGER
     }


rRemLANID OBJECT-TYPE
     SYNTAX  INTEGER (0..1000)
     ACCESS  read-only
     STATUS  mandatory
     DESCRIPTION
	     "Tells you the index of this remote LAN. A value of 0 indicates
	     the default remote-LAN configuration; that is, this entry is used
	     to determine the default parameters for remote LANs that are
	     dynamically learned."
     ::= { rlanRemLANConfigEntry 1 }


rRemLANName OBJECT-TYPE
     SYNTAX  DisplayString (SIZE(1..16))
     ACCESS  read-write
     STATUS  mandatory
     DESCRIPTION
	     "Enter the name of the current remote LAN. The name can use 
	     up to 16 characters but cannot contain spaces. The name 
	     must also be unique. It cannot be LOCAL_LAN or begin with 
	     LEARNT_LAN. The default entry (instance zero) cannot be
	     modified."
     ::= { rlanRemLANConfigEntry 2 }


rRemLANOpMode OBJECT-TYPE
     SYNTAX  INTEGER {
		 disabled(1),
		 answerCallsOnly(2),
		 answerAndOriginateCalls(3),
		 callingOnly(4)
	     }
     ACCESS  read-write
     STATUS  mandatory
     DESCRIPTION
	     "Tells you the current operational mode of this remote LAN,
              which can be one of:
		1- disabled: the system will not accept calls from
			     this remote LAN or generate calls to this
			     remote LAN
		2- answerCallsOnly: the system will only answer 
				    calls from this remote LAN.
		3- answerAndOriginateCalls: the system will accept and 
				       generate calls from/to this 
				       remote LAN.
		4- originateCallsOnly: the system will only 
				       generate calls to this Remote LAN.
DEFAULT = answerAndOriginateCalls"
     DEFVAL { answerAndOriginateCalls }                                  
     ::= { rlanRemLANConfigEntry 3 }
 
 
rRemLANOutMinBearer OBJECT-TYPE
     SYNTAX  INTEGER {
		 kbps64Unrestrict(1),
		 kbps56Dig(2),
		 audio3100Hz(3)
	      }
     ACCESS   read-write
     STATUS   mandatory
     DESCRIPTION
	    "Select the minimum bearer capability allowed during an
	    outgoing call to a remote LAN when using ISDN services:
              64 Kbps Unrestricted, 56 Kbps Digital, 3100 Hz Audio.
	    DEFAULT = kbps64Unrestrict "
     DEFVAL { kbps64Unrestrict }        
     ::= { rlanRemLANConfigEntry 4 }


rRemLANCompression OBJECT-TYPE
     SYNTAX  INTEGER {
		 none(1),
		 any(2),
		 gandalf(3),
		 stacker(4)
	      }
     ACCESS   read-write
     STATUS   mandatory
     DESCRIPTION
	     "Select the type of compression when you want this remote LAN
	      to use."
     DEFVAL { disabled }        
     ::= { rlanRemLANConfigEntry 5 }


rRemLANWanProtocol OBJECT-TYPE
     SYNTAX  INTEGER {
		 gandalfProprietary(1),
		 ppp(2)
	     }
     ACCESS  read-write
     STATUS  mandatory
     DESCRIPTION
	     "Select the communications protocol you want
	     the system to use when establishing a call to this remote LAN. The table
	     rlanGandalfProtoConfigTable contains additional information
	     when this object is set to gandalfProprietary(1) otherwise
	     the rlanPppConfigTable is to be used when this object is
	     set to ppp(2). 
	    NOTE: When you are changing or creating new remote LANs, rRemLANSerialNumber
                  or rRemLANPppSecret for the remote LAN must be present (depending on
                  the setting of the remote LAN) in the same SNMP message.
	     DEFAULT = gandalfProprietary"
     DEFVAL { gandalfProprietary }
     ::= { rlanRemLANConfigEntry 6 }


rRemLANIdleTimeout OBJECT-TYPE
     SYNTAX  INTEGER (0..86400)
     ACCESS  read-write
     STATUS  mandatory
     DESCRIPTION
	     "Enter how long (in seconds) the connection must be idle before the 
             system decides to disconnect the channel(s). If you enter a value of '0',
	     there is no idle time-out.
	     DEFAULT = 90"
     DEFVAL { 90 }
     ::= { rlanRemLANConfigEntry 7 }


rRemLANMaxChannels OBJECT-TYPE
     SYNTAX  INTEGER (1..2)
     ACCESS  read-write
     STATUS  mandatory
     DESCRIPTION
	     "Enter the  maximum number of channels to be connected to a 
	     remote LAN."
     DEFVAL { 1 }
     ::= { rlanRemLANConfigEntry 8 }


rRemLANFlooding OBJECT-TYPE
     SYNTAX  INTEGER {
		 filter(1),
		 to(2),
		 from(3),
		 bi-directional(4)
	     }
     ACCESS  read-write
     STATUS  mandatory
     DESCRIPTION
	     "Specify whether or not the system should allow flooding of unknown 
             destination unicast packets to the remote LAN or from this remote LAN
             to other remote LANs.
	     DEFAULT = to"
     DEFVAL { to }
     ::= { rlanRemLANConfigEntry 9 }


rRemLANMCastFwd OBJECT-TYPE
     SYNTAX  INTEGER {
		 filter(1),
		 to(2),
		 from(3),
		 bi-directional(4)
	     }
     ACCESS  read-write
     STATUS  mandatory
     DESCRIPTION
	     "Select the multicast packet treatment to be used for this remote 
	     LAN.
	     DEFAULT = bi-directional"
     DEFVAL { bi-directional }
     ::= { rlanRemLANConfigEntry 10 }


rRemLANBCastFwd OBJECT-TYPE
     SYNTAX  INTEGER {
		 filter(1),
		 to(2),
		 from(3),
		 bi-directional(4)
	      }
     ACCESS   read-write
     STATUS   mandatory
     DESCRIPTION
	     "Select the broadcast packet treatment to be used for this remote LAN.
	     DEFAULT = bi-directional"
     DEFVAL { bi-directional }
     ::= { rlanRemLANConfigEntry 11 }


rRemLANCallForce OBJECT-TYPE
     SYNTAX  INTEGER {
		  connect(1),
		  disconnect(2),
		  statusQuo(3)
	     }
     ACCESS  read-write
     STATUS  mandatory
     DESCRIPTION
	     "To tell the system to disconnect this remote LAN,
	     select disconnect from the list of available options.
	     When you select connect, the system will try to
	     connect to the remote LAN on an available channel as
	     specified in the rlanDestAddressConfigTable selection
	     parameters (i.e., channel group)
	     DEFAULT = statusQuo."
     DEFVAL { statusQuo }
     ::= { rlanRemLANConfigEntry 12 }


rRemLANWatchdogSpoofing OBJECT-TYPE
     SYNTAX  INTEGER {
		  disabled(1),
		  enabled(2)
	     }
     ACCESS  read-write
     STATUS  mandatory
     DESCRIPTION
	     "Select this option when you want the
	     system to respond to watchdog query packets received from 
	     the local LAN by this remote LAN.
	     DEFAULT = disabled"
     DEFVAL { disabled }
     ::= { rlanRemLANConfigEntry 13 }


rRemLANSAPandRIPSpoofingFiltering OBJECT-TYPE
     SYNTAX  INTEGER {
		  forward(1),
		  spoof(2),
		  filter(3)
	     }
     ACCESS  read-write
     STATUS  mandatory
     DESCRIPTION
	     "Select this option when you want the system to forward, 
              spoof or filter SAP/RIP requests to this remote LAN.
	     DEFAULT = disabled"
     DEFVAL { forward }
     ::= { rlanRemLANConfigEntry 14 }


rRemLANSAPGroups OBJECT-TYPE
     SYNTAX  OCTET STRING (SIZE(1..5))
     ACCESS  read-write
     STATUS  mandatory
     DESCRIPTION
	     "A list of indexes into the rlanSAPGroupTable. A single octet 
	     value of 1 indicates the 'All' SAP group (any 
	     other octets with values will generate a bad value error). 
	     Setting this object to an octet string length of zero deletes 
	     all previous values and returns this object to its default.
	     If rRemLANSAPandRIPSpoofingFiltering is disabled, this attribute
	     will return a zero length string (attempts to set this attribute
	     to any non-zero length string will generate a bad value error).
	     DEFAULT = 2H"
     DEFVAL { '2'H }
     ::= { rlanRemLANConfigEntry 15 }


rRemLANStatus OBJECT-TYPE
     SYNTAX  RowStatus
     ACCESS  read-write
     STATUS  mandatory
     DESCRIPTION
	     "Tells you the current status of this entry."
     ::= { rlanRemLANConfigEntry 16 }

rRemLANAroundCorner OBJECT-TYPE
     SYNTAX  INTEGER {
     		disabled(1),
     		enabled(2)
     }
     ACCESS   read-write
     STATUS   mandatory
     DESCRIPTION
	     "Select this option when you want this remote LAN
	      to receive data from another remote LAN."
     DEFVAL { disabled }
     ::= { rlanRemLANConfigEntry 17 }

rRemLANPPPNcpTypes OBJECT-TYPE
     SYNTAX  INTEGER {
         bcp(1),
         ipcp(2),
         bcpandipcp(3),
         ipxcp(4),
         bcpandipxcp(5),
         ipcpandipxcp(6),
         bcpandipcpandipxcp(7)
     }
     ACCESS   read-write
     STATUS   mandatory
     DESCRIPTION
	          "Select the NCP layer that the system should use 
         	  when communcating with this remote LAN
                   DEFAULT = BCP and IPCP"
     DEFVAL { bcpandipcp }
     ::= { rlanRemLANConfigEntry 18 }
 
rRemLANHuntGroup OBJECT-TYPE
     SYNTAX  INTEGER (1..16)
     ACCESS   read-write
     STATUS   mandatory
     DESCRIPTION
             "Indicates the huntgroup used by this remote LAN.
              1 indicates that no Hunt group is defined for this
              RemLAN."
     DEFVAL { 1 }
     ::= { rlanRemLANConfigEntry 19 }
 
rRemLANMdmAnswer OBJECT-TYPE
     SYNTAX  INTEGER {
                originate(1),
                answer(2)
     }
     ACCESS   read-write
     STATUS   mandatory
     DESCRIPTION
             "Select this option when you want this modem to 
              originate or answer."
     DEFVAL { originate }
     ::= { rlanRemLANConfigEntry 20 }

rRemLANEncryption OBJECT-TYPE
     SYNTAX  INTEGER {
                disabled(1),
                enabled(2)
     }
     ACCESS   read-write
     STATUS   mandatory
     DESCRIPTION
             "Select this option when you want to all data to be 
              encrypted/decrypted to/from this remote LAN."
     DEFVAL { disabled }
     ::= { rlanRemLANConfigEntry 21 }

rRemLANSNASpoofing OBJECT-TYPE
     SYNTAX  INTEGER {
                disabled(1),
                enabled(2)
     }
     ACCESS   read-write
     STATUS   mandatory
     DESCRIPTION
             "Select this option when you want the system to spoof SNA
              keepalive messages when all links to this remote LAN are
              down.  This feature is only available with the 'Point-of-
              Sale' version."
     DEFVAL { disabled }
     ::= { rlanRemLANConfigEntry 22 }

rRemLANDialBack OBJECT-TYPE
     SYNTAX  INTEGER {
                disabled(1),
                enabled(2)
     }
     ACCESS   read-write
     STATUS   mandatory
     DESCRIPTION
             "Select this option when you want the system to call right
              back this remote LAN as soon as it is identified and
              authenticated."
     DEFVAL { disabled }
     ::= { rlanRemLANConfigEntry 23 }

rRemLANTestPresence OBJECT-TYPE
     SYNTAX  DisplayString (SIZE(1..16))
     ACCESS  read-write
     STATUS  mandatory
     DESCRIPTION
	     "Use this option to trigger a test call to this remote LAN
        using the supplied phone number.  This will result in a trap,
        either gTestPresenceCallPassed, gTestPresenceCallFailed or
        gTestPresenceCallNotIssued, depending on the outcome of the call.
	     The phone number string can only contain digits and the letters
	     L (Local), N (National) and I (International) as a prefix
	     character. You cannot modify the default entry."
     ::= { rlanRemLANConfigEntry 24 }


rRemLANAllAtOnce OBJECT-TYPE
     SYNTAX  INTEGER {
                disabled(1),
                enabled(2)
     }
     ACCESS   read-write
     STATUS   mandatory
     DESCRIPTION
             "If enabled, once an outgoing call to this remote
	     LAN is required, Xpressway/XpressStack will attempt
	     to bring up the maximum number of channels configured
	     at the same time."
     DEFVAL { disabled }
     ::= { rlanRemLANConfigEntry 25 }

--
--
--     Gandalf Proprietary Point to Point
--

rlanGandalfProtoConfigTable OBJECT-TYPE
     SYNTAX  SEQUENCE OF RlanGandalfProtoConfigEntry
     ACCESS  not-accessible
     STATUS  mandatory
     DESCRIPTION
	     "This table contains objects that pertain to the management of
	     remote LANs that use the Gandalf proprietary link protocol."
     ::= { rlanRemLANGroup 4 }


rlanGandalfProtoConfigEntry OBJECT-TYPE
     SYNTAX  RlanGandalfProtoConfigEntry
     ACCESS  not-accessible
     STATUS  mandatory
     DESCRIPTION
	     "No default entry at conceptual row zero exists in this table.
	     In short a default rRemLANSerialNumber cannot be used when
	     learning a remote LAN since this parameter is one of the few
	     parameters that is actually learnt during this process."
     INDEX { rRemLANID }
     ::= { rlanGandalfProtoConfigTable 1 }


RlanGandalfProtoConfigEntry ::=
     SEQUENCE {
	 rRemLANSerialNumber   OCTET STRING
     }


rRemLANSerialNumber OBJECT-TYPE
     SYNTAX  OCTET STRING (SIZE(8))
     ACCESS  read-write
     STATUS  mandatory
     DESCRIPTION
	     "Enter the unique serial number of the remote LAN."
     ::= { rlanGandalfProtoConfigEntry 1 }
--


--
--     Remote LAN PPP configuration table
--

rlanPppConfigTable OBJECT-TYPE
     SYNTAX  SEQUENCE OF RlanPppConfigEntry
     ACCESS  not-accessible
     STATUS  mandatory
     DESCRIPTION
	     "This table contains objects that pertain to the management of
	     remote LANs that use the PPP Internet standard link protocol."
     ::= { rlanRemLANGroup 5 }


rlanPppConfigEntry OBJECT-TYPE
     SYNTAX  RlanPppConfigEntry
     ACCESS  not-accessible
     STATUS  mandatory
     DESCRIPTION
	     "A default entry at conceptual row zero does exist in this
	     table. The default entry can be used to specify the PPP
	     authentication protocol only."
     INDEX { rRemLANID }
     ::= { rlanPppConfigTable 1 }


RlanPppConfigEntry ::=
     SEQUENCE {
	 rRemLANPppAuth        INTEGER,
	 rRemLANPppSecret      OCTET STRING,
	 rRemLANPppNCP         INTEGER,	  
	 rRemLANRemIPAddrHandling        INTEGER,
	 rRemLANPPPRemIPAddr   IpAddress,
	 rRemLANPPPBapHandling INTEGER
     }


rRemLANPppAuth OBJECT-TYPE
     SYNTAX  INTEGER {
		 chap(1),
		 pap(2),
		 papSentOnIncoming(3),
                 terminalMode(4),
		 mschap(5)
	     }
     ACCESS  read-write
     STATUS  mandatory
     DESCRIPTION
	     "Select the authentication protocol 
	     the system should use when verifying
	     the identification of the remote LAN.
	     DEFAULT = pap"
     DEFVAL { pap }       
     ::= { rlanPppConfigEntry 1 }


rRemLANPppSecret OBJECT-TYPE
     SYNTAX  OCTET STRING (SIZE(1..8))
     ACCESS  read-write
     STATUS  mandatory
     DESCRIPTION
	     "Tells you the PPP secret for the remote LAN. The PPP identity
	     is the name you entered for the remote LAN (rRemLANName). You cannot
	     modify the default entry."
     ::= { rlanPppConfigEntry 2 }

rRemLANPppNCP OBJECT-TYPE
     SYNTAX  INTEGER {
		bcp(1),
		ipcp(2),
      		bcpandipcp(3),
	      	ipxcp(4),
      		bcpandipxcp(5),
      		ipcpandipxcp(6),
      		bcpandipcpandipxcp(7)
	       }
      ACCESS  read-write
      STATUS  mandatory
      DESCRIPTION
	 "Select the NCP layer that the system should use 
	  when communcating with this remote LAN
          DEFAULT = BCP and IPCP"
      DEFVAL { bcpandipcp }
      ::= { rlanPppConfigEntry 3 }

rRemLANRemIPAddrHandling OBJECT-TYPE
    SYNTAX  INTEGER {
                 accept(1),
                 override(2),
		 assign(3)
            }
    ACCESS  read-write
    STATUS  mandatory
    DESCRIPTION
           "This attribute determines wether the system can accept 
	   or override the DNS IP address submitted by 
	   a remote system. DEFAULT = accept."
    DEFVAL { accept }
    ::= { rlanPppConfigEntry 4 }

rRemLANPPPRemIPAddr OBJECT-TYPE
    SYNTAX  IpAddress
    ACCESS  read-write
    STATUS  mandatory
    DESCRIPTION
           "The IP address to assign to remote if rRemLANRemIPAddrHandling
	    is set to assign(3)"
    DEFVAL { accept }
    ::= { rlanPppConfigEntry 5 }


rRemLANPPPBapHandling OBJECT-TYPE
    SYNTAX  INTEGER {
                 none(1),
                 bacp(2),
		 mpplus(3),
		 bacpandmpplus(4)
            }
    ACCESS  read-write
    STATUS  mandatory
    DESCRIPTION
           "This attribute determines which BAP protocol is
	    used on a remote LAN PPP connection.
	    DEFAULT = bacp_and_mpplus."
    DEFVAL { bacpandmpplus }
    ::= { rlanPppConfigEntry 6 }
--


--
--     Destination Address Table
--

rlanDestAddressConfigTable OBJECT-TYPE
     SYNTAX  SEQUENCE OF RlanDestAddressConfigEntry
     ACCESS  not-accessible
     STATUS  mandatory
     DESCRIPTION
	     "This table contains objects that pertain to the management of remote LAN addressing information."
     ::= { rlanRemLANGroup 6 }


rlanDestAddressConfigEntry OBJECT-TYPE
     SYNTAX  RlanDestAddressConfigEntry
     ACCESS  not-accessible
     STATUS  mandatory
     DESCRIPTION
	     "For the default rRemLANID entry (conceptual row zero) two
	     defaults exist in this table."
     INDEX  { rRemLANID, rDestAddrId }
     ::= { rlanDestAddressConfigTable 1 }


RlanDestAddressConfigEntry ::=
     SEQUENCE {
	 rDestAddrId           INTEGER,
	 rDestPrefix           INTEGER,
	 rDestPhoneNum         DisplayString,
	 rDestChannelGroupId   INTEGER,
	 rDestLANCLID          DisplayString,
	 rDestLANMdmRequest    INTEGER
     }


rDestAddrId OBJECT-TYPE
     SYNTAX  INTEGER (1..2)
     ACCESS  read-only
     STATUS  mandatory
     DESCRIPTION
	     "Tells you the unique identifier for this entry."
     ::= { rlanDestAddressConfigEntry 1 }


rDestPrefix OBJECT-TYPE
     SYNTAX  INTEGER (1..33)
     ACCESS  read-write
     STATUS  mandatory
     DESCRIPTION
	     "Enter an index (1 to 33) into the rlanAddressPrefixConfigTable.
	     DEFAULT = 1"
     DEFVAL { 1 }        
     ::= { rlanDestAddressConfigEntry 2 }


rDestPhoneNum OBJECT-TYPE
     SYNTAX  DisplayString (SIZE(0..16))
     ACCESS  read-write
     STATUS  mandatory
     DESCRIPTION
	     "Enter the address of this remote LAN (e.g., a phone number). The
	     phone number string can only contain digits and the letters
	     L (Local), N (National) and I (International) as a prefix
	     character. You cannot modify the default entry."
     ::= { rlanDestAddressConfigEntry 3 }


rDestChannelGroupId OBJECT-TYPE
     SYNTAX  INTEGER (1..65)
     ACCESS  read-write
     STATUS  mandatory
     DESCRIPTION
	     "Enter an index (1 to 65) into the rlanChannelGroupTable.
	     The system uses the selected entry in this table to determine 
	     which group of channels to use when it attempts  to establish a 
	     call to a remote LAN.
	     DEFAULT = 1"
     DEFVAL { 1 }        
     ::= { rlanDestAddressConfigEntry 4 }


rDestLANCLID OBJECT-TYPE
     SYNTAX  DisplayString (SIZE(0..16))
     ACCESS  read-write
     STATUS  mandatory
     DESCRIPTION
	     "Enter the primary Calling Line IDentity number presented
	     during an incoming call from this Remote LAN. The CLID must
	     contain all 16 digits. You cannot modify the default entry."
     ::= { rlanDestAddressConfigEntry 5 }

rDestLANMdmRequest OBJECT-TYPE
     SYNTAX  INTEGER {
                disabled(1),
                enabled(2)
     }
     ACCESS   read-write
     STATUS   mandatory
     DESCRIPTION
             "Select this option when you want to use a modem for this
	      remote LAN."
     DEFVAL { disabled }
     ::= { rlanDestAddressConfigEntry 6 }
--


--
--       Destination Address Prefix Table
--
rAddrPrefixIdUnused OBJECT-TYPE
     SYNTAX  INTEGER (0..33)
     ACCESS  read-only
     STATUS  mandatory
     DESCRIPTION
	     "This object is used to identify a potentially unused index
	     that can be used as the rAddrPrefixId instance when
	     creating new entries in the rlanAddressPrefixConfigTable. A 
	     returned value of zero indicates that the table is full."
     ::= { rlanRemLANGroup 7 }


rlanAddressPrefixConfigTable OBJECT-TYPE
     SYNTAX  SEQUENCE OF RlanAddressPrefixConfigEntry
     ACCESS  not-accessible
     STATUS  mandatory
     DESCRIPTION
	     "This table contains objects that pertain to the 
	     management of destination address extension prefixes."
     ::= { rlanRemLANGroup 8 }


rlanAddressPrefixConfigEntry OBJECT-TYPE
     SYNTAX  RlanAddressPrefixConfigEntry
     ACCESS  not-accessible
     STATUS  mandatory
     DESCRIPTION
	     "The first entry (rAddrPrefixId value of one) corresponds 
	     to the default entry. This entry cannot be modified or 
	     deleted."
     INDEX { rAddrPrefixId }
     ::= { rlanAddressPrefixConfigTable 1 }


RlanAddressPrefixConfigEntry ::=
     SEQUENCE {
	 rAddrPrefixId        INTEGER,
	 rAddrPrefixName      DisplayString,
	 rAddrPrefixString    OCTET STRING,
	 rAddrPrefixStatus    RowStatus
     }


rAddrPrefixId OBJECT-TYPE
     SYNTAX  INTEGER (1..33)
     ACCESS  read-only
     STATUS  mandatory
     DESCRIPTION
	     "Tells you the prefix entry id."
     ::= { rlanAddressPrefixConfigEntry 1 }


rAddrPrefixName OBJECT-TYPE
     SYNTAX  DisplayString (SIZE(1..16))
     ACCESS  read-write
     STATUS  mandatory
     DESCRIPTION
	     "Enter the ASCII name that is associated with a prefix entry.
	     The name must be unique and is not case sensitive. You cannot
	     modify the default entry 'None'."
     ::= { rlanAddressPrefixConfigEntry 2 }


rAddrPrefixString OBJECT-TYPE
     SYNTAX  OCTET STRING (SIZE(0..40))
     ACCESS  read-write
     STATUS  mandatory
     DESCRIPTION
	     "Enter the prefix string that will precede the destination phone
	     number."
     ::= { rlanAddressPrefixConfigEntry 3 }


rAddrPrefixStatus OBJECT-TYPE
     SYNTAX  RowStatus
     ACCESS  read-write
     STATUS  mandatory
     DESCRIPTION
	     "The current status of this entry. Entries that are in use
	     (referenced by an entry in the rlanDestAddressConfigTable)
	     cannot be destroyed. The default entry cannot be destroyed."
     ::= { rlanAddressPrefixConfigEntry 4 }
--


--
--     Remote LAN Statistics Table
--

rlanRemLANStatsTable OBJECT-TYPE
     SYNTAX  SEQUENCE OF RlanRemLANStatsEntry
     ACCESS  not-accessible
     STATUS  mandatory
     DESCRIPTION
	     "This table provides a management view of the
	     system configuration specific to individual Remote 
	     Lans."
     ::= { rlanRemLANGroup 9 }


rlanRemLANStatsEntry OBJECT-TYPE
     SYNTAX  RlanRemLANStatsEntry
     ACCESS  not-accessible
     STATUS  mandatory
     INDEX { rRemLANID }
     ::= { rlanRemLANStatsTable 1 }


RlanRemLANStatsEntry ::=
     SEQUENCE {
	 rRemLANWANStatsIndex          OCTET STRING,
	 rRemLANLastBearer             INTEGER,
	 rRemLANLastFail               INTEGER,
	 rRemLANLastTime               TimeTicks,
	 rRemLANInCompressedBits       Counter,
	 rRemLANInUncompressedBits     Counter,
	 rRemLANInFrames               Counter,
	 rRemLANInUCastFwds            Counter,
	 rRemLANInUCastFilts           Counter,
	 rRemLANInMCastFwds            Counter,
	 rRemLANInMCastFilts           Counter,
	 rRemLANInBCastFwds            Counter,
	 rRemLANInBCastFilts           Counter,
	 rRemLANOutCompressedBits      Counter,
	 rRemLANOutUncompressedBits    Counter,
	 rRemLANOutFrames              Counter,
	 rRemLANOutUCastFwds           Counter,
	 rRemLANOutMCastFwds           Counter,
	 rRemLANOutBCastFwds           Counter,
	 rRemLANDiscTrans              Counter,
	 rRemLANResShorts              Counter,
	 rRemLANDuration               TimeTicks,
	 rRemLANRemoteIP               IpAddress,
	 rRemLANCompressionResetsRx    Counter,
	 rRemLANCompressionResetsTx    Counter,
	 rRemLANLocalDecompressionType INTEGER,
	 rRemLANLocalCompressionType   INTEGER,
	 rRemLANBcpStatus	       INTEGER,
	 rRemLANIpcpStatus	       INTEGER,
	 rRemLANIpxcpStatus	       INTEGER,
	 rRemLANBacpStatus	       INTEGER,
	 rRemLANMpplusStatus	       INTEGER,
	 rRemLANDynamic		       INTEGER,
	 rRemLANUserMustAuthenticate   INTEGER,
	 rRemLANLastConnected	       DisplayString
     }


rRemLANWANStatsIndex OBJECT-TYPE
     SYNTAX  OCTET STRING
     ACCESS  read-only
     STATUS  mandatory
     DESCRIPTION
	     "This string of octets is used to indicate active entries
	     in the rlanWANStatsTable entries where each octet represents
	     an index into this table. A null string length indicates that
	     this remote LAN is currently not active (up). If more than
	     one octet is returned then multi-linking is being performed."
     ::= { rlanRemLANStatsEntry 1 }


rRemLANLastBearer OBJECT-TYPE
     SYNTAX  INTEGER {
		  kbps64Unrestrict(1),
		  kbps56Dig(2),
		  audio3100Hz(3),
		  speech(4),
		  idle(5),
		  xsm(6)
	      }
     ACCESS   read-only
     STATUS   mandatory
     DESCRIPTION
	     "Tells you which bearer capability was used for the last call to 
	     this remote LAN. Connections to remote LANs that were made using
	     XSM channels are reported as xsm(6)."
     ::= { rlanRemLANStatsEntry 2 }


rRemLANLastFail OBJECT-TYPE
     SYNTAX  INTEGER
     ACCESS  read-only
     STATUS  mandatory
     DESCRIPTION
	     "Tells you the failure code for the last call."
     ::= { rlanRemLANStatsEntry 3 }


rRemLANLastTime OBJECT-TYPE
     SYNTAX  TimeTicks
     ACCESS  read-only
     STATUS  mandatory
     DESCRIPTION
	     "Tells you the number of TimeTicks that have
	     elapsed since the last connection to this remote LAN. This
	     value resets every time the remote LAN connects to the local
	     LAN. Returns a 0 if a connection has yet to be made." 
     ::= { rlanRemLANStatsEntry 4 }


rRemLANInCompressedBits OBJECT-TYPE
     SYNTAX  Counter
     ACCESS  read-only
     STATUS  mandatory
     DESCRIPTION
	     "Tells you how many compressed bits have been 
	     received from this remote LAN. The system uses this
	     information when calculating the inbound compression ratio."
     ::= { rlanRemLANStatsEntry 5 }


rRemLANInUncompressedBits OBJECT-TYPE
     SYNTAX  Counter
     ACCESS  read-only
     STATUS  mandatory
     DESCRIPTION
	     "Tells you how many  uncompressed bits have been
	     received from this remote LAN. The system uses this
	     Information when calculating the inbound compression ratio."
     ::= { rlanRemLANStatsEntry 6 }


rRemLANInFrames OBJECT-TYPE
     SYNTAX  Counter
     ACCESS  read-only
     STATUS  mandatory
     DESCRIPTION
	     "Tells you how many frames (both unicast and non-unicast)
	     have been received from this remote LAN
	     and forwarded to the local LAN."
     ::= { rlanRemLANStatsEntry 7 }


rRemLANInUCastFwds OBJECT-TYPE
     SYNTAX  Counter
     ACCESS  read-only
     STATUS  mandatory
     DESCRIPTION
	     "Tells you how many unicast frames have been received from 
	     this remote LAN and forwarded to the local LAN."
     ::= { rlanRemLANStatsEntry 8 }


rRemLANInUCastFilts OBJECT-TYPE
     SYNTAX  Counter
     ACCESS  read-only
     STATUS  mandatory
     DESCRIPTION
	     "Tells you how many  frames have been received from 
	     this remote LAN and filtered out."
     ::= { rlanRemLANStatsEntry 9 }


rRemLANInMCastFwds OBJECT-TYPE
     SYNTAX  Counter
     ACCESS  read-only
     STATUS  mandatory
     DESCRIPTION
	     "Tells you many multicast frames have been received from
	     this remote LAN and forwarded to the local LAN."
     ::= { rlanRemLANStatsEntry 10 }


rRemLANInMCastFilts OBJECT-TYPE
     SYNTAX  Counter
     ACCESS  read-only
     STATUS  mandatory
     DESCRIPTION
	     "Tells you how many multicast frames have been received from
	     the remote LAN and filtered out."
     ::= { rlanRemLANStatsEntry 11 }


rRemLANInBCastFwds OBJECT-TYPE
     SYNTAX  Counter
     ACCESS  read-only
     STATUS  mandatory
     DESCRIPTION
	     "Tells you how many broadcast frames have been received from
	     the remote LAN and forwarded to the local LAN."
     ::= { rlanRemLANStatsEntry 12 }


rRemLANInBCastFilts OBJECT-TYPE
     SYNTAX  Counter
     ACCESS  read-only
     STATUS  mandatory
     DESCRIPTION
	     "Tells you how many frames have been received from
	      the remote LAN  and filtered out."
     ::= { rlanRemLANStatsEntry 13 }


rRemLANOutCompressedBits OBJECT-TYPE
     SYNTAX  Counter
     ACCESS  read-only
     STATUS  mandatory
     DESCRIPTION
	     "Tells you how many compressed bits have been 
	     forwarded to the remote LAN. The system uses this 
	     information when calculating the outbound compression ratio."
     ::= { rlanRemLANStatsEntry 14 }


rRemLANOutUncompressedBits OBJECT-TYPE
     SYNTAX  Counter
     ACCESS  read-only
     STATUS  mandatory
     DESCRIPTION
	     "Tells you how many uncompressed bits have been
	     forwarded to the remote LAN. The system uses this 
	     information when calculating the outbound compression ratio."
     ::= { rlanRemLANStatsEntry 15 }


rRemLANOutFrames OBJECT-TYPE
     SYNTAX  Counter
     ACCESS  read-only
     STATUS  mandatory
     DESCRIPTION
	     "Tells you how many frames (both unicast and non-unicast)
	      have been forwarded to a WAN link
	     assigned to this remote LAN."
     ::= { rlanRemLANStatsEntry 16 }


rRemLANOutUCastFwds OBJECT-TYPE
     SYNTAX  Counter
     ACCESS  read-only
     STATUS  mandatory
     DESCRIPTION
	     "Tells you how many unicast frames have been forwarded to a 
	     WAN link assigned to this remote LAN."
     ::= { rlanRemLANStatsEntry 17 }


rRemLANOutMCastFwds OBJECT-TYPE
     SYNTAX  Counter
     ACCESS  read-only
     STATUS  mandatory
     DESCRIPTION
	     "Tells you how many multicast frames have been received from
	     the local LAN and forwarded to the WAN link 
	     assigned to this remote LAN."
     ::= { rlanRemLANStatsEntry 18 }


rRemLANOutBCastFwds OBJECT-TYPE
     SYNTAX  Counter
     ACCESS  read-only
     STATUS  mandatory
     DESCRIPTION
	     "Tells you how many broadcast frames received from
	     the local LAN have been forwarded to the remote LAN."
     ::= { rlanRemLANStatsEntry 19 }


rRemLANDiscTrans OBJECT-TYPE
     SYNTAX  Counter
     ACCESS  read-only
     STATUS  mandatory
     DESCRIPTION
	     "Tells you how many frames  were queued to be transmitted 
	     but then discarded because their transit delay exceeded the 
	     maximum limit."
     ::= { rlanRemLANStatsEntry 20 }


rRemLANResShorts OBJECT-TYPE
     SYNTAX  Counter
     ACCESS  read-only
     STATUS  mandatory
     DESCRIPTION
	     "Tells you how many frames  were queued to be transmitted 
	     but then discarded because of an internal resource shortage."
     ::= { rlanRemLANStatsEntry 21 }


rRemLANDuration OBJECT-TYPE
     SYNTAX  TimeTicks
     ACCESS  read-only
     STATUS  mandatory
     DESCRIPTION
	     "Tells you how long this remote LAN has been connected 
	     since the last system reset."
     ::= { rlanRemLANStatsEntry 22 }

rRemLANRemoteIP OBJECT-TYPE
     SYNTAX  IpAddress
     ACCESS  read-only
     STATUS  mandatory
     DESCRIPTION
	     "The IP Address of the remote LAN ."
     ::= { rlanRemLANStatsEntry 23 }

rRemLANCompressionResetsRx OBJECT-TYPE
     SYNTAX  Counter
     ACCESS  read-only
     STATUS  mandatory
     DESCRIPTION
             "Tells you how many compression resets we received from the 
             peer."
     ::= { rlanRemLANStatsEntry 24 }
 
rRemLANCompressionResetsTx OBJECT-TYPE
     SYNTAX  Counter
     ACCESS  read-only
     STATUS  mandatory
     DESCRIPTION
             "Tells you how many compression resets we sent to the peer."
     ::= { rlanRemLANStatsEntry 25 }

rRemLANLocalDecompressionType OBJECT-TYPE
     SYNTAX  INTEGER {
                  noCompression (1),
                  anyCompression(2),
                  slmlFZA(3),
                  slmlIPX(4),
                  slmlFZAP(5),
                  slmlFZAPEncrypt(6),
                  slmlEncrypt(7),
                  pppFZA(8),
                  pppFZAP(9),
                  pppFZAPEncrypt(10),
                  pppEncrypt(11),
                  pppStacNone(12),
                  pppStacLCB(13),
                  pppStacCRC(14),
                  pppStacSeq(15),
                  pppStacExt(16),
                  pppAscendLCB(17)
              }
     ACCESS   read-only
     STATUS   mandatory
     DESCRIPTION
             "Tells you which bearer capability was used for the last call to
             this remote LAN. Connections to remote LANs that were made using
             XSM channels are reported as xsm(6)."
     ::= { rlanRemLANStatsEntry 26 }
 
rRemLANLocalCompressionType OBJECT-TYPE
     SYNTAX  INTEGER {
                  noCompression (1),
                  anyCompression(2),
                  slmlFZA(3),
                  slmlIPX(4),
                  slmlFZAP(5),
                  slmlFZAPEncrypt(6),
                  slmlEncrypt(7),
                  pppFZA(8),
                  pppFZAP(9),
                  pppFZAPEncrypt(10),
                  pppEncrypt(11),
                  pppStacNone(12),
                  pppStacLCB(13),
                  pppStacCRC(14),
                  pppStacSeq(15),
                  pppStacExt(16),
                  pppAscendLCB(17)
              }
     ACCESS   read-only
     STATUS   mandatory
     DESCRIPTION
             "Tells you which bearer capability was used for the last call to
             this remote LAN. Connections to remote LANs that were made using
             XSM channels are reported as xsm(6)."
     ::= { rlanRemLANStatsEntry 27}
 
rRemLANBcpStatus OBJECT-TYPE
     SYNTAX  INTEGER {
		 active(1),
		 inactive(2)
	     }
     ACCESS  read-only
     STATUS  mandatory
     DESCRIPTION
	     "Tell you if the BCP Network Control Protocol
	      (NCP) is active for this remote LAN."
     ::= { rlanRemLANStatsEntry 28 }

rRemLANIpcpStatus OBJECT-TYPE
     SYNTAX  INTEGER {
		 active(1),
		 inactive(2)
	     }
     ACCESS  read-only
     STATUS  mandatory
     DESCRIPTION
	     "Tell you if the IPCP Network Control Protocol
	      (NCP) is active for this remote LAN."
     ::= { rlanRemLANStatsEntry 29 }

rRemLANIpxcpStatus OBJECT-TYPE
     SYNTAX  INTEGER {
		 active(1),
		 inactive(2)
	     }
     ACCESS  read-only
     STATUS  mandatory
     DESCRIPTION
	     "Tell you if the IPXCP Network Control Protocol
	      (NCP) is active for this remote LAN."
     ::= { rlanRemLANStatsEntry 30 }

rRemLANBacpStatus OBJECT-TYPE
     SYNTAX  INTEGER {
		 active(1),
		 inactive(2)
	     }
     ACCESS  read-only
     STATUS  mandatory
     DESCRIPTION
	     "Tell you if the PACP Protocol
	      is active for this remote LAN."
     ::= { rlanRemLANStatsEntry 31 }


rRemLANMpplusStatus OBJECT-TYPE
     SYNTAX  INTEGER {
		 active(1),
		 inactive(2)
	     }
     ACCESS  read-only
     STATUS  mandatory
     DESCRIPTION
	     "Tell you if the Mpplus Protocol
	      is active for this remote LAN."
     ::= { rlanRemLANStatsEntry 32 }

rRemLANDynamic OBJECT-TYPE
     SYNTAX  INTEGER {
		 true(1),
		 false(2)
	     }
     ACCESS  read-only
     STATUS  mandatory
     DESCRIPTION
	     "Tell you if this remote LAN has been
	      created dynamically"
     ::= { rlanRemLANStatsEntry 33 }

rRemLANUserMustAuthenticate OBJECT-TYPE
     SYNTAX  INTEGER {
		 true(1),
		 false(2)
	     }
     ACCESS  read-only
     STATUS  mandatory
     DESCRIPTION
	     "Tell you if this remote LAN must 
	      use authentication"
     ::= { rlanRemLANStatsEntry 34 }

rRemLANLastConnected OBJECT-TYPE
     SYNTAX  DisplayString (SIZE(1..80))
     ACCESS  read-only
     STATUS  mandatory
     DESCRIPTION
	     "ASCII String of the last time this remote 
	      has connected."
     ::= { rlanRemLANStatsEntry 35 }

-- End of rlanRemLANGroup
--


--
-- Definition of rlanLocLANGroup
-- No table defined. There is only one local LAN. Some of the stats
-- of the local LAN are defined in MIB-II.
--

rLocLANAdmst OBJECT-TYPE
     SYNTAX  INTEGER {
		 disabled(1),
		 enabled(2)
	     }
     ACCESS  read-write
     STATUS  mandatory
     DESCRIPTION
	     "Select the desired state of
	     the local LAN: disabled or enabled."
     ::= { rlanLocLANGroup 1 }


rLocLANConnector OBJECT-TYPE
     SYNTAX  INTEGER {
		 aui(1),
		 p2(2)
	     }
     ACCESS  read-write
     STATUS  mandatory
     DESCRIPTION
	     "Select the Ethernet interface for the local LAN depending
              on the Hardware platform: for the 10095 and 8441 boards the
              choices are AUI or P2. The 10444 boards cannot be changed.
	     NOTE: Changing the Ethernet interface may disconnect 
	     any active connections with the system  through the LAN port."
     ::= { rlanLocLANGroup 2 }


rLocLANMACAddress OBJECT-TYPE
     SYNTAX  PhysAddress
     ACCESS  read-only
     STATUS   mandatory
     DESCRIPTION
	     "Tells you the MAC address of the local LAN."
     ::= { rlanLocLANGroup 3 }


rLocLANOpState OBJECT-TYPE
     SYNTAX  INTEGER {
		 disabled(1),
		 enabled(2),
		 faulty(3)
	     }
     ACCESS  read-only
     STATUS  mandatory
     DESCRIPTION
	     "Tells you whether the local LAN is disabled, enabled, or faulty."
     ::= { rlanLocLANGroup 4 }


rLocLANRxFrames OBJECT-TYPE
     SYNTAX  Counter
     ACCESS  read-only
     STATUS  mandatory
     DESCRIPTION
	     "Tells you how many Ethernet frames have been received
	     from the local LAN since the last system reset."
     ::= { rlanLocLANGroup 5 }


rLocLANRxOctets OBJECT-TYPE
     SYNTAX  Counter
     ACCESS  read-only
     STATUS  mandatory
     DESCRIPTION
	     " Tells you how many octets have been received
	     from the local LAN since the last
	     system reset."
     ::= { rlanLocLANGroup 6 }


rLocLANRxAlignErrs OBJECT-TYPE
     SYNTAX  Counter
     ACCESS  read-only
     STATUS  mandatory
     DESCRIPTION
	     "Tells you how many frames from the local LAN
	     have been lost during reception due to alignment errors
	     since the last system reset."
     ::= { rlanLocLANGroup 7 }


rLocLANRxCRCErrs OBJECT-TYPE
     SYNTAX  Counter
     ACCESS  read-only
     STATUS  mandatory
     DESCRIPTION
	     " Tells you how many frames
	     from the local LAN were lost during reception
	     due to CRC errors since the last
	     system reset."
     ::= { rlanLocLANGroup 8 }

rLocLANRxMCasts OBJECT-TYPE
     SYNTAX  Counter
     ACCESS  read-only
     STATUS  mandatory
     DESCRIPTION
	     "Tells you how many multicast packets have 
	     been received from the local LAN since the last
	     system reset."
     ::= { rlanLocLANGroup 9 }


rLocLANRxBCasts OBJECT-TYPE
     SYNTAX  Counter
     ACCESS  read-only
     STATUS  mandatory
     DESCRIPTION
	     "Tells you how many broadcast packets have
	     been received from the local LAN since the last
	     system reset."
     ::= { rlanLocLANGroup 10 }


rLocLANTxFrames OBJECT-TYPE
     SYNTAX  Counter
     ACCESS  read-only
     STATUS  mandatory
     DESCRIPTION
	     "Tells you how many frames have been transmitted 
	     successfully to the local LAN since the last
	     system reset."
     ::= { rlanLocLANGroup 11 }


rLocLANTxOctets OBJECT-TYPE
     SYNTAX  Counter
     ACCESS  read-only
     STATUS  mandatory
     DESCRIPTION
	     "Tells you how many octets have been transmitted
	     successfully to the local LAN since the last
	     system reset."
     ::= { rlanLocLANGroup 12 }


rLocLANTxSingleColls OBJECT-TYPE
     SYNTAX  Counter
     ACCESS  read-only
     STATUS  mandatory
     DESCRIPTION
	     "Tells you how many frames have been lost due to single 
	     collisions since the last system reset."
     ::= { rlanLocLANGroup 13 }


rLocLANTxMultiColls OBJECT-TYPE
     SYNTAX  Counter
     ACCESS  read-only
     STATUS  mandatory
     DESCRIPTION
	     "Tells you how many frames from the local LAN
	     have been lost due to multiple 
	     collisions since the last system reset."
     ::= { rlanLocLANGroup 14 }


rLocLANTxErrs OBJECT-TYPE
     SYNTAX  Counter
     ACCESS  read-only
     STATUS  mandatory
     DESCRIPTION
	     "Tells you how many frames from the local LAN
	     have been lost during reception due to CRC errors
	     and alignment errors since the last system reset."
     ::= { rlanLocLANGroup 15 }


rLocLANLateColls OBJECT-TYPE
     SYNTAX  Counter
     ACCESS  read-only
     STATUS  mandatory
     DESCRIPTION
	     "Tells you how many frames from the local LAN
	     have been lost due to a late collision since the last
	     system reset."
     ::= { rlanLocLANGroup 16 }


rLocLANExcessColls OBJECT-TYPE
     SYNTAX  Counter
     ACCESS  read-only
     STATUS  mandatory
     DESCRIPTION
	     "Tells you how many frames this port has tried to 
	     transmit unsuccessfully since the last
	     system reset because it was not  
	     clear-to-send (CTS) or because the 82596 chip
	     locked and had to reset."
     ::= { rlanLocLANGroup 17 }


rLocLANTxMCasts OBJECT-TYPE
     SYNTAX  Counter
     ACCESS  read-only
     STATUS  mandatory
     DESCRIPTION
	     "Tells you how many multicast packets have been
	     transmitted to the local LAN since the last
	     system reset."
     ::= { rlanLocLANGroup 18 }


rLocLANTxBCasts OBJECT-TYPE
     SYNTAX  Counter
     ACCESS  read-only
     STATUS  mandatory
     DESCRIPTION
	     "Tells you how many broadcast packets have been
	     transmitted to the local LAN since the last
	     system reset."
     ::= { rlanLocLANGroup 19 }


rLocLANResShorts OBJECT-TYPE
     SYNTAX  Counter
     ACCESS  read-only
     STATUS  mandatory
     DESCRIPTION
	    "Tells you how many frames could not be
	     transmitted to the local LAN since the last 
	     system reset due to a lack of memory or other resources."
     ::= { rlanLocLANGroup 20 }

rLocLANCSErrs OBJECT-TYPE
     SYNTAX  Counter
     ACCESS  read-only
     STATUS  mandatory
     DESCRIPTION
	     "Tells you how many frames could not be
	     transmitted to the local LAN since the last 
	     system reset due to carrier sense errors."
     ::= { rlanLocLANGroup 21 }

rLocLANProtocolFilterForward OBJECT-TYPE
     SYNTAX  INTEGER {
	     forwardall(1),
	     forwardselected(2),
	     filterselected(3)
     }
     ACCESS  read-write
     STATUS  mandatory
     DESCRIPTION
	"Select this if you want LAN Protocol Filtering/forwarding."
     ::= { rlanLocLANGroup 22 }

rLocLANProtocolID OBJECT-TYPE
     SYNTAX  OCTET STRING (SIZE(1..5))
     ACCESS  read-write
     STATUS  mandatory
     DESCRIPTION
	     "A list of indexes into the rlanLANProtocolIDTable. Indexes
	     122-127 are predefined entries in the table:
                122 Novell IPX/SPX  8137
                123 AppleTalk ARP   80F3
                124 AppleTalk       809B
                125 Reverse ARP     8035
                126 ARP             0806
                127 TCP/IP          0800
             Indexes 1-121 are reserved for future predefined entry expansion.
	     Indexes 128 and up are user defined entries.
	     If rLocLANProtocolFilterForward is forwardall, this attribute
	     will return a zero length string (attempts to set this attribute
	     to any non-zero length string will generate a bad value error)."
     ::= { rlanLocLANGroup 23 }

rLocLANOperatingMode OBJECT-TYPE
     SYNTAX  INTEGER {
             eth100basetx(1),
             eth100baset(2),
             eth10basetx(3),
             eth10baset(4)
     }
     ACCESS  read-only
     STATUS  mandatory
     DESCRIPTION
             "Tells you the mode of operation that the RSC 9002 
              LAN controller has negociated. Only valid on the 9002 
              platform."
     ::= { rlanLocLANGroup 24 }

rLocLANEthMode OBJECT-TYPE
     SYNTAX  INTEGER {
             autonegotiate(1),
             eth100baseTxfdx(2),
             eth100baseTx(3),
             eth10baseTfdx(4),
             eth10baseT(5)
       }
     ACCESS  read-write
     STATUS  mandatory
     DESCRIPTION
	     "This attribute selects the operational mode of the Ethernet physical interfaces.
	      It is only applicable to systems that support 100 Meg Ethernet.  An error condition 
	      will be returned if 100 Meg Ethernet is not supported.
	       	      
	      1- autonegotiate: indicates that the interface will use the auto-negotiation feature 
	                        from the 802.3u standard to determine link speed. 
	      2- 100baseT_fdx:  forces the interface into 100baseTX full duplex mode.
	      3- 100baseT:      forces the interface into 100baseTX mode.
	      4- 10baseT_fdx:   forces the interface into 10baseT full duplex mode.
	      5- 10baseT:	      forces the interface into 10baseT mode.

DEFAULT = autonegotiate"
     DEFVAL { autonegotiate }                                  
     ::= { rlanLocLANGroup 25 }

 		   
-- End of rlanLocLANGroup
--



--
-- Definition of rlanLocLANFilterGroup
--

rLocLANFilterInFrames OBJECT-TYPE
     SYNTAX  Counter
     ACCESS  read-only
     STATUS  mandatory
     DESCRIPTION
	     "Tells you how many frames (both unicast and non-unicast)
	     have been received from the local LAN since the last
	     system reset."
     ::= { rlanLocLANFilterGroup 1 }


rLocLANFilterInUCasts OBJECT-TYPE
     SYNTAX  Counter
     ACCESS  read-only
     STATUS  mandatory
     DESCRIPTION
	     "Tells you how many valid unicast frames (filtered frames  
	     plus forwarded frames) have been received 
	     from the local LAN since the last
	     system reset."
     ::= { rlanLocLANFilterGroup 2 }


rLocLANFilterInUCastFwds OBJECT-TYPE
     SYNTAX  Counter
     ACCESS  read-only
     STATUS  mandatory
     DESCRIPTION
	     "Tells you how many valid unicast frames have been received 
	     from the local LAN and forwarded to the remote LAN
	     since the last system reset."
     ::= { rlanLocLANFilterGroup 3 }


rLocLANFilterInUCastFilts OBJECT-TYPE
     SYNTAX  Counter
     ACCESS  read-only
     STATUS  mandatory
     DESCRIPTION
	      "Tells you how many valid unicast frames have been received 
	      from the local LAN but filtered out since the last
	      system reset."
     ::= { rlanLocLANFilterGroup 4 }


rLocLANFilterInMCasts OBJECT-TYPE
     SYNTAX  Counter
     ACCESS  read-only
     STATUS  mandatory
     DESCRIPTION
	     "Tells you how many valid multicast frames (filtered
	     frames and forwarded frames) have been received 
	     from the local LAN since the last system reset."
     ::= { rlanLocLANFilterGroup 5 }


rLocLANFilterInMCastFwds OBJECT-TYPE
     SYNTAX  Counter
     ACCESS  read-only
     STATUS  mandatory
     DESCRIPTION
	     "Tells you how many valid multicast frames have been received 
	     from the local LAN and forwarded to the remote LAN
	     since the last system reset."

     ::= { rlanLocLANFilterGroup 6 }


rLocLANFilterInMCastFilts OBJECT-TYPE
     SYNTAX  Counter
     ACCESS  read-only
     STATUS  mandatory
     DESCRIPTION
	     "Tells you how many valid multicast frames have been received 
	     from the local LAN but filtered out since the last
	     system reset."
     ::= { rlanLocLANFilterGroup 7 }


rLocLANFilterInBCasts OBJECT-TYPE
     SYNTAX  Counter
     ACCESS  read-only
     STATUS  mandatory
     DESCRIPTION
	     "Tells you how many valid broadcast frames (filtered
	     frames and forwarded frames) have been received 
	     from the local LAN since the last system reset."
     ::= { rlanLocLANFilterGroup 8 }


rLocLANFilterInBCastFwds OBJECT-TYPE
     SYNTAX  Counter
     ACCESS  read-only
     STATUS  mandatory
     DESCRIPTION
	     "Tells you how many valid broadcast frames have been received 
	     from the local LAN and forwarded to the remote LAN
	     since the last system reset."
     ::= { rlanLocLANFilterGroup 9 }


rLocLANFilterInBCastFilts OBJECT-TYPE
     SYNTAX  Counter
     ACCESS  read-only
     STATUS  mandatory
     DESCRIPTION
	     "Tells you how many valid broadcast frames have been received 
	     from the local LAN and filtered out since the last system reset."
     ::= { rlanLocLANFilterGroup 10 }


rLocLANFilterDiscTrans OBJECT-TYPE
     SYNTAX  Counter
     ACCESS  read-only
     STATUS  mandatory
     DESCRIPTION
	     "Tells you how many frames have been queued to be 
	     transmitted but discarded because their transit delay 
	     exceeded the maximum since the last system reset."
     ::= { rlanLocLANFilterGroup 11 }


rLocLANFilterResShorts OBJECT-TYPE
     SYNTAX  Counter
     ACCESS  read-only
     STATUS  mandatory
     DESCRIPTION
	      "Tells you how many frames have been queued to be 
	     transmitted but discarded due to a shortage of
	     internal resource(s) since the last system reset."
     ::= { rlanLocLANFilterGroup 12 }

-- End of rlanLocLANFilterGroup


--


--
-- Definition of the rlanFilterCfgGroup
--


rFilterCfgLocAgingTime OBJECT-TYPE
     SYNTAX  INTEGER  (10..999999)
     ACCESS  read-write
     STATUS  mandatory
     DESCRIPTION
	     "Enter the length of time (in seconds) a station entry for a 
	     local LAN that has become inactive should remain in
	     the filter table."
     ::= { rlanFilterCfgGroup 1 }


rFilterCfgRemAgingTime OBJECT-TYPE
     SYNTAX  INTEGER (10..999999)
     ACCESS  read-write
     STATUS  mandatory
     DESCRIPTION
	     "Enter the length of time (in seconds) a station entry for a 
	     remote LAN that has become inactive should remain in
	     the filter table."
     ::= { rlanFilterCfgGroup 2 }


rFilterCfgAgingState OBJECT-TYPE
     SYNTAX  INTEGER{
		 disabled(1),
		 enabled(2)
	     }
     ACCESS  read-write
     STATUS  mandatory
     DESCRIPTION
	     "Choose to disable or enable dynamic aging of station entries 
              from the filter table."
     ::= { rlanFilterCfgGroup 3 }

rFilterCfgBlockRoam OBJECT-TYPE
     SYNTAX  INTEGER{
		 disabled(1),
		 enabled(2)
	     }
     ACCESS  read-write
     STATUS  mandatory
     DESCRIPTION
	     "Choose to disable or enable block roaming." 
     ::= { rlanFilterCfgGroup 4 }

-- End of rlanFilterCfgGroup
--


--
-- Definition of the rlanMACFilterGroup
--

rlanMACFilterTable OBJECT-TYPE
     SYNTAX  SEQUENCE OF RlanMACFilterEntry
     ACCESS  not-accessible
     STATUS  mandatory
     DESCRIPTION
	     "This table provides a management view of the
	     system configuration specific to individual MAC 
	     addresses.  The table is indexed using the physical 
	     address (MAC address)."
     ::= { rlanMACFilterGroup 1 }


rlanMACFilterEntry OBJECT-TYPE
     SYNTAX  RlanMACFilterEntry
     ACCESS  not-accessible
     STATUS  mandatory
     INDEX   {  rMACID }
     ::= { rlanMACFilterTable 1 }


RlanMACFilterEntry ::=
     SEQUENCE {
	 rMACID          PhysAddress,
	 rMACType        INTEGER,
	 rMACHomePort    INTEGER
     }


rMACID OBJECT-TYPE
     SYNTAX  PhysAddress
     ACCESS  read-only
     STATUS  mandatory
     DESCRIPTION
	     "Tells you the MAC address of one entry in the filter table."
    ::= { rlanMACFilterEntry 1 }


rMACType OBJECT-TYPE
     SYNTAX  INTEGER {
		 dynamic(1),
		 static(2),
		 blocked(3),
		 invalid(254)
	     }
     ACCESS  read-write
     STATUS  mandatory
     DESCRIPTION
	     "Enter the MAC address type, which can be one of the following:

		1- dynamic - the MAC address was learned and is subject to
	 		     age out if aging is enabled.
		2- static  - the MAC address was manually entered in the
			     system through the console or SNMP
		3- blocked - the system will filter this MAC address.
		4- invalid - used to delete MAC filter entries.

	     NOTE: You can create or set a MAC address with a dynamic type.
	     That MAC address will simply be subject to aging as soon as it's
	     created or modified."
     ::= { rlanMACFilterEntry 2 }


rMACHomePort OBJECT-TYPE
     SYNTAX  INTEGER (0..1000)
     ACCESS  read-write
     STATUS  mandatory
     DESCRIPTION
	     "Enter the id for the remote LAN associated with this MAC address.

		1) A rMACHomePort with a value of 0 means that the MAC 
		   address resides on the local LAN.

		2) A rMACHomePort with a value from 1 to 1000 will map to 
		   the rRemLANID attribute of 1 to 1000.

	     This attribute cannot be SET alone. A GEN_ERROR will be
	     returned. If you want to change the home port on which the
	     MAC resides, you have to delete by setting rMACType to
	     INVALID and then recreate the entry by having all the attributes
	     in the same SET-REQUEST packet with valid values.

	     NOTE: If you want to create a new MAC
	     entry, you have to make sure that the rMACHomePort 
	     attribute that you use has already been created and is, therefore, 
	     known by the system."
     ::= { rlanMACFilterEntry 3 }

-- End of rlanMACFilterGroup
--


--
-- TCPIP Group Definition
--

--  { rlanTCPIPGroup 1 } has been obsoleted


rTCPIPAddress OBJECT-TYPE
     SYNTAX  IpAddress
     ACCESS  read-write
     STATUS  mandatory
     DESCRIPTION
	     "Enter the IP address of your system."
      ::= { rlanTCPIPGroup 2 }


rTCPIPSubMask OBJECT-TYPE
     SYNTAX  IpAddress
     ACCESS  read-write
     STATUS  mandatory
     DESCRIPTION
	     "Enter the subnet mask."
      ::= { rlanTCPIPGroup 3 }


rTCPIPDefGw OBJECT-TYPE
     SYNTAX  IpAddress
     ACCESS  read-write
     STATUS  mandatory
     DESCRIPTION
	     "Enter the IP address of the default gateway."
      ::= { rlanTCPIPGroup 4 }
      
--


--
--     Telnet console access group definition
--

rlanTelnetGroup                     OBJECT IDENTIFIER ::= { rlanTCPIPGroup 5 }


rTelnetAccess OBJECT-TYPE
     SYNTAX  INTEGER { 
		 disabled(1),
		 enabled(2)
	     }
     ACCESS  read-write
     STATUS  mandatory
     DESCRIPTION
	     "Choose to disable or enable the acceptance of an incoming TELNET 
	     connection."
      ::= { rlanTelnetGroup 1 }


rTelnetIpAddr OBJECT-TYPE
     SYNTAX  IpAddress
     ACCESS  read-write
     STATUS  mandatory
     DESCRIPTION
	     "Enter  the IP address of an acceptable host for a TELNET connection."
      ::= { rlanTelnetGroup 2 }


rTelnetIpSubMask OBJECT-TYPE
     SYNTAX  IpAddress
     ACCESS  read-write
     STATUS  mandatory
     DESCRIPTION
	     "Enter the mask to be used when an incoming Telnet request
	     is being processed. The source IP address is masked
	     with this attribute and compared to the rTelnetIpAddr attribute
	     for access privileges."
      ::= { rlanTelnetGroup 3 }

--


--
--       File Transfer Client Configuration Table
--

rFtpByteCount OBJECT-TYPE
     SYNTAX  Gauge
     ACCESS  read-only
     STATUS  mandatory
     DESCRIPTION
	     "Tells you how many bytes have been transferred
	     during a file transfer that is in process. If no file
	     transfer is in process,  the field will display a value
	     zero (0)."
      ::= { rlanTCPIPGroup 6 }
 
rFtpInProgress OBJECT-TYPE
     SYNTAX  INTEGER {
                 fxFinished(1),
                 fxInProgress(2)
             }
     ACCESS  read-only
     STATUS  mandatory
     DESCRIPTION
             "Tells you if a file transfer is progress."
      ::= { rlanTCPIPGroup 7 }

rFtpLastResultCode OBJECT-TYPE
     SYNTAX  INTEGER {
                 successful(1),
                 aborted(2),
                 invalidId(3),
                 invalidPwd(4),
                 invalidFile(5),
                 invalidCRC(6),
                 invalidVersion(7),
                 noResponseByHost(8),
                 fileAccessError(9),
                 noFlashAvail(10),
                 badFlash(11),
                 flashInUse(12),
                 fxInProgress(13)
             }
     ACCESS  read-only
     STATUS  mandatory
     DESCRIPTION
             "Tells you the Last Result Code for the last file transfer that took place."
      ::= { rlanTCPIPGroup 8 }
 
rFtpConfigTable OBJECT-TYPE
     SYNTAX  SEQUENCE OF RFtpConfigEntry
     ACCESS  not-accessible
     STATUS  mandatory
     DESCRIPTION
	     "These objects manage the system's embedded ftp client and can
	     be used to initiate file transfers to or from a specified ftp
	     server."
     ::= { rlanTCPIPGroup 9 }
 
rFtpConfigEntry OBJECT-TYPE
     SYNTAX  RFtpConfigEntry
     ACCESS  not-accessible
     STATUS  mandatory
     INDEX   {  rFtpFileId }
     ::= { rFtpConfigTable 1 }
 
 
RFtpConfigEntry ::=
     SEQUENCE {
	 rFtpFileId          INTEGER,
	 rFtpServerIpAddr    IpAddress,
	 rFtpClientId        DisplayString,
	 rFtpClientPasswd    DisplayString,
	 rFtpFilePath        DisplayString,
	 rFtpFileName        DisplayString,
	 rFtpOperation       INTEGER
     }
 
 
rFtpFileId OBJECT-TYPE
     SYNTAX  INTEGER {
		 code(1),
		 database(2),
		 auditRecords(3)
	     }
     ACCESS  read-only
     STATUS  mandatory
     DESCRIPTION
	     "Tells you the file ID for this entry, which can be
	      code, database or auditRecords."
    ::= { rFtpConfigEntry 1 }
 
 
rFtpServerIpAddr OBJECT-TYPE
     SYNTAX  IpAddress
     ACCESS  read-write
     STATUS  mandatory
     DESCRIPTION
	     "Enter the IP address of the FTP server."
    ::= { rFtpConfigEntry 2 }
 
 
rFtpClientId OBJECT-TYPE
     SYNTAX  DisplayString (SIZE(1..16))
     ACCESS  read-write
     STATUS  mandatory
     DESCRIPTION
	     "Enter the user ID to be used when the system identifies its embedded
	     FTP client to the FTP server. You must enter this information when 
	     you issue a set for code(1) or database(2) file transfers."
    ::= { rFtpConfigEntry 3 }
 
 
rFtpClientPasswd OBJECT-TYPE
     SYNTAX  DisplayString (SIZE(0..16))
     ACCESS  read-write
     STATUS  mandatory
     DESCRIPTION
	     "Enter the user password to be used when the sytem identifies its 
	     embedded FTP client to the FTP server. You must enter this information when 
	     you issue a set for code(1) or database(2) file transfers."
    ::= { rFtpConfigEntry 4 }
 
 
rFtpFilePath OBJECT-TYPE
     SYNTAX  DisplayString (SIZE(1..80))
     ACCESS  read-write
     STATUS  mandatory
     DESCRIPTION
	     "Enter the directory path on the FTP server that the file is to be
	     copied to/from."
    ::= { rFtpConfigEntry 5 }
 
 
rFtpFileName OBJECT-TYPE
     SYNTAX  DisplayString (SIZE(1..20))
     ACCESS  read-write
     STATUS  mandatory
     DESCRIPTION
	     "Enter the filename to be used when the file is 
	     saved on the FTP server."
    ::= { rFtpConfigEntry 6 }
 
 
rFtpOperation OBJECT-TYPE
     SYNTAX  INTEGER {
		 get(1),
		 put(2),
		 setup(3)
	     }
     ACCESS  read-write
     STATUS  mandatory
     DESCRIPTION
	     "Select the operation the RSC should perform: get, put, or setup. The 
	     get(1) operation is allowed on code and database records. The 
	     put(2) operation is allowed on database files and audit records. 
	     The setup(3) operation is allowed on all records, which commits
	     the parameters to non-volatile storage. Setting this object 
	     to either get(1) or put(2) initiates a file transfer that
	     will be trapped on completion. The get and put operations also 
	     perform an implied commit to non-volatile storage.
	     DEFAULT = setup"
    DEFVAL { setup }
    ::= { rFtpConfigEntry 7 }

rTCPIPDynamicIP OBJECT-TYPE
     SYNTAX  IpAddress
     ACCESS  read-write
     STATUS  obsolete
     DESCRIPTION
	     "Enter the start IP address of the dynamic IP pool."
      ::= { rlanTCPIPGroup 10 }
      
rTCPIPNumDynIp OBJECT-TYPE
     SYNTAX  INTEGER (0..150)
     ACCESS  read-write
     STATUS  obsolete
     DESCRIPTION
	     "Enter the number of dynamic IPs in the pool."
      ::= { rlanTCPIPGroup 11 }


      
-- End of TCPIP group
--


--
-- Definition of the rlanBlacklistGroup
--


rlanBlacklistTable OBJECT-TYPE
     SYNTAX  SEQUENCE OF RlanBlacklistEntry
     ACCESS  not-accessible
     STATUS  mandatory
     DESCRIPTION
	     "This table provides a management view of the
	     system configuration specific to individual 
	     blacklisted phone numbers."
     ::= { rlanBlacklistGroup 1 }


rlanBlacklistEntry OBJECT-TYPE
     SYNTAX  RlanBlacklistEntry
     ACCESS  not-accessible
     STATUS  mandatory
     INDEX   {  rBlacklistID }
     ::= { rlanBlacklistTable 1 }


RlanBlacklistEntry ::=
     SEQUENCE {
	 rBlacklistID          INTEGER,
	 rBlacklistCLID        DisplayString,
	 rBlacklistStatus      RowStatus
     }


rBlacklistID OBJECT-TYPE
     SYNTAX  INTEGER (1..64)
     ACCESS  read-only
     STATUS  mandatory
     DESCRIPTION
	     "Tells you the ID of any of the possible 64
	     blacklisted entries."
     ::= { rlanBlacklistEntry 1 }


rBlacklistCLID OBJECT-TYPE
     SYNTAX  DisplayString (SIZE(1..16))
     ACCESS  read-write
     STATUS  mandatory
     DESCRIPTION
	     "Tells you the blacklisted phone number."
     ::= { rlanBlacklistEntry 2 }


rBlacklistStatus OBJECT-TYPE
     SYNTAX  RowStatus
     ACCESS  read-write
     STATUS  mandatory
     DESCRIPTION
	     "Tells you the current status of this blacklisted entry."
     ::= { rlanBlacklistEntry 3 }

 
rBlacklistIDUnused OBJECT-TYPE
     SYNTAX  INTEGER (0..64)
     ACCESS  read-only
     STATUS  mandatory
     DESCRIPTION
	     "Identifies a potentially unused index
	     that can be used as the rBlacklistID instance when you're creating 
	     new entries in the rlanBlacklistTable. A returned value of 
	     zero indicates that the table is full."
     ::= { rlanBlacklistGroup 2 }

-- END of the rBlacklistGroup
--


--
-- Definition of the rlanProtocolGroup
--


rlanProtocolTable OBJECT-TYPE
     SYNTAX  SEQUENCE OF RlanProtocolEntry
     ACCESS  not-accessible
     STATUS  mandatory
     DESCRIPTION
	     "This table provides a management view of the
	     system configuration specific to network addresses.
	     The table is indexed using the network IP address."
     ::= { rlanProtocolGroup 1 }


rlanProtocolEntry OBJECT-TYPE
     SYNTAX  RlanProtocolEntry
     ACCESS  not-accessible
     STATUS  mandatory
     DESCRIPTION
	     "Once an entry has been created it cannot be modified.
	     It must be deleted first."
     INDEX   { rProtocolID }
     ::= { rlanProtocolTable 1 }


RlanProtocolEntry ::=
     SEQUENCE {
	 rProtocolID       NetworkAddress,
	 rProtocolMask     NetworkAddress,
	 rProtocolRemLANID INTEGER,
	 rProtocolType     INTEGER,
	 rProtocolStatus   RowStatus
     }


rProtocolID OBJECT-TYPE
     SYNTAX  NetworkAddress
     ACCESS  read-only
     STATUS  mandatory
     DESCRIPTION
	     "Tells you the network address of one entry in the protocol 
	     table. It represents a unique device attached to 
	     the associated home port."
     ::= { rlanProtocolEntry 1 }


rProtocolMask OBJECT-TYPE
     SYNTAX  NetworkAddress
     ACCESS  read-write
     STATUS  mandatory
     DESCRIPTION
	     "Tells you the network mask associated with this unique 
	     entry."
     ::= { rlanProtocolEntry 2 }


rProtocolRemLANID OBJECT-TYPE
     SYNTAX  INTEGER (1..1000)
     ACCESS  read-write
     STATUS  mandatory
     DESCRIPTION
	     "Tells you the ID of the remote LAN associated with this
	     network address. The value maps one- to-one to the value
	     for the attribute rRemLANID."
     ::= { rlanProtocolEntry 3 }

rProtocolType OBJECT-TYPE
     SYNTAX  INTEGER {
		 ip(1)
	     }
     ACCESS  read-write
     STATUS  mandatory
     DESCRIPTION
	     "Enter the network-address type associated with this 
	     unique entry.
	     DEFAULT = ip"
     DEFVAL  { ip }
     ::= { rlanProtocolEntry 4 }


rProtocolStatus OBJECT-TYPE
     SYNTAX  RowStatus
     ACCESS  read-write
     STATUS  mandatory
     DESCRIPTION
	     "Tells you the current status of this protocol entry."
     ::= { rlanProtocolEntry 5 }
-- END of rProtocolGroup
--


--
-- Definition of rlanPortGroup
--

rlanPriPortTable OBJECT-TYPE
     SYNTAX  SEQUENCE OF RlanPriPortEntry
     ACCESS  not-accessible
     STATUS  mandatory
     DESCRIPTION
	     "This table provides a management view of the  
	     system configuration specific to individual PRI 
	     Ports."
     ::= { rlanPriPortGroup 1 }


rlanPriPortEntry OBJECT-TYPE
     SYNTAX  RlanPriPortEntry
     ACCESS  not-accessible
     STATUS  mandatory
     INDEX   { rPortCardID, rPortPortID }
     ::= { rlanPriPortTable 1 }


RlanPriPortEntry ::=
     SEQUENCE {
	 rPortCardID              INTEGER,
	 rPortPortID              INTEGER,
	 rPortCardType            INTEGER,
	 rPortLineFormat          INTEGER,
	 rPortPRISwitch           INTEGER,
	 rPortDChanFormat         INTEGER,
	 rPortDChanTimeslot       INTEGER,
	 rPortYellowAlarm         INTEGER,
	 rPortAISAlarm            INTEGER,
	 rPortRedAlarm            INTEGER,
	 rPortPhoneNumber         DisplayString,
	 rPortAdmst               INTEGER,
	 rPortDLinkNum            INTEGER,
	 rPortIfId                INTEGER,
         rPortDOSBS               INTEGER,
	 rPortHuntGroup           INTEGER,
	 rPortHoldoff             INTEGER,
	 rPortNetsync		  INTEGER,
	 rPortPBXType		  INTEGER
     }


rPortCardID OBJECT-TYPE
     SYNTAX  INTEGER (1..10)
     ACCESS  read-only
     STATUS  mandatory
     DESCRIPTION
	     "Tells you the position of this card within the hub with respect to 
	     the P2 backplane.  Each PRI card can take slot position 1 to 10."
     ::= { rlanPriPortEntry 1 }


rPortPortID OBJECT-TYPE
     SYNTAX  INTEGER (1..2)
     ACCESS  read-only
     STATUS  mandatory
     DESCRIPTION
	     "Tells you the port ID for a specific interface."
     ::= { rlanPriPortEntry 2 }


rPortCardType OBJECT-TYPE
     SYNTAX  INTEGER {
		 pri9360DB15 (180),
		 pri9346DB15 (184),
		 pri9346eDB15(188),
		 pri9330BNC(192),
		 pri9330DB15(196),
		 pri9323DB15(200),
		 pri9360eDB15(204)
	     }
     ACCESS  read-only
     STATUS  mandatory
     DESCRIPTION
	    "Tells you the card type to which this port belongs, 
	    which can be one of pri9360DB15, pri9346DB15, pri9330BNC,
	    pri9330DB15, pri9323DB15."
     ::= { rlanPriPortEntry 3 }


rPortLineFormat OBJECT-TYPE
     SYNTAX  INTEGER {
		 naDS1ESF(1),
		 naDS1D4(2),
		 euroCEPT(3),
		 euroCEPTCRC4(4),
		 naDS1D4B8ZS(5)
	     }
     ACCESS  read-write
     STATUS  mandatory
     DESCRIPTION
	     "Select the line format to be used by a PRI port,
              which can be one of naDS1ESF, naDS1D4, naDS1D4B8ZS, euroCEPT, 
	      euroCEPTCRC4. 
	     The first three are North American; the last two are European."
     ::= { rlanPriPortEntry 4 }


rPortPRISwitch OBJECT-TYPE
     SYNTAX  INTEGER {
		 att4ESS(1),
		 att5ESS(2),
		 ntDMS100(3),
		 ntDMS250(4),
		 leased(5),
		 dass2 (6),
		 dass15 (7),
		 euroisdn(8),
		 austel(9),
		 euroisdn-no-restarts(10),
		 euroisdn-numeris(11),
		 ins64(12),
                 passThrough(13),
                 robbedBit(14),
                 ni2(15),
                 ni2LowLow(16),
		 dpnss-a(17),
		 dpnss-b(18),
		 other1(249),
		 other2(250),
		 other3(251),
		 other4(252),
		 other5(253),
		 other6(254)
	      }
     ACCESS   read-write
     STATUS   mandatory
     DESCRIPTION
	     "Select the switch type to
	     which this PRI port connects, which can be one of att4ESS,
	     att5ESS, ntDMS100, ntDMS250, leased, dass2, dass15, euroisdn,
	     kdd. NOTE: The dass15 switch type is valid only if the timeslot
	     is less than 16; any B channels above timeslot 16 will be invalid."
     ::= { rlanPriPortEntry 5 }


rPortDChanFormat OBJECT-TYPE
     SYNTAX  INTEGER {
		 kbps64(1),
		 kbps64Inverted(2),
		 kbps56(3)
	      }
     ACCESS   read-write
     STATUS   mandatory
     DESCRIPTION
	     "Select the format of the D Channel
	     to be used by this port, which can be one of 64 Kbps, 64 Kbps
	     inverted or 56 Kbps. European standards allow only 64kbps inverted.
	     NOTE: This attribute is applicable only if the port is not leased. 
	     If the port is leased, a get or set will generate 
	      a noSuchName error. The system will skip this port
	     if the previous attribute has initiated a get-next."
     ::= { rlanPriPortEntry 6 }


rPortDChanTimeslot OBJECT-TYPE
     SYNTAX  INTEGER (1..31)
     ACCESS  read-write
     STATUS  mandatory
     DESCRIPTION
	     "Enter the timeslot to be used by the D channel.
	     Valid timeslots for the various switch types are:
		 North American:  1..24
		 European:        1..31
		 DASS2-15:        1..16
	     NOTE: This attribute is applicable only if the port is not leased. 
	     If the port is leased, a get or set will generate 
	      a noSuchName error. The system will skip this port
	     if the previous attribute has initiated a get-next."
     ::= { rlanPriPortEntry 7 }


rPortYellowAlarm  OBJECT-TYPE
     SYNTAX   INTEGER {
		  off(1),
		  on(2)
	      }
     ACCESS   read-only
     STATUS   mandatory
     DESCRIPTION
	     "Tells you if the YELLOW alarm is off 
	     or on. If it's on,  the network 
	     cannot synchronize itself with the data transmitted 
	     by the PRI port."
     ::= { rlanPriPortEntry 8 }


rPortAISAlarm OBJECT-TYPE
     SYNTAX  INTEGER {
		 off(1),
		 on(2)
	     }
     ACCESS  read-only
     STATUS  mandatory
     DESCRIPTION
	     "Tells you if the AIS alarm is off or on. 
              If it's on,  the network cannot accept calls."
     ::= { rlanPriPortEntry 9 }


rPortRedAlarm OBJECT-TYPE
     SYNTAX  INTEGER {
		 off(1),
		 on(2)
	     }
     ACCESS  read-only
     STATUS  mandatory
     DESCRIPTION
	     "Tells you if the RED alarm is off or on. If it's on, 
              the PRI port has failed to synchronize with the received data."
     ::= { rlanPriPortEntry 10 }


rPortPhoneNumber OBJECT-TYPE
     SYNTAX  DisplayString (SIZE(0..16))
     ACCESS  read-write
     STATUS  mandatory
     DESCRIPTION
	     "Tells you the phone number that this port answers for.
	     NOTE: This attribute is applicable only if the port is not leased. 
	     If the port is leased, a get or set will generate 
	      a noSuchName error. The system will skip this port
	     if the previous attribute has initiated a get-next."
     ::= { rlanPriPortEntry 11 }


rPortAdmst OBJECT-TYPE
     SYNTAX  INTEGER {
	       disabled(1),
	       enabled(2)
	     }
     ACCESS  read-write
     STATUS  mandatory
     DESCRIPTION
	     "Select this option to enable a port.
	     If a port is disabled, current calls won't be torn down,
	     but the port will not accept or originate
	     subsequent calls.  If the port is enabled, it will both 
	     accept and originate calls.
	     DEFAULT = enabled"
      DEFVAL  { enabled }
     ::= { rlanPriPortEntry 12 }

rPortDLinkNum OBJECT-TYPE
     SYNTAX  INTEGER (1..2)
     ACCESS  read-write
     STATUS  mandatory
     DESCRIPTION
             "Indicates which port this D channel resides on."
     ::= { rlanPriPortEntry 13 }

rPortIfId OBJECT-TYPE
     SYNTAX  INTEGER (0..31)
     ACCESS  read-write
     STATUS  mandatory
     DESCRIPTION
             "The identifier of the interface of interest."
     ::= { rlanPriPortEntry 14 }

rPortDOSBS OBJECT-TYPE
     SYNTAX  INTEGER {
               disabled(1),
               enabled(2)
             }
     ACCESS  read-write
     STATUS  mandatory
     DESCRIPTION
             "Select this option to enable digital over speech bearer."
      DEFVAL  { disabled }
     ::= { rlanPriPortEntry 15 }

rPortHuntGroup OBJECT-TYPE
     SYNTAX  INTEGER ( 1..16 )
     ACCESS  read-write
     STATUS  mandatory
     DESCRIPTION
             "Indicates the huntgroup used by this remote LAN.
              1 indicates that no Hunt group is defined for this
              port."
     DEFVAL { 1 }
     ::= { rlanPriPortEntry 16 }

rPortHoldOff OBJECT-TYPE
     SYNTAX  INTEGER (0..30)
     ACCESS  read-write
     STATUS  mandatory
     DESCRIPTION
             "Enter the time (in seconds) between a leased line failure
              and the time before a reconnection is tried.
             DEFAULT = 10"
     DEFVAL { 10 }
     ::= { rlanPriPortEntry 17 }

rPortNetsync OBJECT-TYPE
     SYNTAX  INTEGER {
	       primary(1),
	       secondary(2),
	       none(3)
	     }
     ACCESS  read-write
     STATUS  mandatory
     DESCRIPTION
             "Select whether to source the system clock from this network
              connection."
     ::= { rlanPriPortEntry 18 }

rPortPBXType OBJECT-TYPE
     SYNTAX  INTEGER {
	       other(1),
	       mitelSx2000(2),
	       gptIsdx(3)
	     }
     ACCESS  read-write
     STATUS  mandatory
     DESCRIPTION
             "Select the type of PBX attached to the port."
     ::= { rlanPriPortEntry 19 }



rPortIsdnRoutingTable OBJECT-TYPE
     SYNTAX  SEQUENCE OF RlanPortIsdnRoutingEntry
     ACCESS  not-accessible
     STATUS  mandatory
     DESCRIPTION
	     "This table provides a management view of the  
	     call routing table specific to a PRI port connected to
	     an ISDN network."
     ::= { rlanPriPortGroup 2 }

rPortIsdnRoutingEntry OBJECT-TYPE
     SYNTAX  RlanPortIsdnRoutingEntry
     ACCESS  not-accessible
     STATUS  mandatory
     ::= { rPortIsdnRoutingTable 1 }

RlanPortIsdnRoutingEntry ::=
     SEQUENCE {
	 rPortIsdnRouting         INTEGER 
     }

rPortIsdnRouting OBJECT-TYPE
     SYNTAX  INTEGER (0..4)
     ACCESS  read-write
     STATUS  mandatory
     DESCRIPTION
             "Enter the index number of the rIsdnDDIRoutingTable associated
	     with this port. Selecting none (0) forces the call type to be 
	     determined in-band.
	     DEFAULT = 0"
     DEFVAL { 0 }
     ::= { rPortIsdnRoutingEntry 1 }



rPortPBXRoutingTable OBJECT-TYPE
     SYNTAX  SEQUENCE OF RlanPortPBXRoutingEntry
     ACCESS  not-accessible
     STATUS  mandatory
     DESCRIPTION
	     "This table provides a management view of the  
	     call routing table specific to a PRI port connected to
	     a PBX."
     ::= { rlanPriPortGroup 3 }

rPortPBXRoutingEntry OBJECT-TYPE
     SYNTAX  RlanPortPBXRoutingEntry
     ACCESS  not-accessible
     STATUS  mandatory
     ::= { rPortPBXRoutingTable 1 }

RlanPortPBXRoutingEntry ::=
     SEQUENCE {
	 rPortPBXRouting         INTEGER 
     }

rPortPBXRouting OBJECT-TYPE
     SYNTAX  INTEGER (0..4)
     ACCESS  read-write
     STATUS  mandatory
     DESCRIPTION
             "Enter the index number of the rPbxCallRoutingTable associated
	     with this port. Selecting none (0) forces the call type to be 
	     determined in-band.
	     DEFAULT = 0"
     DEFVAL { 0 }
     ::= { rPortPBXRoutingEntry 1 }



--
-- THE IPX Group definition
--

rIPXWatchdogSpoofing OBJECT-TYPE
     SYNTAX  INTEGER {
		 disabled(1),
		 enabled(2)
	     }
     ACCESS  read-write
     STATUS  mandatory
     DESCRIPTION
	     "Select this option to  enable watchdog spoofing from the 
	     local LAN."
     ::= { rlanIPXGroup 1 }


rIPXWatchdogSpoofingTimer OBJECT-TYPE
     SYNTAX  INTEGER (0..99999)
     ACCESS  read-write
     STATUS  mandatory
     DESCRIPTION
	     "Enter the length of time ( in seconds) that spoofing should continue."
     ::= { rlanIPXGroup 2 }


rIPXSAPLearning OBJECT-TYPE
     SYNTAX  INTEGER {
		 stop-learning(1),
		 start-keep-static(2),
		 start-drop-static(3)
	     }
     ACCESS  read-write
     STATUS  mandatory
     DESCRIPTION
	     "Tell the system whether it should learn
	     SAPs. When you want the system to learn SAPs, select one of:

		start-keep-static - Static entries are saved
		start-drop-static - Static entries are deleted

	     NOTE: You can enable learning only when bridging is disabled and no calls 
	     are active."
     ::= { rlanIPXGroup 3 }


rIPXSAPLearningOPState OBJECT-TYPE
     SYNTAX  INTEGER {
		 disabled(1),
		 enabled(2)
	     }
     ACCESS  read-only
     STATUS  mandatory
     DESCRIPTION
	     "Tells you whether or not the system is in SAP learning mode."
     ::= { rlanIPXGroup 4 }


rIPXLearntSAPs OBJECT-TYPE
     SYNTAX  Counter
     ACCESS  read-only
     STATUS  mandatory
     DESCRIPTION
	     "Tells you how many SAP the system has learned
	      since the last learned mode was enabled."
     ::= { rlanIPXGroup 5 }
--


--
--      The IPX Service Advertisement Protocol table
--

rlanSAPTable OBJECT-TYPE
     SYNTAX  SEQUENCE OF RlanSAPEntry
     ACCESS  not-accessible
     STATUS  mandatory
     DESCRIPTION
	     "The IPX Service Advertisement Protocol table."
     ::= { rlanSAPGroup 1 }


rlanSAPEntry OBJECT-TYPE
     SYNTAX  RlanSAPEntry
     ACCESS  not-accessible
     STATUS  mandatory
     INDEX   { rSAPServiceType, rSAPServerName  }
     ::= { rlanSAPTable 1 }


RlanSAPEntry ::=
     SEQUENCE {
	 rSAPServiceType            INTEGER,
	 rSAPServerName             OCTET STRING,
	 rSAPType                   INTEGER,
	 rSAPNetworkAddress         OCTET STRING,
	 rSAPNodeAddress            OCTET STRING,
	 rSAPSocketAddress          INTEGER,
	 rSAPHops                   INTEGER,
	 rSAPGroup                  INTEGER,
	 rSAPStatus                 RowStatus
     }


rSAPServiceType OBJECT-TYPE
     SYNTAX  INTEGER (0..65535)
     ACCESS  read-only
     STATUS  mandatory
     DESCRIPTION
	     "Tells you the type of service that this server provides at this socket.
	     For example:
		 01h = user
		 04h = file server
		 07h = printer server
		 27h = TCP/IP gateway"
     ::= { rlanSAPEntry 1 }


rSAPServerName OBJECT-TYPE
     SYNTAX  OCTET STRING (SIZE(48))
     ACCESS  read-only
     STATUS  mandatory
     DESCRIPTION
	     "Tells you the name of the server."
     ::= { rlanSAPEntry 2 }


rSAPType OBJECT-TYPE
     SYNTAX  INTEGER {
		 dynamic(1),
		 static(2)
	     }
     ACCESS  read-write
     STATUS  mandatory
     DESCRIPTION
	     "Select the option that indicates how this entry was learned
	     (dynamic or static).
	     DEFAULT = static"
     DEFVAL  { static }
     ::= { rlanSAPEntry 3 }


rSAPNetworkAddress OBJECT-TYPE
     SYNTAX  OCTET STRING (SIZE(4))
     ACCESS  read-write
     STATUS  mandatory
     DESCRIPTION
	     "Enter the network address of the server."
     ::= { rlanSAPEntry 4 }


rSAPNodeAddress OBJECT-TYPE
     SYNTAX  OCTET STRING (SIZE(6))
     ACCESS  read-write
     STATUS  mandatory
     DESCRIPTION
	     "Enter the 48-bit node address of the server."
     ::= { rlanSAPEntry 5 }


rSAPSocketAddress OBJECT-TYPE
     SYNTAX  INTEGER (0..65535)
     ACCESS  read-write
     STATUS  mandatory
     DESCRIPTION
	     "Enter the socket address of the server.
	      For example,  04 53 = Routing Info Protocol."
     ::= { rlanSAPEntry 6 }


rSAPHops OBJECT-TYPE
     SYNTAX  INTEGER (1..15)
     ACCESS  read-write
     STATUS  mandatory
     DESCRIPTION
	     "Enter the number of routers to go through to reach the specified
	     server."
     ::= { rlanSAPEntry 7 }


rSAPGroup OBJECT-TYPE
     SYNTAX  INTEGER (2..34)
     ACCESS  read-write
     STATUS  mandatory
     DESCRIPTION
	     "Enter the SAP group that this entry belongs to."
     DEFVAL  { 2 }
     ::= { rlanSAPEntry 8 }


rSAPStatus OBJECT-TYPE
     SYNTAX  RowStatus
     ACCESS  read-write
     STATUS  mandatory
     DESCRIPTION
	     "The current status of this SAP entry."
     ::= { rlanSAPEntry 9 }

--

 
--
--      The SAP Group definition
--
rSAPGroupIdUnused OBJECT-TYPE
     SYNTAX  INTEGER (0..34)
     ACCESS  read-only
     STATUS  mandatory
     DESCRIPTION
	     "This object is used to identify a potentially unused index
	     that can be used as the rSAPGroupId instance when creating 
	     new entries in the rlanSAPGroupTable. A returned value of 
	     zero indicates that the table is full."
     ::= { rlanSAPGroup 2 }

 
rlanSAPGroupTable OBJECT-TYPE
     SYNTAX  SEQUENCE OF RlanSAPGroupEntry
     ACCESS  not-accessible
     STATUS  mandatory
     DESCRIPTION
	     "This table provides an administrative view of the
	     SAP group table."
     ::= { rlanSAPGroup 3 }
 
 
rlanSAPGroupEntry OBJECT-TYPE
     SYNTAX  RlanSAPGroupEntry
     ACCESS  not-accessible
     STATUS  mandatory
     DESCRIPTION
	     "Each entry in this table is a SAP group
	     name. Each name is used to group learned (and static)
	     IPX services together to form a SAP group. This group
	     can then be assigned to a remote LAN that is interested
	     in this grouping of IPX services. 

	     Two default entries exist in this table which cannot be
	     modified or deleted. A rSAPGroupId value of 1 corresponds
	     to the 'All' SAP group, a rSAPGroupId value of 2 corresponds
	     to the 'Default' SAP group. All learned IPX services in the
	     SAP table default to the 'Default' group and all IPX services
	     logically belong to the 'All' group."
     INDEX   { rSAPGroupId }
     ::= { rlanSAPGroupTable 1 }
 
 
RlanSAPGroupEntry ::=
     SEQUENCE {
	 rSAPGroupId            INTEGER,
	 rSAPGroupName          DisplayString,
	 rSAPGroupStatus        RowStatus
     }


rSAPGroupId OBJECT-TYPE
     SYNTAX  INTEGER (1..34)
     ACCESS  read-only
     STATUS  mandatory
     DESCRIPTION
	     "Tells you the index of the entry."
     ::= { rlanSAPGroupEntry 1 }
 
 
rSAPGroupName OBJECT-TYPE
     SYNTAX  DisplayString (SIZE(1..16))
     ACCESS  read-write
     STATUS  mandatory
     DESCRIPTION
	     "Enter the identifier for  this SAP group.
	     NOTE: SAP group names must be unique,
	     but they're not case sensitive. You cannot modify
	     the two default entries (All and Default)."
     ::= { rlanSAPGroupEntry 2 }
 

rSAPGroupStatus OBJECT-TYPE
     SYNTAX  RowStatus
     ACCESS  read-write
     STATUS  mandatory
     DESCRIPTION
	     "Enter the current status of this entry.
	     NOTE: Entries that are currently
	     in use (e.g., either referenced by a remote LAN or in the
	     rlanSAPTable) cannot be destroyed. The default entries 'All'
	     and 'Default' cannot be destroyed."
     ::= { rlanSAPGroupEntry 3 }
 
--


--
--     The IPX RIP Group definition
--

rlanRIPTable OBJECT-TYPE
     SYNTAX  SEQUENCE OF RlanRIPEntry
     ACCESS  not-accessible
     STATUS  mandatory
     DESCRIPTION
	     " The IPX Routing Information Protocol table."
     ::= { rlanRIPGroup 1 }


rlanRIPEntry OBJECT-TYPE
     SYNTAX  RlanRIPEntry
     ACCESS  not-accessible
     STATUS  mandatory
     INDEX   { rRIPNetworkAddress  }
     ::= { rlanRIPTable 1 }


RlanRIPEntry ::=
     SEQUENCE {
	 rRIPNetworkAddress    OCTET STRING,
	 rRIPHops              INTEGER,
	 rRIPTicks             TimeTicks,
	 rRIPMACAddress        PhysAddress
     }


rRIPNetworkAddress OBJECT-TYPE
     SYNTAX  OCTET STRING (SIZE(4))
     ACCESS  read-only
     STATUS  mandatory
     DESCRIPTION
	     "Tells you the network address of this route."
     ::= { rlanRIPEntry 1 }


rRIPHops OBJECT-TYPE
     SYNTAX  INTEGER (1..15)
     ACCESS  read-only
     STATUS  mandatory
     DESCRIPTION
	     "Tells you the number of routers to go through before reaching
	     this network."
     ::= { rlanRIPEntry 2}


rRIPTicks OBJECT-TYPE
     SYNTAX  TimeTicks
     ACCESS  read-only
     STATUS  mandatory
     DESCRIPTION
	     "Tells you how long (in time-ticks) it takes to reach this network."
     ::= { rlanRIPEntry 3 }


rRIPMACAddress OBJECT-TYPE
     SYNTAX  PhysAddress
     ACCESS  read-only
     STATUS  mandatory
     DESCRIPTION
	     "Tells you the physical (MAC) address of the remote LAN."
     ::= { rlanRIPEntry 4 }

--


--
--     The SNMP Group
--

rlanSnmpSetStatus OBJECT-TYPE
     SYNTAX  INTEGER {
		 noError(1),
		 internalError(2),
		 badInstance(3),
		 dupName(4),
		 tableFull(5),
		 notFound(6),
		 badValue(7),
		 setError(8),
		 getError(9),
		 createError(10),
		 deleteError(11),
		 dupXID(12),
		 linkUp(13),
		 linkDown(14),
		 offline(15),
		 outCallFail(16),
		 badName(17),
		 noFlash(18),
		 badVersion(19),
		 enabledError(20),
		 inUse(21),
		 tooFew(22),
		 cannotModify(23),
		 sapLearning(24),
		 noIpxRoute(25)
	     }
     ACCESS  read-only
     STATUS  mandatory
     DESCRIPTION
	     "This object records the result code of the last SNMP set 
	     operation. On a set that fails this object can be retrieved
	     to enhance the error codes provided by the SNMP protocol.
	     If the set response contains a non zero error index then
	     this object relates to the object in the set request as 
	     indicated by the error index (as per normal PDU error 
	     parsing). If the set response message indicates an error but
	     the error index is zero then this object pertains to the
	     semantics of the attempted set operation on the system as
	     as whole (e.g. table full)."
     ::= { rlanSnmpGroup 1 }
 
--


--
--     The SNMP Community Table
--

rSnmpCommunityIndexUnused OBJECT-TYPE
     SYNTAX  INTEGER (0..5)
     ACCESS  read-only
     STATUS  mandatory
     DESCRIPTION
	     "This object is used to identify a potentially unused index
	     that can be used as the rSnmpCommunityIndex instance when 
	     creating new entries in the rlanSnmpCommunityTable. A 
	     returned value of zero indicates that the table is full."
     ::= { rlanSnmpGroup 2 }


rlanSnmpCommunityTable OBJECT-TYPE
     SYNTAX  SEQUENCE OF RlanSnmpCommunityEntry
     ACCESS  not-accessible
     STATUS  mandatory
     DESCRIPTION
	     "This table provides a management view of which device can 
	     poll this resource via SNMP based on the Community Name, 
	     IP address, Privilege and MIB view."
     ::= { rlanSnmpGroup 3 }


rlanSnmpCommunityEntry OBJECT-TYPE
     SYNTAX  RlanSnmpCommunityEntry
     ACCESS  not-accessible
     STATUS  mandatory
     DESCRIPTION
	     "This is a list of attributes that make the Community
	     Table."
     INDEX   { rSnmpCommunityIndex }
     ::= { rlanSnmpCommunityTable 1 }
 
RlanSnmpCommunityEntry ::=
    SEQUENCE {
	rSnmpCommunityIndex      INTEGER,
	rSnmpCommunityName       DisplayString,
	rSnmpCommunityIpAddr     IpAddress,
	rSnmpCommunityPriv       INTEGER,
	rSnmpCommunityViewIndex  INTEGER,
	rSnmpCommunityRowStatus  RowStatus
     }
 
 
rSnmpCommunityIndex OBJECT-TYPE
     SYNTAX  INTEGER (1..5)
     ACCESS  read-only
     STATUS  mandatory
     DESCRIPTION
	     "Tells you the index entry of this community."
     ::= { rlanSnmpCommunityEntry 1 }
 
 
rSnmpCommunityName OBJECT-TYPE
     SYNTAX  DisplayString (SIZE(1..16))
     ACCESS  read-write
     STATUS  mandatory
     DESCRIPTION
	     "Tells you the name of a community supported by this SNMP agent."
     ::= { rlanSnmpCommunityEntry 2 }

 
rSnmpCommunityIpAddr OBJECT-TYPE
     SYNTAX  IpAddress
     ACCESS  read-write
     STATUS  mandatory
     DESCRIPTION
	     "Enter the IP address of a manager  associated with a community
	     that will be supported by the SNMP agent.  NOTE: A value of
	     zero means that all managers from that community will be
	     supported."
     ::= { rlanSnmpCommunityEntry 3 }
 
 
rSnmpCommunityPriv OBJECT-TYPE
     SYNTAX  INTEGER {
		 none(1),
		 readOnly(2),
		 readWrite(3)
	     }
     ACCESS  read-write
     STATUS  mandatory
     DESCRIPTION
	     "Enter the access privilege associated with this community,
	     which can be one of none, readOnly, or readWrite.
	     DEFAULT = readOnly"
     DEFVAL { readOnly }       
     ::= { rlanSnmpCommunityEntry 4 }
 
 
rSnmpCommunityViewIndex OBJECT-TYPE
     SYNTAX  INTEGER (1..4)
     ACCESS  read-write
     STATUS  mandatory
     DESCRIPTION
	     "Enter the identifier for  the MIB view that is visible to this
	     community.
	     DEFAULT = 2"
     DEFVAL { 2 }
     ::= { rlanSnmpCommunityEntry 5 }
 
 
rSnmpCommunityRowStatus OBJECT-TYPE
     SYNTAX  RowStatus
     ACCESS  read-write
     STATUS  mandatory
     DESCRIPTION
	     "Enter the current status of this entry."
     ::= { rlanSnmpCommunityEntry 6 }

--


--
--      The Snmp Trap community table
--

rSnmpTrapCommunityIndexUnused OBJECT-TYPE
     SYNTAX  INTEGER (0..5)
     ACCESS  read-only
     STATUS  mandatory
     DESCRIPTION
	     "This object is used to identify a potentially unused index
	     that can be used as the rSnmpTrapCommunityIndex instance when 
	     creating new entries in the rlanSnmpTrapCommunityTable. A 
	     returned value of zero indicates that the table is full."
     ::= { rlanSnmpGroup 4 }


rlanSnmpTrapCommunityTable OBJECT-TYPE
     SYNTAX  SEQUENCE OF RlanSnmpTrapCommunityEntry
     ACCESS  not-accessible
     STATUS  mandatory
     DESCRIPTION
	     "This table provide a management view of which device(s)
	     (i.e., LAN Managers) this resource will send traps to." 
     ::= { rlanSnmpGroup 5 }


rlanSnmpTrapCommunityEntry OBJECT-TYPE
     SYNTAX  RlanSnmpTrapCommunityEntry
     ACCESS  not-accessible
     STATUS  mandatory
     DESCRIPTION
	     "This is a list of attributes that make the trap
	     community table."
     INDEX  { rSnmpTrapCommunityIndex }
     ::= { rlanSnmpTrapCommunityTable 1 }
 
RlanSnmpTrapCommunityEntry ::=
     SEQUENCE {
	 rSnmpTrapCommunityIndex   INTEGER,
	 rSnmpTrapCommunityName    DisplayString,
	 rSnmpTrapIpAddr           IpAddress,
	 rSnmpTrapRemotePort       INTEGER,
	 rSnmpTrapStatus           RowStatus
     }

rSnmpTrapCommunityIndex OBJECT-TYPE
     SYNTAX  INTEGER (1..5)
     ACCESS  read-only
     STATUS  mandatory
     DESCRIPTION
	     "Tells you the index of this community entry."
     ::= { rlanSnmpTrapCommunityEntry 1 }
 

rSnmpTrapCommunityName OBJECT-TYPE
     SYNTAX  DisplayString (SIZE(1..16))
     ACCESS  read-write
     STATUS  mandatory
     DESCRIPTION
	     "Enter the name of a trap community associated with a LAN
	     manager."
     ::= { rlanSnmpTrapCommunityEntry 2 }

 
rSnmpTrapIpAddr OBJECT-TYPE
     SYNTAX  IpAddress
     ACCESS  read-write
     STATUS  mandatory
     DESCRIPTION
	     "Enter the IP address of a manager that will receive traps
	     generated by this SNMP agent."
     ::= { rlanSnmpTrapCommunityEntry 3 }

 
rSnmpTrapRemotePort OBJECT-TYPE
     SYNTAX  INTEGER
     ACCESS  read-write
     STATUS  mandatory
     DESCRIPTION
	     "Enter the remote UDP port number used by an agent to receive traps.
	     DEFAULT = 162"
     DEFVAL { 162 }
     ::= { rlanSnmpTrapCommunityEntry 4 }
 

rSnmpTrapStatus OBJECT-TYPE
     SYNTAX  RowStatus
     ACCESS  read-write
     STATUS  mandatory
     DESCRIPTION
	    "Enter the current status of this entry."
     ::= { rlanSnmpTrapCommunityEntry 5 }

--


--
--    The Snmp View Name Table
--

rSnmpViewNameIndexUnused OBJECT-TYPE
     SYNTAX  INTEGER (0..4)
     ACCESS  read-only
     STATUS  mandatory
     DESCRIPTION
	     "This object is used to identify a potentially unused index
	     that can be used as the rSnmpViewNameIndex instance when
	     creating new entries in the rlanSnmpViewNameTable. A
	     returned value of zero indicates that the table is full."
     ::= { rlanSnmpGroup 6 }
 
 
rlanSnmpViewNameTable OBJECT-TYPE
     SYNTAX  SEQUENCE OF RlanSnmpViewNameEntry
     ACCESS  not-accessible
     STATUS  mandatory
     DESCRIPTION
	     "The table is contained in the local database which defines local 
	     MIB views. Reference RFC 1647 for details on MIB views. This
	     table has been adopted from RFC 1647 to an SNMPv1 environment
	     however the logic is the same."
     ::= { rlanSnmpGroup 7 }


rlanSnmpViewNameEntry OBJECT-TYPE
     SYNTAX  RlanSnmpViewNameEntry
     ACCESS  not-accessible
     STATUS  mandatory
     INDEX   { rSnmpViewNameIndex }
     ::= { rlanSnmpViewNameTable 1 }


RlanSnmpViewNameEntry ::=
     SEQUENCE {
	 rSnmpViewNameIndex    INTEGER,
	 rSnmpViewName         DisplayString,
	 rSnmpViewNameStatus   RowStatus
     }


rSnmpViewNameIndex OBJECT-TYPE
     SYNTAX  INTEGER (1..4)
     ACCESS  read-only
     STATUS  mandatory
     DESCRIPTION
	     "Tells you the index identifier of the name entry for this MIB view.
	     NOTE: MIB view indexes one(1) and two(2) are statistically configured
	     and cannot be modified. "
     ::= { rlanSnmpViewNameEntry 1 }


rSnmpViewName OBJECT-TYPE
     SYNTAX  DisplayString (SIZE(1..16))
     ACCESS  read-write
     STATUS  mandatory
     DESCRIPTION
	     "Enter the ASCII name assigned to this MIB view."
     ::= { rlanSnmpViewNameEntry 2 }


rSnmpViewNameStatus OBJECT-TYPE
     SYNTAX  RowStatus
     ACCESS  read-write
     STATUS  mandatory
     DESCRIPTION
	     "Enter the current status of this entry."
     ::= { rlanSnmpViewNameEntry 3 }
     
--


--
--   The MIB View Database Group
--

rlanSnmpViewTable OBJECT-TYPE
     SYNTAX  SEQUENCE OF RlanSnmpViewEntry
     ACCESS  not-accessible
     STATUS  mandatory
     DESCRIPTION
	     "The table is contained in the local database which defines local 
	     MIB views. Reference RFC 1647 for details on MIB views. This
	     table has been adopted from RFC 1647 to a SNMPv1 enironment
	     however the logic is the same."
     ::= { rlanSnmpGroup 8 }


rlanSnmpViewEntry OBJECT-TYPE
     SYNTAX  RlanSnmpViewEntry
     ACCESS  not-accessible
     STATUS  mandatory
     INDEX   { rSnmpViewNameIndex, rSnmpViewSubtree }
     ::= { rlanSnmpViewTable 1 }


RlanSnmpViewEntry ::=
     SEQUENCE {
	 rSnmpViewSubtree      OBJECT IDENTIFIER,
	 rSnmpViewMask         OCTET STRING,
	 rSnmpViewType         INTEGER,
	 rSnmpViewStatus       RowStatus
     }


rSnmpViewSubtree OBJECT-TYPE
     SYNTAX  OBJECT IDENTIFIER
     ACCESS  read-only
     STATUS  mandatory
     DESCRIPTION
	     "Identifies a MIB subtree."
     ::= { rlanSnmpViewEntry 1 }

rSnmpViewMask OBJECT-TYPE
     SYNTAX  OCTET STRING (SIZE(0..4))
     ACCESS  read-write
     STATUS  mandatory
     DESCRIPTION
	     "The bit mask which, in combination with the
	     corresponding instance of viewSubtree, defines a
	     family of view subtrees.

	     Each bit of this bit mask corresponds to a sub-
	     identifier of viewSubtree, with the most
	     significant bit of the i-th octet of this octet
	     string value (extended if necessary, see below)
	     corresponding to the (8*i - 7)-the sub-identifier,
	     and the least significant bit of the i-th octet of
	     this octet string corresponding to the (8*i)-th
	     sub-identifier, where i is in the range 1 through
	     16.
 
	     Each bit of this bit mask specifies whether or not
	     the corresponding sub-identifiers must match when
	     determining if an OBJECT IDENTIFIER is in this
	     family of view subtrees; a '1' indicates that an
	     exact match must occur; a '0' indicates 'wild
	     card', i.e., any sub-identifier value matches.
	     Thus, the OBJECT IDENTIFIER X of an object
	     instance is contained in a family of view subtrees
	     if the following criteria are met:
 
	     for each sub-identifier of the value of
	     viewSubtree, either:
 
		    the i-th bit of viewMask is 0, or
 
		    the i-th sub-identifier of X is equal to
		    the i-th sub-identifier of the value of
		    viewSubtree.
 
	     If the value of this bit mask is M bits long and
	     there are more than M sub-identifiers in the
	     corresponding instance of viewSubtree, then the
	     bit mask is extended with 1's to be the required
	     length.

	     Note that when the value of this object is the
	     zero-length string, this extension rule results in
	     a mask of all-1's being used (i.e., no 'wild
	     card'), and the family of view subtrees is the one
	     view subtree uniquely identified by the
	     corresponding instance of viewSubtree."
     DEFVAL  { ''H }
     ::= { rlanSnmpViewEntry 2 }


rSnmpViewType OBJECT-TYPE
     SYNTAX  INTEGER {
		 included(1),
		 excluded(2)
	     }
     ACCESS  read-write
     STATUS  mandatory
     DESCRIPTION
	     "The status of a particular family of view
	     subtrees within the particular SNMPv2 context's
	     MIB view.  The value, included(1), indicates that
	     the corresponding instances of viewSubtree and
	     viewMask define a family of view subtrees included
	     in the MIB view.  The  value, excluded(2),
	     indicates that the corresponding instances of
	     viewSubtree and viewMask define a family of view
	     subtrees excluded from the MIB view."
     DEFVAL  { included }
     ::= { rlanSnmpViewEntry 3 }
 

rSnmpViewStatus OBJECT-TYPE
     SYNTAX  RowStatus
     ACCESS  read-write
     STATUS  mandatory
     DESCRIPTION
	     "Enter the status of this conceptual row in the viewTable."
     ::= { rlanSnmpViewEntry 4 }

--


--
--    The Snmp Trap Profile Table
--

rlanSnmpTrapProfileTable OBJECT-TYPE
     SYNTAX  SEQUENCE OF RlanSnmpTrapProfileEntry
     ACCESS  not-accessible
     STATUS  mandatory
     DESCRIPTION
	     "This table provides a management interface to the trap
	     profile table objects."
     ::= { rlanSnmpGroup 9 }
 
 
rlanSnmpTrapProfileEntry OBJECT-TYPE
     SYNTAX  RlanSnmpTrapProfileEntry
     ACCESS  not-accessible
     STATUS  mandatory
     INDEX   { rSnmpTrapEnterprise, rSnmpTrapId }
     ::= { rlanSnmpTrapProfileTable 1 }
 
 
RlanSnmpTrapProfileEntry ::=
     SEQUENCE {
	 rSnmpTrapEnterprise   OBJECT IDENTIFIER,
	 rSnmpTrapId           INTEGER,
	 rSnmpCommunities      OCTET STRING
     }
 
 
rSnmpTrapEnterprise OBJECT-TYPE
     SYNTAX  OBJECT IDENTIFIER
     ACCESS  read-only
     STATUS  mandatory
     DESCRIPTION
	     "The object identifier of the enterprise in which this trap
	     is defined. For example; to disable the gDChanUp trap defined
	     in this MIB this object would contain the object identifier
	     for gandalf (1.3.6.1.4.1.64)."
     ::= { rlanSnmpTrapProfileEntry 1 }
 
 
rSnmpTrapId OBJECT-TYPE
     SYNTAX  INTEGER
     ACCESS  read-only
     STATUS  mandatory
     DESCRIPTION
	     "The unique trap id that the associated enterprise has assigned
	     this trap. For example; to disable the gDChanUp trap defined
	     in this MIB this object would contain the value 9024."
     ::= { rlanSnmpTrapProfileEntry 2 }


rSnmpCommunities OBJECT-TYPE
     SYNTAX  OCTET STRING
     ACCESS  read-write
     STATUS  mandatory
     DESCRIPTION
	     "The list of communities that are interested in this trap. Can
	     also be used to disable traps. Communities are represented as
	     a bit string where each bit in each octet represents a
	     community. The most significant bit of octet one represents 
	     the community whose rSnmpTrapCommunityIndex value is one."
     DEFVAL { 'E0'h }        
     ::= { rlanSnmpTrapProfileEntry 3 }
--


--
--    Audit Group
--

rAuditingEnabled OBJECT-TYPE
     SYNTAX  INTEGER {
		 disabled(1),
		 enabled(2)
	     }
     ACCESS  read-write
     STATUS  mandatory
     DESCRIPTION
	     "Select this option when you want to enable auditing. Can only be enabled 
              if a valid file transfer profile is set up for it."
     DEFVAL { disabled }
     ::= { rlanAuditGroup 1 }
 
 
rAuditTimeOfDayTransfer OBJECT-TYPE
     SYNTAX  INTEGER {
		 disabled(1),
		 enabled(2)
	     }    
     ACCESS  read-write
     STATUS  mandatory
     DESCRIPTION
	     "Select this option when you want the system to transfer
	     audit records at a specified time of day
	     DEFAULT = disabled"
     DEFVAL { disabled }        
     ::= { rlanAuditGroup 2 }


rAuditTimeOfDay OBJECT-TYPE
     SYNTAX  INTEGER (0..86340)
     ACCESS  read-write
     STATUS  mandatory
     DESCRIPTION
	     "Enter the time of day you want the system to initiate the file
	     transfer. NOTE: The times are entered as seconds but will only be accepted 
             on a 60 sec boundary.  A value of zero indicates midnight, a value of 60 
             indicates 12:01, 43200 indicates 12am, 86340 indicates 23:59 and so on.
	     DEFAULT = 0"
     DEFVAL { 0 }        
     ::= { rlanAuditGroup 3 }


rAuditRecordTermChars OBJECT-TYPE
     SYNTAX  INTEGER {
		 cr(1),
		 lf(2),
		 crlf(3)
	     }
     ACCESS  read-write
     STATUS  mandatory
     DESCRIPTION
	     "Select the way you want the system to
	     set up the termination records for individual audit records.
	     DEFAULT = crlf"
     DEFVAL { crlf }
     ::= { rlanAuditGroup 4 }
 
 
rAuditRecordsInFlash OBJECT-TYPE
     SYNTAX  Gauge 
     ACCESS  read-only
     STATUS  mandatory
     DESCRIPTION
	     "Tells you how many audit records are
	     are currently in flash memory. NOTE: After a file transfer,
	     this field is reset to zero."
     ::= { rlanAuditGroup 5 }

--^L
 
--
--    Flash Group
--

rlanFlashDirectoryTable OBJECT-TYPE
     SYNTAX  SEQUENCE OF RlanFlashDirectoryEntry
     ACCESS  not-accessible
     STATUS  mandatory
     DESCRIPTION
	     "This table provides a management interface to the flash
	     directory listings."
     ::= { rlanFlashGroup 1 }
 
 
rlanFlashDirectoryEntry OBJECT-TYPE
     SYNTAX  RlanFlashDirectoryEntry
     ACCESS  not-accessible
     STATUS  mandatory
     INDEX   { rFlashFileIndex }
     ::= { rlanFlashDirectoryTable 1 }
 
 
RlanFlashDirectoryEntry ::=
     SEQUENCE {
	 rFlashFileIndex           INTEGER,
	 rFlashFileType            DisplayString,
	 rFlashFileId              INTEGER,
	 rFlashFileAddress         OCTET STRING,
	 rFlashFileSize            INTEGER,
	 rFlashFileVersion         DisplayString,
	 rFlashFileCrc             INTEGER
     }
 
 
rFlashFileIndex OBJECT-TYPE
     SYNTAX  INTEGER (1..16)
     ACCESS  read-only
     STATUS  mandatory
     DESCRIPTION
	     "Tells you the directory index associated with this file in flash memory."
     ::= { rlanFlashDirectoryEntry 1 }
 
 
rFlashFileType OBJECT-TYPE
     SYNTAX  DisplayString (SIZE(1..16))
     ACCESS  read-write
     STATUS  mandatory
     DESCRIPTION
	     "Tells you the type of file (e.g., BRI
	     operating software) associated with this entry."
     ::= { rlanFlashDirectoryEntry 2 }
 
 
rFlashFileId OBJECT-TYPE
     SYNTAX  INTEGER
     ACCESS  read-only
     STATUS  mandatory
     DESCRIPTION
	     "Tells you id of this file in flash memory ."
     ::= { rlanFlashDirectoryEntry 3 }
 
 
rFlashFileAddress OBJECT-TYPE
     SYNTAX  OCTET STRING
     ACCESS  read-only
     STATUS  mandatory
     DESCRIPTION
	     "Tells you the address of this file in flash memory."
     ::= { rlanFlashDirectoryEntry 4 }
 
 
rFlashFileSize OBJECT-TYPE
     SYNTAX  INTEGER
     ACCESS  read-only
     STATUS  mandatory
     DESCRIPTION
	     "Tells you (in bytes) the size of this file in flash memory."
     ::= { rlanFlashDirectoryEntry 5 }
 
 
rFlashFileVersion OBJECT-TYPE
     SYNTAX  DisplayString (SIZE(1..16))
     ACCESS  read-write
     STATUS  mandatory
     DESCRIPTION
	     "Tells you the software version of the file in flash memory."
     ::= { rlanFlashDirectoryEntry 6 }
 
 
rFlashFileCrc OBJECT-TYPE
     SYNTAX  INTEGER {
		 good(1),
		 bad(2)
	     }
     ACCESS  read-only
     STATUS  mandatory
     DESCRIPTION
	     "Tells you whether the checksum for the embedded file(s)
	     matches the checksum generated by the RSC."
     ::= { rlanFlashDirectoryEntry 7 }

--


--
--      The LAN Protocol ID definition
--
rLANProtocolIDIdUnused OBJECT-TYPE
     SYNTAX  INTEGER (0..159)
     ACCESS  read-only
     STATUS  mandatory
     DESCRIPTION
	     "This object is used to identify a potentially unused index
	     that can be used as the rLANProtocolIDId instance when creating 
	     new entries in the rlanLANProtocolIDTable. A returned value of 
	     zero indicates that the table is full."
     ::= { rlanLANProtocolIDGroup 1 }

 
rlanLANProtocolIDTable OBJECT-TYPE
     SYNTAX  SEQUENCE OF RlanLANProtocolIDEntry
     ACCESS  not-accessible
     STATUS  mandatory
     DESCRIPTION
	     "This table provides an administrative view of the
	     LAN protocol ID table."
     ::= { rlanLANProtocolIDGroup 2 }
 
 
rlanLANProtocolIDEntry OBJECT-TYPE
     SYNTAX  RlanLANProtocolIDEntry
     ACCESS  not-accessible
     STATUS  mandatory
     DESCRIPTION
	     "Each entry in this table is a LAN protocol ID and
	     name. This entry can then be used in designing which
	     protocol that is to be filtered or forwarded.

	     Six default entries exist in this table which cannot be
	     modified or deleted. They are:
                122 Novell IPX/SPX  8137
                123 AppleTalk ARP   80F3
                124 AppleTalk       809B
                125 Reverse ARP     8035
                126 ARP             0806
                127 TCP/IP          0800"
     INDEX   { rLANProtocolIDId }
     ::= { rlanLANProtocolIDTable 1 }
 
 
RlanLANProtocolIDEntry ::=
     SEQUENCE {
	 rLANProtocolIDId            INTEGER,
	 rLANProtocolID              INTEGER,
	 rLANProtocolIDName          DisplayString,
	 rLANProtocolIDStatus        RowStatus
     }


rLANProtocolIDId OBJECT-TYPE
     SYNTAX  INTEGER (1..159)
     ACCESS  read-only
     STATUS  mandatory
     DESCRIPTION
	     "Tells you the index of the entry."
     ::= { rlanLANProtocolIDEntry 1 }
 
 
rLANProtocolID OBJECT-TYPE
     SYNTAX  INTEGER (1501..65535)
     ACCESS  read-write
     STATUS  mandatory
     DESCRIPTION
	     "16 bit ID of the LAN protocol.
	     You cannot modify the predefined entries."
     ::= { rlanLANProtocolIDEntry 2 }
 
 
rLANProtocolIDName OBJECT-TYPE
     SYNTAX  DisplayString (SIZE(1..16))
     ACCESS  read-write
     STATUS  mandatory
     DESCRIPTION
	     "Enter the identifier for this LAN protocol ID.
	     You cannot modify the predefined entries."
     ::= { rlanLANProtocolIDEntry 3 }
 

rLANProtocolIDStatus OBJECT-TYPE
     SYNTAX  RowStatus
     ACCESS  read-write
     STATUS  mandatory
     DESCRIPTION
	     "Enter the current status of this entry.
	     NOTE: Entries that are currently
	     in use (e.g., assigned to be filtered or forwarded)
	     cannot be destroyed. The predefined entries cannot be
	     destroyed."
     ::= { rlanLANProtocolIDEntry 4 }
 
--

--
-- Definition of the rlanModemGroup
--


--
--
--  System wide modem objects.
--
--

rlanMdmCountry OBJECT-TYPE
    SYNTAX  INTEGER {
                 argintina(1),
                 australia(2),
                 austria(3),
                 belgium(4),
                 brazil(5),
                 canada(6),
                 chile(7),
                 china(8),
                 columbia(9),
                 czechRepublic(10),
                 denmark(11),
                 finland(12),
                 france(13),
                 germany(14),
                 greece(15),
                 hongKong(16),
                 hungary(17),
                 india(18),
                 indonesia(19),
                 ireland(20),
                 israel(21),
                 italy(22),
                 italySip(23),
                 japan(24),
                 korea(25),
                 malaysia(26),
                 mexico(27),
                 netherlands(28),
                 newZealand(29),
                 norway(30),
                 peru(31),
                 philippines(32),
                 poland(33),
                 saudiaArabia(34),
                 singapore(35),
                 southAfricA(36),
                 spain(37),
                 sweden(38),
                 switzerland(39),
                 tiawan(40),
                 thailand(41),
                 unitedKingdom(42),
                 unitedStates(43)
               }
    ACCESS  read-write
    STATUS  mandatory
    DESCRIPTION
           "This attribute configures the system for a 
            specific country.
            DEFAULT = United States"
    DEFVAL { unitedStates }
    ::= { rlanModemGroup 1 }

--  { rlanModemGroup 2 } obsoleted

rlanMdmMode OBJECT-TYPE
    SYNTAX  INTEGER {
                 modemOriginate(1),
                 modemAnswer(2)
               }
    ACCESS  read-write
    STATUS  mandatory
    DESCRIPTION
           "Defines that modems are setup for either 
            originate or answer.  When there is an
	    incomming call the setting in this object will
	    be the default for all the modems.  On an outgoing 
	    call the value of rRemLANMdmAnswer will control
	    the individual modem.  DEFAULT = modemAnswer"
    DEFVAL { modemAnswer }
    ::= { rlanModemGroup 3 }

rlanMdmIDTable OBJECT-TYPE
    SYNTAX  SEQUENCE OF RlanMdmIDEntry
    ACCESS  not-accessible
    STATUS  mandatory
    DESCRIPTION
           "The base table for the modems managed by this MIB.  The
            rlanMdmLineTable, rlanMdmDTEInterfaceTable, 
            rlanMdmCallControlTable, and rlanMdmStatsTable all augment
            the rows defined in this table."
    ::= { rlanModemGroup 4 }

rlanMdmIDEntry OBJECT-TYPE
    SYNTAX  RlanMdmIDEntry
    ACCESS  not-accessible
    STATUS  mandatory
    DESCRIPTION
           "Entries in this table are created only by the agent. One
            entry exists for each modem managed by the agent."
    INDEX   {  rChanCardID, rChanPortID }
    ::= { rlanMdmIDTable 1 }

RlanMdmIDEntry ::=
    SEQUENCE {
        rMdmIDManufacturerOID
            OBJECT IDENTIFIER,

        rMdmIDProductDetails
            DisplayString
    }

rMdmIDManufacturerOID OBJECT-TYPE
    SYNTAX  OBJECT IDENTIFIER
    ACCESS  read-only
    STATUS  mandatory
    DESCRIPTION
           "This value is intended to identify the manufacturer, model,
            and version of this modem.  This may be used to identify the
            existance of enterprise-specific functions and behaviours."
    REFERENCE
           "V.58 attribute manufacturerID subfield ManufacturerOI"
    ::= { rlanMdmIDEntry 2 }

rlanMdmIDProductDetails OBJECT-TYPE
    SYNTAX  DisplayString
    ACCESS  read-only
    STATUS  mandatory
    DESCRIPTION
           "A textual description of this device, including the
            manufacturer's name, modem model name, hardware revision,
            firmware revision, and optionally, its serial number.  The
            exact format of this description is defined by the vendor.
            This description may only contain characters from the NVT
            ASCII character set."
    REFERENCE
           "V.58 attribute manufacturerID subfield productDetails"
    ::= { rlanMdmIDEntry 3 }

rlanMdmLineTable OBJECT-TYPE
    SYNTAX  SEQUENCE OF RlanMdmLineEntry
    ACCESS  not-accessible
    STATUS  mandatory
    DESCRIPTION
           "The modem Line Table augments the modem ID table."
    ::= { rlanModemGroup 5 }

rlanMdmLineEntry OBJECT-TYPE
    SYNTAX  RlanMdmLineEntry
    ACCESS  not-accessible
    STATUS  mandatory
    DESCRIPTION
           "Entries in this table are created only by the agent. One
            entry exists for each modem managed by the agent."
-- AUGMENTS { rlanMdmIDEntry } 
    ::= { rlanMdmLineTable  1 }

RlanMdmLineEntry ::=
    SEQUENCE {
        rMdmLineState
            INTEGER
    }


rMdmLineState OBJECT-TYPE
    SYNTAX  INTEGER {
                 idle(1),
                 incomingRing(2),
                 dialingOrAnswering(3),
                 waitingForCarrier(4),
                 connected(5),
                 busiedOut(6),
                 disconnecting(7),
                 retraining(8),
                 rateChange(9)
               }
    ACCESS  read-only
    STATUS  mandatory
    DESCRIPTION
           "Allows the inspection of the state of the
            modem."
    ::= { rlanMdmLineEntry  2 }

rlanMdmECTable OBJECT-TYPE
    SYNTAX  SEQUENCE OF RlanMdmECEntry
    ACCESS  not-accessible
    STATUS  mandatory
    DESCRIPTION
           "The modem error correcting table augments the modem ID
            table."
    ::= { rlanModemGroup 6 }

rlanMdmECEntry OBJECT-TYPE
    SYNTAX  RlanMdmECEntry
    ACCESS  not-accessible
    STATUS  mandatory
    DESCRIPTION
           "Entries in this table are created only by the agent. One
            entry exists for each modem managed by the agent."
-- AUGMENTS { rlanMdmIDEntry } 
    ::= { rlanMdmECTable  1 }

RlanMdmECEntry ::=
    SEQUENCE {
        rMdmECErrorControlUsed
            INTEGER
    }

rMdmECErrorControlUsed OBJECT-TYPE
    SYNTAX  INTEGER {
                 normal(1),
                 direct(2),
                 mnp(3),
                 lapmV42(4),
                 sync(5)
               }
    ACCESS  read-only
    STATUS  mandatory
    DESCRIPTION
           "Indicates the error control method used during the current
            or previous call."
::= { rlanMdmECEntry  1 }

rlanMdmDCTable OBJECT-TYPE
    SYNTAX  SEQUENCE OF RlanMdmDCEntry
    ACCESS  not-accessible
    STATUS  mandatory
    DESCRIPTION
           "The modem data compression table augments the modem ID
            table."
    ::= { rlanModemGroup 7 }

rlanMdmDCEntry OBJECT-TYPE
    SYNTAX  RlanMdmDCEntry
    ACCESS  not-accessible
    STATUS  mandatory
    DESCRIPTION
           "Entries in this table are created only by the agent. One
            entry exists for each modem managed by the agent."
-- AUGMENTS { rlanMdmIDEntry } 
    ::= { rlanMdmDCTable  1 }

RlanMdmDCEntry ::=
    SEQUENCE {
        rMdmDCCompressionTypeUsed
            INTEGER
    }

rMdmDCCompressionTypeUsed OBJECT-TYPE
    SYNTAX  INTEGER {
                 none(1),
                 v24bis(2),
                 mnpClass5(3)
	    }
    ACCESS  read-only
    STATUS  mandatory
    DESCRIPTION
           "Indicates the data compression method used during the
            current or previous call.  If no compression protocol is in 
            use, this object shall have the value 1."
    ::= { rlanMdmDCEntry  1 }

rlanMdmSCTable OBJECT-TYPE
    SYNTAX  SEQUENCE OF RlanMdmSCEntry
    ACCESS  not-accessible
    STATUS  mandatory
    DESCRIPTION
           "The modem signal convertor table augments the modem ID
            table."
    ::= { rlanModemGroup 8 }

rlanMdmSCEntry OBJECT-TYPE
    SYNTAX  RlanMdmSCEntry
    ACCESS  not-accessible
    STATUS  mandatory
    DESCRIPTION
           "Entries in this table are created only by the agent. One
            entry exists for each modem managed by the agent."
-- AUGMENTS { rlanMdmIDEntry } 
    ::= { rlanMdmSCTable  1 }

RlanMdmSCEntry ::=
    SEQUENCE {
        rMdmSCCurrentLineTransmitRate
            INTEGER (0..2147483647),

        rMdmSCCurrentLineReceiveRate
            INTEGER (0..2147483647),

        rMdmSCModulationSchemeUsed
            INTEGER
    }

rMdmSCCurrentLineTransmitRate OBJECT-TYPE
    SYNTAX  INTEGER (0..2147483647)
    ACCESS  read-only
    STATUS  mandatory
    DESCRIPTION
           "The current link transmit rate of a connection, or the last
            link transmit rate of the last connection in bits per
            second."
    REFERENCE
           "V.58 transmissionSignallingRateActive"
    ::= { rlanMdmSCEntry  1 }

rMdmSCCurrentLineReceiveRate OBJECT-TYPE
    SYNTAX  INTEGER (0..2147483647)
    ACCESS  read-only
    STATUS  mandatory
    DESCRIPTION
           "The current link receive rate of a connection, or the last
            link receive rate of the last connection in bits per
            second."
    REFERENCE
           "V.58 transmissionSignallingRateActive"
    ::= { rlanMdmSCEntry  2 }

rMdmSCModulationSchemeUsed OBJECT-TYPE
    SYNTAX  INTEGER {
                 bell103A(1),
                 bell212A(2),
                 v21(3),
                 v22(4),
                 v22bis(5),
                 v23(6),
                 v32(7),
                 v32bis(8),
		 vfc(9),
                 v34(10),
                 v34bis(11),
		 x2(12),
		 k56flex(13),
		 v90(14)
              }
    ACCESS  read-only
    STATUS  mandatory
    DESCRIPTION
           "The modulation scheme of the current or previous call."
    REFERENCE
           "V.58 gstnModulationSchemeActive"
    ::= { rlanMdmSCEntry  5 }

rlanMdmStatsTable OBJECT-TYPE
    SYNTAX  SEQUENCE OF RlanMdmStatsEntry
    ACCESS  not-accessible
    STATUS  mandatory
    DESCRIPTION
           "The modem statistics Table augments the modem ID table."
    ::= { rlanModemGroup 9 }

rlanMdmStatsEntry OBJECT-TYPE
    SYNTAX  RlanMdmStatsEntry
    ACCESS  not-accessible
    STATUS  mandatory
    DESCRIPTION
           "Entries in this table are created only by the agent. One
            entry exists for each modem managed by the agent."
-- AUGMENTS { rlanMdmIDEntry } 
    ::= { rlanMdmStatsTable  1 }

RlanMdmStatsEntry ::=
    SEQUENCE {
        rMdmStatsRetrains
            Counter,

        rMdmStatsSentOctets
            Counter,

        rMdmStatsReceivedOctets
            Counter,

        rMdmStatsSentDataFrames
            Counter,

        rMdmStatsReceivedDataFrames
            Counter,

        rMdmStatsResentFrames
            Counter,

        rMdmStatsErrorFrames
            Counter,

        rMdmStatsDisconnectCause
            INTEGER,

        rMdmStatsControlList
            INTEGER,

        rMdmStatsReceiveLevel
            INTEGER,

        rMdmStatsTransmitLevel
            INTEGER,

	rMdmStatsSignalToNoiseRatio
	    INTEGER,

	rMdmStatsSpeedChanges
	    INTEGER
   }

rMdmStatsRetrains OBJECT-TYPE
    SYNTAX  Counter
    ACCESS  read-only
    STATUS  mandatory
    DESCRIPTION
           "The number of retrains experienced on connections on this
            line."
    ::= { rlanMdmStatsEntry  1 }

rMdmStatsSentOctets OBJECT-TYPE
    SYNTAX  Counter
    ACCESS  read-only
    STATUS  mandatory
    DESCRIPTION
           "The number of octets presented to the modem by the DTE."
    ::= { rlanMdmStatsEntry  2 }

rMdmStatsReceivedOctets OBJECT-TYPE
    SYNTAX  Counter
    ACCESS  read-only
    STATUS  mandatory
    DESCRIPTION
           "The number of octets presented to the DTE by the modem."
    ::= { rlanMdmStatsEntry  3 }

rMdmStatsSentDataFrames OBJECT-TYPE
    SYNTAX  Counter
    ACCESS  read-only
    STATUS  mandatory
    DESCRIPTION
           "The number of data frames sent on the line interface.  If
            there is no frame-oriented protocol in use on the line
            interface, this counter shall not increment."
    ::= { rlanMdmStatsEntry  4 }

rMdmStatsReceivedDataFrames OBJECT-TYPE
    SYNTAX  Counter
    ACCESS  read-only
    STATUS  mandatory
    DESCRIPTION
           "The number of data frames received on the line interface.
            If there is no frame-oriented protocol in use on the line
            interface, this counter shall not increment."
    ::= { rlanMdmStatsEntry  5 }

rMdmStatsResentFrames OBJECT-TYPE
    SYNTAX  Counter
    ACCESS  read-only
    STATUS  mandatory
    DESCRIPTION
           "The number of times this modem retransmits frames on the
            line interface.  If there is no frame-oriented protocol in
            use on the line interface, this counter shall not
            increment."
    ::= {rlanMdmStatsEntry  6 }

rMdmStatsErrorFrames OBJECT-TYPE
    SYNTAX  Counter
    ACCESS  read-only
    STATUS  mandatory
    DESCRIPTION
           "The number of block errors received on the link.  If there
            is no frame-oriented protocol in use on the line interface,
            this counter shall not increment."
    ::= { rlanMdmStatsEntry  7 }

rMdmStatsDisconnectCause OBJECT-TYPE
    SYNTAX  INTEGER {
                 lostCarrier(1),
                 noCarrier(2),
                 noDialtone(3),
                 busy(4),
                 reserved(5),
                 reserved(6),
                 watchdogTimeout(7),
                 dtrDrop(9),
                 userHangup(10),
                 compressionProblem(12),
                 retrainFailure(13),
                 remoteLinkDisconnect(14),
                 abort(15),
                 terminateLostCarrier(16),
                 reserved(17),
                 inactivityTimeout(18),
                 dialStringError(19),
                 autoLogonError(20),
                 ccpNotSeen(21),
                 reserved(22),
                 reserved(24),
                 linkFailure(25),
                 callbackFailed(26),
                 modulationError(27),
                 dialTimeout(28),
                 remoteHangup(30),
                 reserved(31),
                 blacklist(32),
                 lastMicrocomDiscReason(33),
                 timeoutAtConnectTime(128),
                 normalImpDisconnect(129),
                 mdmResourceUnavailable(130),
                 mdmResourceCommitted(131),
                 mdmResourceError(132),
                 lastMdmResultCodes(133)
              }
    ACCESS  read-only
    STATUS  mandatory
    DESCRIPTION
           "The disconnect reason of the last call."
    ::= { rlanMdmStatsEntry  8 }

rMdmStatsControlList OBJECT-TYPE
     SYNTAX  INTEGER
     ACCESS  read-only
     STATUS  mandatory
     DESCRIPTION
             "Tells you the control signal state at the interface, which is bit-
             mapped as follows:
                     Bit    
                     ---   
                      0      RTS
                      1      DTR
                      2      CTS
                      3      DCD
                      4      DSR
                      5      TXDATA 
                      6      RXDATA
                      7      OFFHOOK
                      8      SYNCINDICATION
                      9      MODEMRESET
                      10     RINGINDICATE
             NOTE:  Bit zero (0) is the least significant bit."
    ::= { rlanMdmStatsEntry  9 }

rMdmStatsReceiveLevel OBJECT-TYPE
    SYNTAX  INTEGER
    ACCESS  read-only
    STATUS  mandatory
    DESCRIPTION
           "Received analog dBm level on the modem line." 
	   
   ::= { rlanMdmStatsEntry  10 }

rMdmStatsTransmitLevel OBJECT-TYPE
    SYNTAX  INTEGER
    ACCESS  read-only
    STATUS  mandatory
    DESCRIPTION
           "Transmitted analog dBm level on the modem line."
    ::= { rlanMdmStatsEntry  11 }

rMdmStatsSignalToNoiseRatio OBJECT-TYPE
    SYNTAX  INTEGER
    ACCESS  read-only
    STATUS  mandatory
    DESCRIPTION
           "The signal to noise ration of the modem."
    ::= { rlanMdmStatsEntry  12 }

rMdmStatsSpeedChanges OBJECT-TYPE
    SYNTAX  INTEGER
    ACCESS  read-only
    STATUS  mandatory
    DESCRIPTION
           "The number of speed changes."
    ::= { rlanMdmStatsEntry  13 }


rlanMdmACCMTable OBJECT-TYPE
    SYNTAX  SEQUENCE OF RlanMdmACCMEntry
    ACCESS  not-accessible
    STATUS  mandatory
    DESCRIPTION
           "The ACC Mask table."
    ::= { rlanModemGroup 10 }

rlanMdmACCMEntry OBJECT-TYPE
    SYNTAX  RlanMdmACCMEntry
    ACCESS  not-accessible
    STATUS  mandatory
    DESCRIPTION
           "Entries in this table are created only by the agent. One
            entry exists for each modem managed by the agent."
-- AUGMENTS { rlanMdmACCMEntry } 
    ::= { rlanMdmACCMTable  1 }

RlanMdmACCMEntry ::=
    SEQUENCE {
        rMdmACCMRx DisplayString,
        rMdmACCMTx DisplayString    
    }

rMdmACCMRx OBJECT-TYPE
    SYNTAX  DisplayString (SIZE(1..12))
    ACCESS  read-only
    STATUS  mandatory
    DESCRIPTION
           "ACCM Received."
    ::= { rlanMdmACCMEntry  1 }

rMdmACCMTx OBJECT-TYPE
    SYNTAX  DisplayString (SIZE(1..12))
    ACCESS  read-only
    STATUS  mandatory
    DESCRIPTION
	   "ACCM Transmitted."
    ::= { rlanMdmACCMEntry  2 }


--
-- PPP Group Definition
--


rPppNegotiateFirst OBJECT-TYPE
    SYNTAX  INTEGER {
                 chap(1),
                 pap(2)
               }
    ACCESS  read-write
    STATUS  mandatory
    DESCRIPTION
           "This attribute defines which PPP authentication protocol
	    is negotiated first on incoming call.
	    DEFAULT = chap"
    DEFVAL { chap }
    ::= { rlanPppGroup 1 }


rPppDynamicIPAddr OBJECT-TYPE
     SYNTAX  IpAddress
     ACCESS  read-write
     STATUS  mandatory
     DESCRIPTION
	     "This attribute defines the start address 
	     of the dynamic addres pool."
      ::= { rlanPppGroup 2 }


rPppNumDynamicIPAddr OBJECT-TYPE
     SYNTAX  INTEGER (1..150)
     ACCESS  read-write
     STATUS  mandatory
     DESCRIPTION
	     "This attribute defines the number of 
	     dynamic IP addresses in the pool."
     DEFVAL { 0 }
     ::= { rlanPppGroup 3 }


rPppDynamicIPAdrrHoldoff OBJECT-TYPE
     SYNTAX  INTEGER (1..300)
     ACCESS  read-write
     STATUS  mandatory
     DESCRIPTION
	     "This attribute defines the time in seconds befor 
	     the same IP address can be reused after a call 
	     has been disconnected."
     DEFVAL { 120 }
     ::= { rlanPppGroup 4 }

rPppDNSServerIPAddr OBJECT-TYPE
     SYNTAX  IpAddress
     ACCESS  read-write
     STATUS  mandatory
     DESCRIPTION
	     "This attribute defines the DNS server IP address of 
	     your Network."
      ::= { rlanPppGroup 5 }

rPppRemDNSIPAddrHandling OBJECT-TYPE
    SYNTAX  INTEGER {
                 accept(1),
                 override(2),
		 overridewith(3)
            }
    ACCESS  read-write
    STATUS  mandatory
    DESCRIPTION
           "This attribute determines wether the system can accept 
	   or override the DNS IP address submitted by 
	   a remote system. DEFAULT = accept.
	   Override has been superceded by overridewith."
    DEFVAL { accept }
    ::= { rlanPppGroup 6 }

rPppSecondaryDNSServerIPAddr OBJECT-TYPE
     SYNTAX  IpAddress
     ACCESS  read-write
     STATUS  mandatory
     DESCRIPTION
             "This attribute defines the Secondary DNS server IP address of
             your Network."
      ::= { rlanPppGroup 7 }
 
rPppPrimaryWINSServerIPAddr OBJECT-TYPE
     SYNTAX  IpAddress
     ACCESS  read-write
     STATUS  mandatory
     DESCRIPTION
             "This attribute defines the Primary WINS server IP address of
             your Network."
      ::= { rlanPppGroup 8 }
 
rPppSecondaryWINSServerIPAddr OBJECT-TYPE
     SYNTAX  IpAddress
     ACCESS  read-write
     STATUS  mandatory
     DESCRIPTION
             "This attribute defines the Secondary WINS server IP address of
             your Network."
      ::= { rlanPppGroup 9 }
 

--
-- Remote Extension Group Definition
--

rRemExtIDUnused OBJECT-TYPE
     SYNTAX  INTEGER (0..512)
     ACCESS  read-only
     STATUS  mandatory
     DESCRIPTION
	     "This object is used to identify a potentially unused index
	     to be used as the rRemExtID when creating new entries in the 
	     rlanRemExtConfigTable. A returned value of zero indicates that
	     the table is full."
     ::= { rlanRemExtGroup 1 }


rlanRemExtConfigTable OBJECT-TYPE
     SYNTAX  SEQUENCE OF RlanRemExtConfigEntry
     ACCESS  not-accessible
     STATUS  mandatory
     DESCRIPTION
	     "This table provides a management view of the
	     system configuration specific to individual Remote 
	     Extensions."
     ::= { rlanRemExtGroup 2 }


rlanRemExtConfigEntry OBJECT-TYPE
     SYNTAX  RlanRemExtConfigEntry
     ACCESS  not-accessible
     STATUS  mandatory
     DESCRIPTION
	     "The conceptual row at instance zero is used by the
	     Xpressway/XpressStack as the default remote Extension
	     configuration. This entry is also used to change the defaults 
	     chosen when manually configuring a new remote Extension
	     either through the embedded console or via SNMP."
     INDEX { rRemExtID }
     ::= { rlanRemExtConfigTable 1 }

RlanRemExtConfigEntry ::=
     SEQUENCE {
	 rRemExtID                     INTEGER,
	 rRemExtName                   DisplayString,
	 rRemExtPbxExtension           DisplayString,
	 rRemExtAdminState             INTEGER,
	 rRemExtPasswdAdminState       INTEGER,
	 rRemExtPasswd                 DisplayString,
	 rRemExtIdleDisconnectTimer    INTEGER,
	 rRemExtTimeOfDayProfileId     INTEGER,
	 rRemExtConnectedToCard        INTEGER,
	 rRemExtConnectedToModule      INTEGER,
	 rRemExtConnectedToChannel     INTEGER,
	 rRemExtPhoneEndPhNumber       DisplayString,
	 rRemExtSwitchEndPhNumber      DisplayString,
	 rRemExtDialPrefix             INTEGER,
	 rRemExtChannelGroup           INTEGER,
	 rRemExtCLID                   DisplayString,
	 rRemExtMakeSetBusyAdminState  INTEGER,
	 rRemExtMakeSetBusyKey	       DisplayString,
	 rRemExtLogoutSequence	       DisplayString,
	 rRemExtCallProcessing	       INTEGER,
	 rRemExtStatus                 RowStatus,
	 rRemExtCallForce              INTEGER,
	 rRemExtLineKey		       OCTET STRING,
	 rRemExtRxGain		       INTEGER,
	 rRemExtTxGain		       INTEGER,
	 rRemExtPbxInterface           INTEGER,
	 rRemExtOutgoingBearer	       INTEGER,
	 rRemExtDivertImmediate        DisplayString,
	 rRemExtDivertBusy	       DisplayString,
	 rRemExtDivertNoAnswer	       DisplayString,
	 rRemExtOfficeExtension        DisplayString
     }


rRemExtID OBJECT-TYPE
     SYNTAX  INTEGER (0..512)
     ACCESS  read-only
     STATUS  mandatory
     DESCRIPTION
	     "Tells you the index of this remote Extension. A value of 
	     0 indicates the default remote-Extension configuration; 
	     that is, this entry is used to determine the default 
	     parameters for remote Extensions"
     ::= { rlanRemExtConfigEntry 1 }

rRemExtName OBJECT-TYPE
     SYNTAX  DisplayString (SIZE(1..16))
     ACCESS  read-write
     STATUS  mandatory
     DESCRIPTION
	     "Enter the name of the current remote Extension. The name 
	     can use up to 16 characters but cannot contain spaces.
	     The combination of name and pbx extension number must 
	     be unique. The default entry (instance zero) cannot be modified."
     ::= { rlanRemExtConfigEntry 2 }

rRemExtPbxExtension OBJECT-TYPE
     SYNTAX  DisplayString (SIZE(1..8))
     ACCESS  read-write
     STATUS  mandatory
     DESCRIPTION
	     "The numeric extension of this remote extension, 
	     1 to 8 digits. Must be defined.
	     The combination of name and pbx extension number must 
	     be unique. The default entry (instance zero) cannot be modified."

     ::= { rlanRemExtConfigEntry 3 }

rRemExtAdminState OBJECT-TYPE
     SYNTAX  INTEGER {
		disabled(1),
		enabled(2)
	     }
     ACCESS  read-write
     STATUS  mandatory
     DESCRIPTION
	     "The current administrative state of the remote Extension."
     ::= { rlanRemExtConfigEntry 4 }

rRemExtPasswdAdminState OBJECT-TYPE
     SYNTAX  INTEGER {
		disabled(1),
		enabled(2)
	     }
     ACCESS  read-write
     STATUS  mandatory
     DESCRIPTION
	     "The current Administrative state of the remote 
	     Extension's password."
     ::= { rlanRemExtConfigEntry 5 }

rRemExtPasswd OBJECT-TYPE
     SYNTAX  DisplayString (SIZE(0..16))
     ACCESS  read-write
     STATUS  mandatory
     DESCRIPTION
	     "The remote Extension password. Must be a numeric
	     string and must be defined if password admin state
	     is enabled"
     ::= { rlanRemExtConfigEntry 6 }

rRemExtIdleDisconnectTimer OBJECT-TYPE
     SYNTAX  INTEGER (5..300)
     ACCESS  read-write
     STATUS  mandatory
     DESCRIPTION
	     "The time in seconds in which the call will
	     be disconnected when idle. Valid values are
	     5 to 300."
     ::= { rlanRemExtConfigEntry 7 }

rRemExtTimeOfDayProfileId OBJECT-TYPE
     SYNTAX  INTEGER (1..64)
     ACCESS  read-write
     STATUS  mandatory
     DESCRIPTION
	     "The id of the remote extensions Time Of Day profile"
     ::= { rlanRemExtConfigEntry 8 }


rRemExtConnectedToCard OBJECT-TYPE
     SYNTAX  INTEGER (1..4)
     ACCESS  read-write
     STATUS  mandatory
     DESCRIPTION
	     "The VIM card that this extension is connected to.
	      In the case of a 5232, use 1 for this field."	     
     ::= { rlanRemExtConfigEntry 9 }

rRemExtConnectedToModule OBJECT-TYPE
     SYNTAX  INTEGER (1..5)
     ACCESS  read-write
     STATUS  mandatory
     DESCRIPTION
	     "The module that this extension is connected to.
	     In the case of a 5232, use 1 for this field."
     ::= { rlanRemExtConfigEntry 10 }

rRemExtConnectedToChannel OBJECT-TYPE
     SYNTAX  INTEGER (1..6)
     ACCESS  read-write
     STATUS  mandatory
     DESCRIPTION
	     "The channel of the module that this extension 
	     is connected to.
	     In the case of a 5232, use 1 for this field."
     ::= { rlanRemExtConfigEntry 11 }


rRemExtPhoneEndPhNumber OBJECT-TYPE
     SYNTAX  DisplayString (SIZE(0..16))
     ACCESS  read-write
     STATUS  mandatory
     DESCRIPTION
	     "The phone number at the phone end of this
	     PBX extender call.
	     The first character of this field can be
	     L(ocal), N(ational), or I(nternational)."
     ::= { rlanRemExtConfigEntry 12 }

rRemExtSwitchEndPhNumber OBJECT-TYPE
     SYNTAX  DisplayString (SIZE(0..16))
     ACCESS  read-write
     STATUS  mandatory
     DESCRIPTION
	     "The phone number at the switch end of this
	     PBX extender call.
	     The first character of this field can be
	     L(ocal), N(ational), or I(nternational)."

     ::= { rlanRemExtConfigEntry 13 }


rRemExtDialPrefix OBJECT-TYPE
     SYNTAX  INTEGER (1..33)
     ACCESS  read-write
     STATUS  mandatory
     DESCRIPTION
	     "The index (1-33) of the dial prefix of this
	     remote extension. 1 means no dial prefix."
     ::= { rlanRemExtConfigEntry 14 }

rRemExtChannelGroup OBJECT-TYPE
     SYNTAX  INTEGER (1..65)
     ACCESS  read-write
     STATUS  mandatory
     DESCRIPTION
	     "The index (1-65) of the channel group of this
	     remote extension. 1 is the default group."
     ::= { rlanRemExtConfigEntry 15 }

rRemExtCLID OBJECT-TYPE
     SYNTAX  DisplayString (SIZE(1..16))
     ACCESS  read-write
     STATUS  mandatory
     DESCRIPTION
	     "The calling line ID of the remote unit. When
	     CLID security is enabled, the CLID must 
	     match the number here for the call to be
	     accepted."
     ::= { rlanRemExtConfigEntry 16 }

rRemExtMakeSetBusyAdminState OBJECT-TYPE
     SYNTAX  INTEGER {
		disabled(1),
		enabled(2)
	     }

     ACCESS  read-write
     STATUS  mandatory
     DESCRIPTION
	     "The administrative state of the MakeSetBusy
	     function."
     ::= { rlanRemExtConfigEntry 17 }

rRemExtMakeSetBusyKey OBJECT-TYPE
     SYNTAX  DisplayString (SIZE(1))
     ACCESS  read-write
     STATUS  mandatory
     DESCRIPTION
	     "The key value that activates the
	     MakeSetBusy function"
     ::= { rlanRemExtConfigEntry 18 }

rRemExtLogoutSequence OBJECT-TYPE
     SYNTAX  DisplayString (SIZE(0..16))
     ACCESS  read-write
     STATUS  mandatory
     DESCRIPTION
	     "The numeric logout sequence."
     ::= { rlanRemExtConfigEntry 19 }

rRemExtCallProcessing OBJECT-TYPE
     SYNTAX  INTEGER {
		lamp(2),
		ring(3),
	        voice(4)
	     }

     ACCESS  read-write
     STATUS  mandatory
     DESCRIPTION
	     "The call processing type associated with 
	     this remote extension."
     ::= { rlanRemExtConfigEntry 20 }


rRemExtStatus OBJECT-TYPE
     SYNTAX  RowStatus
     ACCESS  read-write
     STATUS  mandatory
     DESCRIPTION
	     "The current status of this remote 
	     extension entry."
     ::= { rlanRemExtConfigEntry 21 }


rRemExtCallForce OBJECT-TYPE
     SYNTAX  INTEGER {
		  connect(1),
		  disconnect(2),
		  statusQuo(3)
	     }
     ACCESS  read-write
     STATUS  mandatory
     DESCRIPTION
	     "To tell the system to disconnect this remote Extension,
	     select disconnect from the list of available options.
	     When you select connect, the system will try to
	     connect to the remote Extension on an available channel 
             as specified in the rlanDestAddressConfigTable selection
	     parameters (i.e., channel group)
	     DEFAULT = statusQuo."
     DEFVAL { statusQuo }
     ::= { rlanRemExtConfigEntry 22 }

rRemExtLineKey OBJECT-TYPE
    SYNTAX  OCTET STRING (SIZE(8))
    ACCESS  read-write
    STATUS  mandatory
    DESCRIPTION
	    "The mask representing the line keys to use."
    ::= { rlanRemExtConfigEntry 23 }

rRemExtRxGain OBJECT-TYPE
     SYNTAX  INTEGER (1..17)
     ACCESS  read-write
     STATUS  mandatory
     DESCRIPTION
	     "The attenuation or gain of the recieved
	      PBX signal. This value is stored in the
	      database as -7 to 9. It is represented
	      in this MIB as 1 to 17."
     ::= { rlanRemExtConfigEntry 24 }

rRemExtTxGain OBJECT-TYPE
     SYNTAX  INTEGER (1..17)
     ACCESS  read-write
     STATUS  mandatory
     DESCRIPTION
	     "The attenuation or gain of the transmitted
	      PBX signal. This value is stored in the
	      database as -9 to 7. It is represented
	      in this MIB as 1 to 17."
     ::= { rlanRemExtConfigEntry 25 }

rRemExtPbxInterface OBJECT-TYPE
     SYNTAX  INTEGER {
		  vrm(1),
		  dpnss(2)
	     }
     ACCESS  read-write
     STATUS  mandatory
     DESCRIPTION
	     "Select the type of PBX connection used for this remote 
	      extension
	     DEFAULT = vrm."
     DEFVAL { vrm }
     ::= { rlanRemExtConfigEntry 26 }

rRemExtOutgoingBearer OBJECT-TYPE
     SYNTAX  INTEGER {
		  kbps64Unrestrict(1),
		  kbps56Dig(2)
	     }
     ACCESS  read-write
     STATUS  mandatory
     DESCRIPTION
	     "Select the type of bearer to use for outgoing calls to this
	      remote extension.
	     DEFAULT = kbps64Unrestrict."
     DEFVAL { kbps64Unrestrict }
     ::= { rlanRemExtConfigEntry 27 }

rRemExtDivertImmediate OBJECT-TYPE
     SYNTAX  DisplayString (SIZE(1..16))
     ACCESS  read-write
     STATUS  mandatory
     DESCRIPTION
	     "The phone number to divert all calls intended for this 
 	      extension to. For normal operation, leave this entry blank.
	      This entry can be modified from the remote extension using
	      a 'star' sequence."
     ::= { rlanRemExtConfigEntry 28 }

rRemExtDivertBusy OBJECT-TYPE
     SYNTAX  DisplayString (SIZE(1..16))
     ACCESS  read-write
     STATUS  mandatory
     DESCRIPTION
	     "The phone number to divert all calls intended for this 
 	      extension to, whilst the extension is busy. Leave this 
	      entry blank to disable this facility. This entry can be 
	      modified from the remote extension using a 'star' 
	      sequence."
     ::= { rlanRemExtConfigEntry 29 }

rRemExtDivertNoAnswer OBJECT-TYPE
     SYNTAX  DisplayString (SIZE(1..16))
     ACCESS  read-write
     STATUS  mandatory
     DESCRIPTION
	     "The phone number to divert all calls intended for this 
 	      extension to, if there is no answer from this extension. 
	      Leave this entry blank to disable this facility. This 
	      entry can be modified from the remote extension using a 
	      'star' sequence."
     ::= { rlanRemExtConfigEntry 30 }

rRemExtOfficeExtension OBJECT-TYPE
     SYNTAX  DisplayString (SIZE(1..16))
     ACCESS  read-write
     STATUS  mandatory
     DESCRIPTION
	     "If the home-worker also has an office extension number, it 
	      should be entered here. Certain facilities are aonly available
	      to this extension for security purposes."
     ::= { rlanRemExtConfigEntry 31 }

--
--     Remote Extension Statistics Table
--

rlanRemExtStatsTable OBJECT-TYPE
     SYNTAX  SEQUENCE OF RlanRemExtStatsEntry
     ACCESS  not-accessible
     STATUS  mandatory
     DESCRIPTION
	     "This table provides a management view of the
	     system configuration specific to individual Remote 
	     Extensions."
     ::= { rlanRemExtGroup 3 }


rlanRemExtStatsEntry OBJECT-TYPE
     SYNTAX  RlanRemExtStatsEntry
     ACCESS  not-accessible
     STATUS  mandatory
     INDEX { rRemExtID }
     ::= { rlanRemExtStatsTable 1 }


RlanRemExtStatsEntry ::=
     SEQUENCE {
	 rRemExtVoiceModule            INTEGER,
	 rRemExtIsdnChan               INTEGER,
	 rRemExtTotalTime              TimeTicks,
	 rRemExtLastTime               TimeTicks,
	 rRemExtCallDuration	       TimeTicks,
	 rRemExtLastFail	       INTEGER,
	 rRemExtWANStatsIndex	       INTEGER
     }


rRemExtVoiceModule OBJECT-TYPE
     SYNTAX  INTEGER
     ACCESS  read-only
     STATUS  mandatory
     DESCRIPTION
	     "Tells you the channel index of the Voice 
	      module in use."
     ::= { rlanRemExtStatsEntry 1 }

rRemExtIsdnChan OBJECT-TYPE
     SYNTAX  INTEGER
     ACCESS  read-only
     STATUS  mandatory
     DESCRIPTION
	     "Tells you the channel index of the ISDN
	      channel used."
     ::= { rlanRemExtStatsEntry 2 }

rRemExtTotalTime OBJECT-TYPE
     SYNTAX  TimeTicks
     ACCESS  read-only
     STATUS  mandatory
     DESCRIPTION
	     "Tells you the total number of TimeTicks that have
	     elapsed while this remote extension has been connected. 
	     This value resets when the RLAN resets. Returns a 0 if 
	     a connection has yet to be made." 
     ::= { rlanRemExtStatsEntry 3 }

rRemExtLastTime OBJECT-TYPE
     SYNTAX  TimeTicks
     ACCESS  read-only
     STATUS  mandatory
     DESCRIPTION
	     "Tells you the time in TimeTicks of the last 
	     connection to this remote extension. Returns 
	     a 0 if a connection has yet to be made." 
     ::= { rlanRemExtStatsEntry 4 }

rRemExtCallDuration OBJECT-TYPE
     SYNTAX  TimeTicks
     ACCESS  read-only
     STATUS  mandatory
     DESCRIPTION
	     "Tells you the number of TimeTicks that have
	     elapsed since this connection has been 
	     established. This value resets every time the remote 
	     extention reconnects. Returns a 0 if a connection 
	     has yet to be made." 
     ::= { rlanRemExtStatsEntry 5 }

rRemExtLastFail OBJECT-TYPE
     SYNTAX  INTEGER
     ACCESS  read-only
     STATUS  mandatory
     DESCRIPTION
	     "Tells you the last calls failure code."
     ::= { rlanRemExtStatsEntry 6 }

rRemExtWANStatsIndex OBJECT-TYPE
     SYNTAX  INTEGER
     ACCESS  read-only
     STATUS  mandatory
     DESCRIPTION
	     "This indicates active entry in the 
	      rlanWANStatsTable entries. 0 indicates that
	     this remote LAN is currently not active (up)."
     ::= { rlanRemExtStatsEntry 7 }

--
-- Remote TimeOfDay Group Definition
--

rTimeOfDayIDUnused OBJECT-TYPE
     SYNTAX  INTEGER (0..64)
     ACCESS  read-only
     STATUS  mandatory
     DESCRIPTION
	     "This object is used to identify a potentially 
	     unused index to be used as the rRemTimeOfDayID 
	     when creating new entries in the rlanRemTimeOfDayTable. 
	     A returned value of zero indicates that the table is full."
     ::= { rlanTimeOfDayGroup 1 }


rlanTimeOfDayProfileTable OBJECT-TYPE
     SYNTAX  SEQUENCE OF RlanTimeOfDayEntry
     ACCESS  not-accessible
     STATUS  mandatory
     DESCRIPTION
	     "This table provides a management view of the
	     system configuration specific to individual Time Of
	     day entries."
     ::= { rlanTimeOfDayGroup 2 }


rlanTimeOfDayProfileEntry OBJECT-TYPE
     SYNTAX  RlanTimeOfDayProfileEntry
     ACCESS  not-accessible
     STATUS  mandatory
     DESCRIPTION
	     "Partial entry"
     INDEX { rTimeOfDayProfileID }
     ::= { rlanTimeOfDayProfileTable 1 }

RlanTimeOfDayProfileEntry ::=
     SEQUENCE {
	 rTimeOfDayProfileID           INTEGER,
	 rTimeOfDayProfileName         DisplayString,
	 rTimeOfDayProfileStatus       RowStatus
     }


rTimeOfDayProfileID OBJECT-TYPE
     SYNTAX  INTEGER (1..64)
     ACCESS  read-only
     STATUS  mandatory
     DESCRIPTION
	     "Tells you the index of this Time Of Day entry."
     ::= { rlanTimeOfDayProfileEntry 1 }

rTimeOfDayProfileName OBJECT-TYPE
     SYNTAX  DisplayString (SIZE(0..16))
     ACCESS  read-write
     STATUS  mandatory
     DESCRIPTION
	     "Tells you the name of this Time Of Day entry.
	     No whitespace and must be unique.
	     Must be defined."
     ::= { rlanTimeOfDayProfileEntry 2 }

rTimeOfDayProfileStatus OBJECT-TYPE
     SYNTAX  RowStatus
     ACCESS  read-write
     STATUS  mandatory
     DESCRIPTION
	     "The current status of this remote 
	     extension entry."
     ::= { rlanTimeOfDayProfileEntry 3 }


rlanTimeOfDayEntryTable OBJECT-TYPE
     SYNTAX  SEQUENCE OF RlanTimeOfDayEntry
     ACCESS  not-accessible
     STATUS  mandatory
     DESCRIPTION
	     "This table provides a management view of the
	     system configuration specific to individual Time Of
	     day profile entries."
     ::= { rlanTimeOfDayGroup 3 }


rlanTimeOfDayEntry OBJECT-TYPE
     SYNTAX  RlanTimeOfDayEntry
     ACCESS  not-accessible
     STATUS  mandatory
     DESCRIPTION
	     "Partial entry"
     INDEX { rTimeOfDayProfileID, rTimeOfDayEntryID }
     ::= { rlanTimeOfDayEntryTable 1 }

RlanTimeOfDayEntry ::=
     SEQUENCE {
	 rTimeOfDayEntryID             INTEGER,
	 rTimeOfDayEntryStart          INTEGER,
	 rTimeOfDayEntryEnd            INTEGER,
	 rTimeOfDayEntryIdleDisconnect INTEGER,
	 rTimeOfDayEntryExclusive      INTEGER
     }


rTimeOfDayEntryID OBJECT-TYPE
     SYNTAX  INTEGER (1..10)
     ACCESS  read-only
     STATUS  mandatory
     DESCRIPTION
	     "Tells you the index of this Time Of Day profile entry."
     ::= { rlanTimeOfDayEntry 1 }

rTimeOfDayEntryStart OBJECT-TYPE
     SYNTAX  INTEGER (0..10079)
     ACCESS  read-write
     STATUS  mandatory
     DESCRIPTION
	     "The start time of this TOD profile entry. The format
	     is an unsigned long taken from the number of minutes
	     from Sunday Midnight. For example, if the start time
	     is Monday at 06:00 this value would be 360. This
	     value must be less than rTimeOfDayProfileEnd and
	     larger than the end time of the previous entry"
     ::= { rlanTimeOfDayEntry 2 }

rTimeOfDayEntryEnd OBJECT-TYPE
     SYNTAX  INTEGER (0..10079)
     ACCESS  read-write
     STATUS  mandatory
     DESCRIPTION
	     "The end time of this TOD profile entry. The format
	     is an unsigned long taken from the number of minutes
	     from Sunday Midnight. For example, if the start time
	     is Monday at 06:01 this value would be 361. This
	     value must be greater than rTimeOfDayProfileStart and
	     smaller than the start time of the next entry."
     ::= { rlanTimeOfDayEntry 3 }

rTimeOfDayEntryIdleDisconnect OBJECT-TYPE
     SYNTAX  INTEGER  {
		disabled(1),
		enabled(2)
	     }
     ACCESS  read-write
     STATUS  mandatory
     DESCRIPTION
	     "Is idle disconnect enabled or disabled during this
	     time span."
     ::= { rlanTimeOfDayEntry 4 }

rTimeOfDayEntryExclusive OBJECT-TYPE
     SYNTAX  INTEGER  {
		disabled(1),
		enabled(2)
	     }
     ACCESS  read-write
     STATUS  mandatory
     DESCRIPTION
	     "Is exclusive enabled or disabled during this
	     time span. That is, are other phones allowed to 
	     connect."
     ::= { rlanTimeOfDayEntry 5 }


--
-- DPNSS B-Channel Group
--

rlanDpnssBchConfigTable OBJECT-TYPE
     SYNTAX  SEQUENCE OF RlanDpnssBchConfigEntry
     ACCESS  not-accessible
     STATUS  mandatory
     DESCRIPTION
	     "This table provides a management view of the
	     B-Channel configuration items specific to DPNSS links."
     ::= { rlanDpnssBchGroup 1 }


rlanDpnssBchConfigEntry OBJECT-TYPE
     SYNTAX  RlanDpnssBchConfigEntry
     ACCESS  not-accessible
     STATUS  mandatory
     DESCRIPTION
	     "Entry defining DPNSS specific B-channel attributes."
     INDEX { rDpnssBchCardID, rDpnssBchPortID, rDpnssBchChanID }
     ::= { rlanDpnssBchConfigTable 1 }

RlanDpnssBchConfigEntry ::=
     SEQUENCE {
     	 rDpnssBchCardID	       INTEGER,
     	 rDpnssBchPortID	       INTEGER,
     	 rDpnssBchChanID	       INTEGER,
     	 rDpnssBchRealXy	       INTEGER,
     	 rDpnssBchVirtualMode	       INTEGER,
     	 rDpnssBchVirtualXy	       INTEGER
     }


rDpnssBchCardID OBJECT-TYPE
     SYNTAX  INTEGER (1..11)
     ACCESS  read-only
     STATUS  mandatory
     DESCRIPTION
	     "The PRI card this entry is referring to"
     ::= { rlanDpnssBchConfigEntry 1 }

rDpnssBchPortID OBJECT-TYPE
     SYNTAX  INTEGER (1..2)
     ACCESS  read-only
     STATUS  mandatory
     DESCRIPTION
	     "The PRI port this entry is referring to"
     ::= { rlanDpnssBchConfigEntry 2 }

rDpnssBchChanID OBJECT-TYPE
     SYNTAX  INTEGER (1..31)
     ACCESS  read-only
     STATUS  mandatory
     DESCRIPTION
	     "The PRI B-channel this entry is referring to"
     ::= { rlanDpnssBchConfigEntry 3 }

rDpnssBchRealXy OBJECT-TYPE
     SYNTAX  INTEGER  {
		x(1),
		y(2)
	     }
     ACCESS  read-write
     STATUS  mandatory
     DESCRIPTION
	     "Select the collision handling of this B-channel. Each B-channel
	      should be set as X on one end of the link and Y on the other
	      end. If there is a call collision on this channel, the end
	      designated X will succeed, whilst the end designated Y will
	      drop back and retry on a different channel.
	      DEFAULT = x."
     DEFVAL { x }
     ::= { rlanDpnssBchConfigEntry 4 }

rDpnssBchVirtualMode OBJECT-TYPE
     SYNTAX  INTEGER  {
		disabled(1),
		enabled(2)
	     }
     ACCESS  read-write
     STATUS  mandatory
     DESCRIPTION
	     "For each B-channel on a DPNSS link there is a corresponding 
	      virtual channel, which is used to signal call-independant 
	      information through the network. Usually all of these channels
	      will be enabled, but a subset may be disabled.
	      DEFAULT = enabled."
     DEFVAL { enabled }
     ::= { rlanDpnssBchConfigEntry 5 }

rDpnssBchVirtualXy OBJECT-TYPE
     SYNTAX  INTEGER  {
		x(1),
		y(2)
	     }
     ACCESS  read-write
     STATUS  mandatory
     DESCRIPTION
	     "Select the collision handling of this Virtual B-channel. 
	      DEFAULT = x."
     DEFVAL { x }
     ::= { rlanDpnssBchConfigEntry 6 }


--
-- Incoming Call Routing Group
--

rlanIsdnDDIRoutingTable OBJECT-TYPE
     SYNTAX  SEQUENCE OF RlanIsdnDDIRoutingEntry
     ACCESS  not-accessible
     STATUS  mandatory
     DESCRIPTION
	     "This table provides a management view of the
	     ISDN Call Routing Table, used to provide incoming call
	     handling ability based on information in the ISDN Setup
	     message."
     ::= { rlanCallRoutingGroup 1 }


rlanIsdnDDIRoutingEntry OBJECT-TYPE
     SYNTAX  RlanIsdnDDIRoutingEntry
     ACCESS  not-accessible
     STATUS  mandatory
     DESCRIPTION
	     "Entry defining incoming call handling for ISDN initiated calls."
     INDEX { rIsdnDDIRtgIndex }
     ::= { rlanIsdnDDIRoutingTable 1 }

RlanIsdnDDIRoutingEntry ::=
     SEQUENCE {
     	 rIsdnDDIRtgIndex	       INTEGER,
	 rIsdnDDIRtgName	       DisplayString,
	 rIsdnDDIRtgRacLoPhnum	       DisplayString,
	 rIsdnDDIRtgRacHiPhnum	       DisplayString,
	 rIsdnDDIRtgApexPhnum	       DisplayString,
	 rIsdnDDIRtgAbsorb	       INTEGER,
	 rIsdnDDIRtgInsert	       DisplayString,
	 rIsdnDDIRtgRowStatus	       RowStatus
     }

rIsdnDDIRtgIndex OBJECT-TYPE
     SYNTAX  INTEGER (1..4)
     ACCESS  read-only
     STATUS  mandatory
     DESCRIPTION
	     "Uniquely identifies this entry"
     ::= { rlanIsdnDDIRoutingEntry 1 }

rIsdnDDIRtgName OBJECT-TYPE
     SYNTAX  DisplayString (SIZE(1..16))
     ACCESS  read-write
     STATUS  mandatory
     DESCRIPTION
	     "Tells you the name of this Routing Table entry.
	     No whitespace and must be unique.
	     Must be defined."
     ::= { rlanIsdnDDIRoutingEntry 2 }

rIsdnDDIRtgRacLoPhnum OBJECT-TYPE
     SYNTAX  DisplayString (SIZE(0..16))
     ACCESS  read-write
     STATUS  mandatory
     DESCRIPTION
	     "A range of phone numbers can be defined such that all 
	     incoming calls with a dialled number in this range are
	     presented to the RAC as data calls. The default for 
	     dialled numbers outside of this range is to route the 
	     call to the PBX. This is the lower bound of the range."
     ::= { rlanIsdnDDIRoutingEntry 3 }

rIsdnDDIRtgRacHiPhnum OBJECT-TYPE
     SYNTAX  DisplayString (SIZE(0..16))
     ACCESS  read-write
     STATUS  mandatory
     DESCRIPTION
	     "A range of phone numbers can be defined such that all 
	     incoming calls with a dialled number in this range are
	     presented to the RAC as data calls. The default for 
	     dialled numbers outside of this range is to route the 
	     call to the PBX. This is the higher bound of the range."
     ::= { rlanIsdnDDIRoutingEntry 4 }

rIsdnDDIRtgApexPhnum OBJECT-TYPE
     SYNTAX  DisplayString (SIZE(0..16))
     ACCESS  read-write
     STATUS  mandatory
     DESCRIPTION
	     "Enter the dialled number which is reserved for remote 
	     analogue extensions to call."
     ::= { rlanIsdnDDIRoutingEntry 5 }

rIsdnDDIRtgAbsorb OBJECT-TYPE
     SYNTAX  INTEGER (0..16)
     ACCESS  read-write
     STATUS  mandatory
     DESCRIPTION
	     "For calls which are passed on to the PBX, a simple number 
	     mapping algorithm can be performed on the dialled number to
	     accomodate the PBXs numbering plan. Enter the number of 
	     digits to absorb from the front of the dialled number."
     ::= { rlanIsdnDDIRoutingEntry 6 }

rIsdnDDIRtgInsert OBJECT-TYPE
     SYNTAX  DisplayString (SIZE(0..16))
     ACCESS  read-write
     STATUS  mandatory
     DESCRIPTION
	     "For calls which are passed on to the PBX, a simple number 
	     mapping algorithm can be performed on the dialled number to
	     accomodate the PBXs numbering plan. Enter a digit string to
	     insert at the front of the dialled number."
     ::= { rlanIsdnDDIRoutingEntry 7 }

rIsdnDDIRtgRowStatus OBJECT-TYPE
     SYNTAX  RowStatus
     ACCESS  read-write
     STATUS  mandatory
     DESCRIPTION
	     "The current status of this routing table entry."
     ::= { rlanIsdnDDIRoutingEntry 8 }


rlanPbxCallRoutingTable OBJECT-TYPE
     SYNTAX  SEQUENCE OF RlanPbxCallRoutingEntry
     ACCESS  not-accessible
     STATUS  mandatory
     DESCRIPTION
	     "This table provides a management view of the
	     PBX Call Routing Table, used to provide incoming call
	     handling ability based on information Initial Service
	     Request Message (ISRM) from the PBX."
     ::= { rlanCallRoutingGroup 2 }


rlanPbxCallRoutingEntry OBJECT-TYPE
     SYNTAX  RlanPbxCallRoutingEntry
     ACCESS  not-accessible
     STATUS  mandatory
     DESCRIPTION
	     "Entry defining incoming call handling for PBX initiated calls."
     INDEX { rPbxCallRtgIndex }
     ::= { rlanPbxCallRoutingTable 1 }

RlanPbxCallRoutingEntry ::=
     SEQUENCE {
     	 rPbxCallRtgIndex	       INTEGER,
	 rPbxCallRtgName	       DisplayString,
	 rPbxCallRtgGwayPhnum	       DisplayString,
	 rPbxCallRtgGwayAbsorb	       INTEGER,
	 rPbxCallRtgRacExtLo	       DisplayString,
	 rPbxCallRtgRacExtHi	       DisplayString,
	 rPbxCallRtgApexExtLo	       DisplayString,
	 rPbxCallRtgApexExtHi	       DisplayString,
	 rPbxCallRtgRowStatus	       RowStatus
     }

rPbxCallRtgIndex OBJECT-TYPE
     SYNTAX  INTEGER (1..4)
     ACCESS  read-only
     STATUS  mandatory
     DESCRIPTION
	     "Uniquely identifies this entry"
     ::= { rlanPbxCallRoutingEntry 1 }

rPbxCallRtgName OBJECT-TYPE
     SYNTAX  DisplayString (SIZE(1..16))
     ACCESS  read-write
     STATUS  mandatory
     DESCRIPTION
	     "Tells you the name of this Routing Table entry.
	     No whitespace and must be unique.
	     Must be defined."
     ::= { rlanPbxCallRoutingEntry 2 }

rPbxCallRtgGwayPhnum OBJECT-TYPE
     SYNTAX  DisplayString (SIZE(0..1))
     ACCESS  read-write
     STATUS  mandatory
     DESCRIPTION
	     "Calls from a PBX where the called number begins with this prefix
	     are routed directly into the ISDN, i.e. using the RLAN as an ISDN
	     gateway. Leave blank if calls from the PBX to the ISDN are not 
	     required. An asterisk may be used to indicate
	     this is the default route."
     ::= { rlanPbxCallRoutingEntry 3 }

rPbxCallRtgGwayAbsorb OBJECT-TYPE
     SYNTAX  INTEGER (0..1)
     ACCESS  read-write
     STATUS  mandatory
     DESCRIPTION
	     "When calls are routed through to the ISDN because they meet
	     the criteria above, this field indicates how many digits to 
	     discard from the front of the called number. Generally the prefix
	     used for routing is absorbed."
     ::= { rlanPbxCallRoutingEntry 4 }

rPbxCallRtgRacExtLo OBJECT-TYPE
     SYNTAX  DisplayString (SIZE(0..8))
     ACCESS  read-write
     STATUS  mandatory
     DESCRIPTION
	     "When the RLAN has a PBX connection, a range of extension
	     numbers are allocated to the RLAN. Calls received by the
	     RLAN down the PBX trunk are treated as normal data calls.
	     This is the low-entry of the range."
     ::= { rlanPbxCallRoutingEntry 5 }

rPbxCallRtgRacExtHi OBJECT-TYPE
     SYNTAX  DisplayString (SIZE(0..8))
     ACCESS  read-write
     STATUS  mandatory
     DESCRIPTION
	     "When the RLAN has a PBX connection, a range of extension
	     numbers are allocated to the RLAN. Calls received by the
	     RLAN down the PBX trunk are treated as normal data calls.
	     This is the high-entry of the range."
     ::= { rlanPbxCallRoutingEntry 6 }

rPbxCallRtgApexExtLo OBJECT-TYPE
     SYNTAX  DisplayString (SIZE(0..8))
     ACCESS  read-write
     STATUS  mandatory
     DESCRIPTION
	     "When the RLAN has a PBX connection, a range of extension
	     numbers are allocated to Remote Extensions. 
	     This is the low-entry of the range."
     ::= { rlanPbxCallRoutingEntry 7 }

rPbxCallRtgApexExtHi OBJECT-TYPE
     SYNTAX  DisplayString (SIZE(0..8))
     ACCESS  read-write
     STATUS  mandatory
     DESCRIPTION
	     "When the RLAN has a PBX connection, a range of extension
	     numbers are allocated to Remote Extensions. 
	     This is the high-entry of the range."
     ::= { rlanPbxCallRoutingEntry 8 }

rPbxCallRtgRowStatus OBJECT-TYPE
     SYNTAX  RowStatus
     ACCESS  read-write
     STATUS  mandatory
     DESCRIPTION
	     "The current status of this routing table entry."
     ::= { rlanPbxCallRoutingEntry 9 }


--
-- rlanSecurityGroup
--


--
--     Banner Configuration Table
--     

rlanSecurityBannerConfigTable OBJECT-TYPE
     SYNTAX  SEQUENCE OF RlanSecurityBannerConfigEntry
     ACCESS  not-accessible
     STATUS  mandatory
     DESCRIPTION
	     "This table provides a management view of the
	     login banner configuration parameters."
     ::= { rlanSecurityGroup 1 }


rlanSecurityBannerConfigEntry OBJECT-TYPE
     SYNTAX  RlanSecurityBannerConfigEntry
     ACCESS  not-accessible
     STATUS  mandatory
--     INDEX   {  }
     ::= { rlanSecurityBannerConfigTable 1 }


RlanSecurityBannerConfigEntry ::=
     SEQUENCE {
	 rSecBannerBanner	DisplayString,
	 rSecBannerLogin	DisplayString,
	 rSecBannerPassword	DisplayString,
	 rSecBannerAccepted	DisplayString,
	 rSecBannerDenied	DisplayString,
	 rSecBannerPart1	DisplayString,
	 rSecBannerPart2	DisplayString,
	 rSecBannerPart3	DisplayString
     }

rSecBannerBanner OBJECT-TYPE
     SYNTAX  DisplayString (SIZE(0..700))
     ACCESS  read-write
     STATUS  mandatory
     DESCRIPTION
	     "The authentication Banner String. This is the 
	      banner that users see before they login. Printable 
 	      characters must be enclosed in quotation marks, 
	      non printable characters entered in 3 digit 
	      decimal numbers, separated by commas.  Length 
	      of banner to be sent must not exceed 512 bytes."
     ::= { rlanSecurityBannerConfigEntry 1 }

rSecBannerLogin OBJECT-TYPE
     SYNTAX  DisplayString (SIZE(0..100))
     ACCESS  read-write
     STATUS  mandatory
     DESCRIPTION
	     "The authentication Login prompt. Printable 
 	      characters must be enclosed in quotation marks, 
	      non printable characters entered in 3 digit 
	      decimal numbers, separated by commas.  Length 
	      of banner to be sent must not exceed 32 bytes."
     ::= { rlanSecurityBannerConfigEntry 2 }

rSecBannerPassword OBJECT-TYPE
     SYNTAX  DisplayString (SIZE(0..100))
     ACCESS  read-write
     STATUS  mandatory
     DESCRIPTION
	     "The authentication Password prompt. Printable 
 	      characters must be enclosed in quotation marks, 
	      non printable characters entered in 3 digit 
	      decimal numbers, separated by commas.  Length 
	      of banner to be sent must not exceed 32 bytes."
     ::= { rlanSecurityBannerConfigEntry 3 }

rSecBannerAccepted OBJECT-TYPE
     SYNTAX  DisplayString (SIZE(0..100))
     ACCESS  read-write
     STATUS  mandatory
     DESCRIPTION
	     "The authentication Accepted banner. This is the
	      banner the user sees when login is successful.
	      Printable characters must be enclosed in quotation
	      marks, non printable characters entered in 3 digit 
	      decimal numbers, separated by commas.  Length 
	      of banner to be sent must not exceed 32 bytes."
     ::= { rlanSecurityBannerConfigEntry 4 }

rSecBannerDenied OBJECT-TYPE
     SYNTAX  DisplayString (SIZE(0..100))
     ACCESS  read-write
     STATUS  mandatory
     DESCRIPTION
	     "The authentication Denied banner. This is the
	      banner the user sees when login is unsuccessful.
	      Printable characters must be enclosed in quotation
	      marks, non printable characters entered in 3 digit 
	      decimal numbers, separated by commas.  Length 
	      of banner to be sent must not exceed 32 bytes."
     ::= { rlanSecurityBannerConfigEntry 5 }

rSecBannerPart1 OBJECT-TYPE
     SYNTAX  DisplayString (SIZE(0..255))
     ACCESS  read-only
     STATUS  mandatory
     DESCRIPTION
	     "The first part of the authentication Banner String. 
	      This is the banner that users see before they login. 
	      The banner is split into 3 parts to accomodate SNMP
	      implementations that cannot read strings larger than
	      256 characters. 
	      Printable characters must be enclosed in quotation 
	      marks, non printable characters entered in 3 digit 
	      decimal numbers, separated by commas.  Length 
	      of banner to be sent must not exceed 512 bytes."
     ::= { rlanSecurityBannerConfigEntry 6 }

rSecBannerPart2 OBJECT-TYPE
     SYNTAX  DisplayString (SIZE(0..255))
     ACCESS  read-only
     STATUS  mandatory
     DESCRIPTION
	     "The second part of the authentication Banner String. 
	      This is the banner that users see before they login. 
	      The banner is split into 3 parts to accomodate SNMP
	      implementations that cannot read strings larger than
	      256 characters. 
	      Printable characters must be enclosed in quotation 
	      marks, non printable characters entered in 3 digit 
	      decimal numbers, separated by commas.  Length 
	      of banner to be sent must not exceed 512 bytes."
     ::= { rlanSecurityBannerConfigEntry 7 }

rSecBannerPart3 OBJECT-TYPE
     SYNTAX  DisplayString (SIZE(0..255))
     ACCESS  read-only
     STATUS  mandatory
     DESCRIPTION
	     "The third part of the authentication Banner String. 
	      This is the banner that users see before they login. 
	      The banner is split into 3 parts to accomodate SNMP
	      implementations that cannot read strings larger than
	      256 characters. 
	      Printable characters must be enclosed in quotation 
	      marks, non printable characters entered in 3 digit 
	      decimal numbers, separated by commas.  Length 
	      of banner to be sent must not exceed 512 bytes."
     ::= { rlanSecurityBannerConfigEntry 8 }




--
-- rlanIpRoutingGroup
--


--
--     Ip Routing Config Table
--     

rlanIpRoutingConfigTable OBJECT-TYPE
     SYNTAX  SEQUENCE OF RlanIpRoutingConfigEntry
     ACCESS  not-accessible
     STATUS  mandatory
     DESCRIPTION
	     "This table provides a management view of the
	     login banner configuration parameters."
     ::= { rlanIpRoutingGroup 1 }


rlanIpRoutingConfigEntry OBJECT-TYPE
     SYNTAX  RlanIpRoutingConfigEntry
     ACCESS  not-accessible
     STATUS  mandatory
--     INDEX   {  }
     ::= { rlanIpRoutingConfigTable 1 }


RlanIpRoutingConfigEntry ::=
     SEQUENCE {
	 rIpRoutingArpProxy		INTEGER,
	 rIpRoutingRipForwarding	INTEGER,
	 rIpRoutingRipType		INTEGER
     }


rIpRoutingArpProxy OBJECT-TYPE
     SYNTAX  INTEGER  {
		 disabled(1),
		 enabled(2)
	     }
     ACCESS  read-write
     STATUS  mandatory
     DESCRIPTION
	     "Enables ARP Proxy"
     ::= { rlanIpRoutingConfigEntry 1 }

rIpRoutingRipForwarding OBJECT-TYPE
     SYNTAX  INTEGER  {
		 disabled(1),
		 enabled(2)
	     }
     ACCESS  read-write
     STATUS  mandatory
     DESCRIPTION
	     "Enables RIP Forwarding"
     ::= { rlanIpRoutingConfigEntry 2 }

rIpRoutingRipType OBJECT-TYPE
     SYNTAX  INTEGER  {
		 rip1(1),
		 rip2(2)
	     }
     ACCESS  read-write
     STATUS  mandatory
     DESCRIPTION
	     "The type of RIP Forwarding"
     ::= { rlanIpRoutingConfigEntry 3 }



--
--                     XPRESS TRAP TYPES
--
--      This section describes the trap types that the
--   system can generate.
--
--      The   SNMP    protocol   provides   a   mechanism   for
-- asynchronously notifying  management stations  of significant
-- changes in  the network.  This mechanism  is the  SNMP  trap
-- message. This section describes the general format for
-- all trap  messages generated by Gandalf's XpressWay RLAN and
-- XpressStack products.
--
--
-- Trap Formats
--
--      The  SNMP  trap  messages  are  composed  of  two  user
-- definable areas: the specific trap type and the VarBindings
-- (e.g.; the interesting information). The specific trap type is
-- an INTEGER  that is used to determine the specific trap that
-- has occurred. The interesting information contains one
-- object, the snmpTrapDescription, which consist of an OCTET
-- STRING which gives a complete description of the trap.  The
-- information will also include the card and port numbers when
-- applicable.
--
--
-- Generic Traps
--
-- The System will generate the coldStart , AuthenticationFailure
-- and enterpriseSpecific generic traps.
--
--    coldStart    trap (0)     A coldStart trap is generated when the
--                              device is restarted
--
--    athenticationFailure (4)  An authenticationFailure trap signifies
--                              that the sending protocol entity is the
--                              addressee of a protocol message that is not
--                              properly authenticated.
--
--    enterpriseSpecific (6)    trap specific to this the XpressWay RLAN or 
--                              XpressStack product
--
--
--

--
--                            Trap Description
--
-- Following are the enterpriseSpecific TRAPs supported by the RAC agent
--
-- Card Installed
--
	gCardInstalled TRAP-TYPE
	    ENTERPRISE  gandalf
	    VARIABLES   { rCardID }
	    DESCRIPTION
	    "This trap indicates that a card was physically
	     installed in the hub.  The trap will include the
	     rCardID attribute that identifies which card was
	     installed."
	    ::= 9000
--
--
-- Card Removed
--
	gCardRemoved TRAP-TYPE
	    ENTERPRISE  gandalf
	    VARIABLES   { rCardID }
	    DESCRIPTION
	    "This trap indicates that a card was physically
	     removed from the hub.  The trap will include the
	     rCardID attribute that identifies which card was
	     removed."
	    ::= 9001

--
-- Card Mismatch
--
	gCardMismatch TRAP-TYPE
	    ENTERPRISE  gandalf
	    VARIABLES   { rCardID, rCardType }
	    DESCRIPTION
	    "This trap indicates that a card was physically
	     installed in a slot configured with a different
	     card type. The rCardID attribute identifying the
	     installed card and the rCardType attribute for
	     this card are going to be included with this trap."
	    ::= 9002

--
-- Card Mismatch Cleared
--
	  gCardMismatchCleared TRAP-TYPE
	    ENTERPRISE  gandalf
	    VARIABLES   { rCardID, rCardType }
	    DESCRIPTION
	      "This trap indicates that the slot causing a Card
	       Mismatch was reconfigured with the proper card
	       type. The rCardID attribute and rCardType
	       attribute will be included with this trap."
	      ::= 9003

--
-- Card Faulty
--
	gCardFaulty TRAP-TYPE
	    ENTERPRISE  gandalf
	    VARIABLES   { rCardID }
	    DESCRIPTION
	    "This trap indicates that a card was found to be
	     faulty by the system. The rCardID
	     attribute will be included with the trap. The text
	     portion of the trap will identify the reason
	     the card was found to be faulty."
	    ::= 9004

--
-- Card Faulty Cleared
--
	  gCardFaultyCleared TRAP-TYPE
	      ENTERPRISE  gandalf
	      VARIABLES   { rCardID }
	      DESCRIPTION
	      "This trap indicates that the slot causing a Card
	       Faulty is now functional again. The rCardID
	       identifying the slot will be included with the
	       trap."
	      ::= 9005


--
-- NVRAM Fault
--
	gNvramFault TRAP-TYPE
	    ENTERPRISE  gandalf
	    DESCRIPTION
	    "This trap indicates that one of the data objects
	     stored in NVRAM failed a CRC test. This object
	     will then be reconfigured with its default
	     parameters."
	    ::= 9006

--
-- Filtering Database Full
--
       gFiltDatabaseFull TRAP-TYPE
	   ENTERPRISE  gandalf
	   DESCRIPTION
	   "This trap indicates that the number of entries in
	    the Filtering Database has reached the upper limit of the system's
	    storage capacity."
	   ::= 9007


--
-- Real Time Clock failed
--

	gRTCFault           TRAP-TYPE
	    ENTERPRISE      gandalf
	    DESCRIPTION
	    " This trap indicates that the internal tests done by the operational code
	      on the Real Time Clock failed."
	    ::= 9008


--
-- LAN interface failure
--

	gLANTestFailure     TRAP-TYPE
	    ENTERPRISE      gandalf
	    DESCRIPTION
	    " This trap indicates that the internal tests done by the operational code
	      on the LAN interface failed."
	    ::= 9009


--
--  CALLs related TRAPs
--


	gCallConnected      TRAP-TYPE
	    ENTERPRISE      gandalf
	    VARIABLES       { rWANStatsIndex,
			      rWANStatsCardID,
			      rWANStatsPortID,
			      rWANStatsChanID
			    }
	    DESCRIPTION
	    "The system just connected to remote LAN.
	     Included with this TRAP will be the rWANStatsIndex, 
	     rWANStatsCardID, rWANStatsPortID, rWANStatsChanID and 
	     rWANStatsRemLANID identifying which card, port, 
	     channel, resource module connected and remote LAN 
	     this call will use."
	    ::= 9010


	gCallDisconnected   TRAP-TYPE
	    ENTERPRISE      gandalf
	    VARIABLES       { rWANStatsIndex,
			      rWANStatsCardID,
			      rWANStatsPortID,
			      rWANStatsChanID
			    }
	     DESCRIPTION
	    "The system just disconnected from a remote LAN.
	     Included with this trap will be the
	     rWANStatsIndex, rWANStatsCardID, rWANStatsPortID,
	     rWANStatsChanID identifying which card, port and
	     channel, resource module connected were associated 
	     with this WAN link."
	    ::= 9011


	gCallFailure        TRAP-TYPE
	    ENTERPRISE      gandalf
	     DESCRIPTION
	    "The  system refused a connection.  If the
	     system rSysTrapCall is set, the TRAP will be sent
	     to the TRAP communities. "
	    ::= 9012

	gP1Backplane        TRAP-TYPE
	    ENTERPRISE      gandalf
	    DESCRIPTION
	    "The system could not detect the presence
	     of a P1 backplane."
	    ::= 9013

	gDatabaseInvalid    TRAP-TYPE
	    ENTERPRISE      gandalf
	    DESCRIPTION
	    "On startup, the system found that the database
	     was a newer revision than the database."
	    ::= 9014

	gNetsyncGain       TRAP-TYPE
	    ENTERPRISE      gandalf
	    DESCRIPTION
	    "The system detected the presence of the NETSYNC
	     clock."
	    ::= 9015

	gNetsyncLoss       TRAP-TYPE
	    ENTERPRISE      gandalf
	    DESCRIPTION
	    "The system detected the loss of the NETSYNC
	     clock."
	    ::= 9016

	gCompression        TRAP-TYPE
	    ENTERPRISE      gandalf
	    DESCRIPTION
	    "The system detected that the compression
	     engine couldn't startup. The text description gives the
	     reason."
	    ::= 9017

	gSecurity           TRAP-TYPE
	    ENTERPRISE      gandalf
	    DESCRIPTION
	    "The system detected a security violation
	     when attempting to accept a call."
	    ::= 9018

	gInvalidISDNSwitch  TRAP-TYPE
	    ENTERPRISE      gandalf
	    DESCRIPTION
	    "The system detected that the I/O card
	     had a software image that wouldn't run with the ISDN switch
	     currently set for the card."
	    ::= 9019

	gXferSuccessful TRAP-TYPE
	    ENTERPRISE      gandalf
	    DESCRIPTION
	    "The system detected that the file transfer
	     was successful. "
	    ::= 9020

	gXferFailed         TRAP-TYPE
	    ENTERPRISE      gandalf
	    DESCRIPTION
	    "The system detected that the file transfer
	     was not successful."
	    ::= 9021

	gCardOverLimit      TRAP-TYPE
	    ENTERPRISE      gandalf
	    DESCRIPTION
	    "The system detected that the maximum number of
	     channels allowed per system has been exceeded."
	    ::= 9022

	gLeasedLineFault    TRAP-TYPE
	    ENTERPRISE      gandalf
	    DESCRIPTION
	    "The system detected that the connection on
	     a leased line has failed. A trap will be generated every
	     fifteen minutes until the connection is completed."
	    ::= 9023

	gDChanUp        TRAP-TYPE
	    ENTERPRISE      gandalf
	    DESCRIPTION
	    "The system detected that a D channel has been
	     successfully brought up. "
	    ::= 9024

	gDChanDown          TRAP-TYPE
	    ENTERPRISE      gandalf
	    DESCRIPTION
	    "The system detected a that D channel has been
	     dropped."
	    ::= 9025

	gInvalidPortConf    TRAP-TYPE
	    ENTERPRISE      gandalf
	    DESCRIPTION
	    "The system detected that a port configuration
	     attribute has been configured incorrectly."
	    ::= 9026

	gCfgChangeNotApplied       TRAP-TYPE
	    ENTERPRISE      gandalf
	    DESCRIPTION
	    "The system detected thath a configuration change
	      has not yet been applied. The specific card must be
	     restarted for the change to take affect."
	    ::= 9027

	gSoftwareLoadIs    TRAP-TYPE
	    ENTERPRISE      gandalf
	    DESCRIPTION
	    "The system detected a variant version of
	     software has been downloaded to an I/O card."
	    ::= 9028

	gDuplicateNetwork   TRAP-TYPE
	    ENTERPRISE      gandalf
	    DESCRIPTION
	    "The system detected a duplicate IPX network
	     number."
	    ::= 9029

	gSapTableFull       TRAP-TYPE
	    ENTERPRISE      gandalf
	    DESCRIPTION
	    "The system detected that the SAP table has
	     reached its 500th Static entry or 2100th Dynamic entry."
	    ::= 9030

	gAuditRecordsLost   TRAP-TYPE
	    ENTERPRISE      gandalf
	    DESCRIPTION
	    "This trap is generated whenever audit records have been lost."
	    ::= 9031

	gLongCall           TRAP-TYPE
	    ENTERPRISE      gandalf
	    VARIABLES       { rRemLANID }
	    DESCRIPTION
	    "This trap is generated whenever a call to a remote LAN has
	    been connected for longer than the Long Call period."
	    ::= 9032
 
        gDChanFaulty        TRAP-TYPE
            ENTERPRISE      gandalf
            DESCRIPTION
            "This trap is generated whenever a D channel is unstable and
            losses the DSL more than the set threshold allows."
            ::= 9033

        gAddressMovedTooOften        TRAP-TYPE
            ENTERPRISE      gandalf
            VARIABLES       { rMACID    }
            DESCRIPTION
            "This trap is generated whenever a mac address moves from lan to
            lan too often which can cause an unstable network."
            ::= 9034
 
        gTestPresenceCallPassed      TRAP-TYPE
            ENTERPRISE      gandalf
            VARIABLES       { rRemLANID,
                              rRemLANName
               }
            DESCRIPTION
            "This trap is generated when a test presence call is successful,
            that is the remote either rang or answered the call."
            ::= 9035
 
        gTestPresenceCallFailed      TRAP-TYPE
            ENTERPRISE      gandalf
            VARIABLES       { rRemLANID,
                              rRemLANName
               }
            DESCRIPTION
            "This trap is generated when a test presence call failed."
            ::= 9036

        gTestPresenceCallNotIssued   TRAP-TYPE
            ENTERPRISE      gandalf
            VARIABLES       { rRemLANID,
                              rRemLANName
               }
            DESCRIPTION
            "This trap is generated when the system is unable to issue a
             test presence call.  This is not an indication that the intended
             remote LAN is not functional, thus the call should be re-
             attempted."
            ::= 9037
 
--
-- Card State Changed
--
	  gCardStateChanged TRAP-TYPE
	      ENTERPRISE  gandalf
	      VARIABLES   { rCardID,
                       	    rCardOpState 
            }
	      DESCRIPTION
	      "This trap indicates that the state of a card has changed.
	       The rCardID identifying the slot will be included with the
	       trap and the rCardOpState indicating the new card state."
	      ::= 9038

--
-- Hardware mismatch
--

	  gHardwareMismatch TRAP-TYPE
	      ENTERPRISE  gandalf
	      VARIABLES   { rChanCardID,
                            rChanPortID
            }
	      DESCRIPTION
	      "This trap indicates that the hardware that is present
	       is not the hardware that is expected."
	      ::= 9039


END
