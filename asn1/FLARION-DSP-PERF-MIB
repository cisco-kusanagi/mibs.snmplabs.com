-- $Id: FLARION-DSP-PERF-MIB.txt,v 1.2 2004/05/14 18:30:54 phsu Exp $

FLARION-DSP-PERF-MIB DEFINITIONS ::= BEGIN
 
IMPORTS
    Unsigned32, OBJECT-TYPE
        FROM SNMPv2-SMI

	DisplayString, TruthValue
        FROM SNMPv2-TC

    flarion, rrMib, HwAddress
        FROM FLARION-MIB;


--
-- Type definitions
--


--
-- Node definitions
--

rrDspPerf           OBJECT IDENTIFIER ::= { rrMib 100 }
dlSnr               OBJECT IDENTIFIER ::= { rrDspPerf 3 }
userLoad            OBJECT IDENTIFIER ::= { rrDspPerf 9 }
userQos             OBJECT IDENTIFIER ::= { rrDspPerf 10 }
recordAccess        OBJECT IDENTIFIER ::= { rrDspPerf 14 }
recordDisconnects   OBJECT IDENTIFIER ::= { rrDspPerf 15 }


--
-- User SNR Histogram
--

dlSnrTable      OBJECT-TYPE
    SYNTAX      SEQUENCE OF DlSnrEntry
    MAX-ACCESS  not-accessible
    STATUS      current
    DESCRIPTION "Histograms of Session ON (SON) user Signal/Noise Ratio (SNR)."
    ::= { dlSnr 1 }

dlSnrEntry      OBJECT-TYPE
    SYNTAX      DlSnrEntry
    MAX-ACCESS  not-accessible
    STATUS      current
    DESCRIPTION ""
    INDEX       { dlSnrSector, dlSnrIndex }
    ::= { dlSnrTable 1 }

DlSnrEntry ::= SEQUENCE { 
        dlSnrSector     INTEGER,
        dlSnrIndex      INTEGER,
        dlSnrAsgPwc     Unsigned32
    }

dlSnrSector     OBJECT-TYPE
    SYNTAX      INTEGER
    MAX-ACCESS  read-only
    STATUS      current
    DESCRIPTION "The sector to which the histogram pertains."
    ::= { dlSnrEntry 1 }

dlSnrIndex      OBJECT-TYPE
    SYNTAX      INTEGER (1..40)
    MAX-ACCESS  read-only
    STATUS      current
    DESCRIPTION "The histogram bin."
    ::= { dlSnrEntry 2 }

dlSnrAsgPwc     OBJECT-TYPE
    SYNTAX      Unsigned32
    MAX-ACCESS  read-only
    STATUS      current
    DESCRIPTION "The assignment power control channel."
    ::= { dlSnrEntry 3 }


--
-- User Load
--

-- Session On Users Histogram

sonUserTable    OBJECT-TYPE
    SYNTAX      SEQUENCE OF SonUserEntry
    MAX-ACCESS  not-accessible
    STATUS      current
    DESCRIPTION "Histogram of number of Session On users."
    ::= { userLoad 1 }

sonUserEntry    OBJECT-TYPE
    SYNTAX      SonUserEntry
    MAX-ACCESS  not-accessible
    STATUS      current
    DESCRIPTION "Description."
    INDEX       { sonUserSector, sonUserIndex }
    ::= { sonUserTable 1 }

SonUserEntry ::= SEQUENCE { 
        sonUserSector   INTEGER,
        sonUserIndex    INTEGER,
        sonUserNum      Unsigned32
    }

sonUserSector   OBJECT-TYPE
    SYNTAX      INTEGER
    MAX-ACCESS  read-only
    STATUS      current
    DESCRIPTION "The sector to which the histogram pertains."
    ::= { sonUserEntry 1 }

sonUserIndex    OBJECT-TYPE
    SYNTAX      INTEGER (1..32)
    MAX-ACCESS  read-only
    STATUS      current
    DESCRIPTION "Session On user index."
    ::= { sonUserEntry 2 }

sonUserNum      OBJECT-TYPE
    SYNTAX      Unsigned32
    MAX-ACCESS  read-only
    STATUS      current
    DESCRIPTION "Number of SON users."
    ::= { sonUserEntry 3 }


-- Active Users Histogram

activeUserTable    OBJECT-TYPE
    SYNTAX      SEQUENCE OF ActiveUserEntry
    MAX-ACCESS  not-accessible
    STATUS      current
    DESCRIPTION "Histogram of number of active users."
    ::= { userLoad 2 }

activeUserEntry    OBJECT-TYPE
    SYNTAX      ActiveUserEntry
    MAX-ACCESS  not-accessible
    STATUS      current
    DESCRIPTION ""
    INDEX       { activeUserSector, activeUserIndex }
    ::= { activeUserTable 1 }

ActiveUserEntry ::= SEQUENCE { 
        activeUserSector   INTEGER,
        activeUserIndex    INTEGER,
        activeUserNum      Unsigned32
    }

activeUserSector   OBJECT-TYPE
    SYNTAX      INTEGER
    MAX-ACCESS  read-only
    STATUS      current
    DESCRIPTION "The sector to which the histogram pertains."
    ::= { activeUserEntry 1 }

activeUserIndex OBJECT-TYPE
    SYNTAX      INTEGER (1..126)
    MAX-ACCESS  read-only
    STATUS      current
    DESCRIPTION "Active user histogram bin."
    ::= { activeUserEntry 2 }

activeUserNum      OBJECT-TYPE
    SYNTAX      Unsigned32
    MAX-ACCESS  read-only
    STATUS      current
    DESCRIPTION "Number of active users."
    ::= { activeUserEntry 3 }


--
-- User QoS Distribution Stats
--

userQosTable    OBJECT-TYPE
    SYNTAX      SEQUENCE OF UserQosEntry
    MAX-ACCESS  not-accessible
    STATUS      current
    DESCRIPTION "Distribution of users with respect to their QoS classes."
    ::= { userQos 1 }

userQosEntry    OBJECT-TYPE
    SYNTAX      UserQosEntry
    MAX-ACCESS  not-accessible
    STATUS      current
    DESCRIPTION ""
    INDEX       { userQosSector, userQosClass }
    ::= { userQosTable 1 }

UserQosEntry ::= SEQUENCE { 
        userQosSector  INTEGER,
        userQosClass   INTEGER,
        userQosName    DisplayString,
        userQosNum     Unsigned32
    }

userQosSector   OBJECT-TYPE
    SYNTAX      INTEGER
    MAX-ACCESS  read-only
    STATUS      current
    DESCRIPTION "The sector to which the user QoS distrubtion pertains."
    ::= { userQosEntry 1 }

userQosClass    OBJECT-TYPE
    SYNTAX      INTEGER
    MAX-ACCESS  read-only
    STATUS      current
    DESCRIPTION "The sector to which the user QoS distrubtion pertains."
    ::= { userQosEntry 2 }

userQosName     OBJECT-TYPE
    SYNTAX      DisplayString
    MAX-ACCESS  read-only
    STATUS      current
    DESCRIPTION "The QoS class name."
    ::= { userQosEntry 3 }

userQosNum      OBJECT-TYPE
    SYNTAX      Unsigned32
    MAX-ACCESS  read-only
    STATUS      current
    DESCRIPTION "Number of users in this QoS class."
    ::= { userQosEntry 4 }


--
-- Record Access
--

acsTable        OBJECT-TYPE
    SYNTAX      SEQUENCE OF AcsEntry
    MAX-ACCESS  not-accessible
    STATUS      current
    DESCRIPTION "This table contains record access counters."
    ::= { recordAccess 1 }
		
acsEntry        OBJECT-TYPE
    SYNTAX      AcsEntry
    MAX-ACCESS  not-accessible
    STATUS      current
    DESCRIPTION "Record access table entries."
    INDEX       { acsSectorIndex }
    ::= { acsTable 1 }

AcsEntry ::= SEQUENCE { 
    acsSectorIndex      INTEGER,
    acsTotalAccesses    Unsigned32,
    acsPowerUp          Unsigned32,
    acsHandoff          Unsigned32,
    acsLU               Unsigned32,
    acsPageResp         Unsigned32,
    acsDenied           Unsigned32,
    acsFailAcsxgLDPC    Unsigned32,
    acsFailAcsxgLowPower Unsigned32,
    acsFailAcsxgCRC     Unsigned32,
    acsMsToBsLu         Unsigned32,
    acsBsToMsLuFastNak  Unsigned32,
    acsBsToMsLuFastAck  Unsigned32,
    acsL3ToBsLuRsp      Unsigned32,
    acsL3ToBsLuRspAck   Unsigned32,
    acsL3ToBsLuRspNak   Unsigned32,
    acsBsToMsLuRsp      Unsigned32,
    acsBsToMsLuRspAck   Unsigned32,
    acsBsToMsLuRspNak   Unsigned32
}

acsSectorIndex  OBJECT-TYPE
    SYNTAX      INTEGER
    MAX-ACCESS  read-only
    STATUS      current
    DESCRIPTION "The sector to which this record access refers."
    ::= { acsEntry 1 }

acsTotalAccesses    OBJECT-TYPE
    SYNTAX      Unsigned32
    MAX-ACCESS  read-only
    STATUS      current
    DESCRIPTION "Total number of accesses."
    ::= { acsEntry 2 }

acsPowerUp      OBJECT-TYPE
    SYNTAX      Unsigned32
    MAX-ACCESS  read-only
    STATUS      current
    DESCRIPTION "Total number of power-up accesses."
    ::= { acsEntry 3 }
		
acsHandoff      OBJECT-TYPE
    SYNTAX      Unsigned32
    MAX-ACCESS  read-only
    STATUS      current
    DESCRIPTION "Total number of handoff accesses."
    ::= { acsEntry 4 }
		
acsLU           OBJECT-TYPE
    SYNTAX      Unsigned32
    MAX-ACCESS  read-only
    STATUS      current
    DESCRIPTION "Total number of location-update accesses."
    ::= { acsEntry 5 }
		
acsPageResp OBJECT-TYPE
    SYNTAX      Unsigned32
    MAX-ACCESS  read-only
    STATUS      current
    DESCRIPTION "Total number of accesses in response to pages."
    ::= { acsEntry 6 }

acsDenied OBJECT-TYPE
    SYNTAX      Unsigned32
    MAX-ACCESS  read-only
    STATUS      current
    DESCRIPTION "Total number of accesses that were denied."
    ::= { acsEntry 7 }

acsFailAcsxgLDPC OBJECT-TYPE
    SYNTAX      Unsigned32
    MAX-ACCESS  read-only
    STATUS      current
    DESCRIPTION "Number of mobile access exchanges that failed due to
                LDPC decoding errors."
    ::= { acsEntry 8 }
		
acsFailAcsxgLowPower OBJECT-TYPE
    SYNTAX      Unsigned32
    MAX-ACCESS  read-only
    STATUS      current
    DESCRIPTION "Number of mobile access exchanges that failed due to
                low power."
    ::= { acsEntry 9 }
		
acsFailAcsxgCRC OBJECT-TYPE
    SYNTAX      Unsigned32
    MAX-ACCESS  read-only
    STATUS      current
    DESCRIPTION "Number of mobile access exchanges that failed due to a CRC
                error-check failure."
    ::= { acsEntry 10 }
		
acsMsToBsLu OBJECT-TYPE
    SYNTAX      Unsigned32
    MAX-ACCESS  read-only
    STATUS      current
    DESCRIPTION "Total number of valid location updated received over airlink,
                equal to the sum of acsBsToMsLuFastNak and acsBsToMsLuFastAck."
    ::= { acsEntry 11 }

acsBsToMsLuFastNak OBJECT-TYPE
    SYNTAX      Unsigned32
    MAX-ACCESS  read-only
    STATUS      current
    DESCRIPTION "Number of valid location updated received at BS but discarded
                because BS is not accepting any."
    ::= { acsEntry 12 }
		
acsBsToMsLuFastAck OBJECT-TYPE
    SYNTAX      Unsigned32
    MAX-ACCESS  read-only
    STATUS      current
    DESCRIPTION "Number of valid location updates received at BS that Fast acked
                and were passed on to the FSM/L3."
    ::= { acsEntry 13 }
		
acsL3ToBsLuRsp OBJECT-TYPE
    SYNTAX      Unsigned32
    MAX-ACCESS  read-only
    STATUS      current
    DESCRIPTION "Number of LU responses received from L3/FSM, equal to the sum
                of acsL3toBsLuRspAck and acsL3ToBsLuRspNak."
    ::= { acsEntry 14 }
		
acsL3ToBsLuRspAck OBJECT-TYPE
    SYNTAX      Unsigned32
    MAX-ACCESS  read-only
    STATUS      current
    DESCRIPTION "Number of LU responses received from L3/FSM that are ACKs."
    ::= { acsEntry 15 }

acsL3ToBsLuRspNak OBJECT-TYPE
    SYNTAX      Unsigned32
    MAX-ACCESS  read-only
    STATUS      current
    DESCRIPTION "Number of LU responses received from L3/FSM that are NAKs."
    ::= { acsEntry 16 }

acsBsToMsLuRsp  OBJECT-TYPE
    SYNTAX      Unsigned32
    MAX-ACCESS  read-only
    STATUS      current
    DESCRIPTION "Number of LU responses sent to mobiles, equal to the sum of
                acsBsToMsLuRspAck and acsBsToMsLuRspNak."
    ::= { acsEntry 17 }
		
acsBsToMsLuRspAck OBJECT-TYPE
    SYNTAX      Unsigned32
    MAX-ACCESS  read-only
    STATUS      current
    DESCRIPTION "Number of LU responses sent to mobiles that are ACKs."
    ::= { acsEntry 18 }
		
acsBsToMsLuRspNak OBJECT-TYPE
    SYNTAX      Unsigned32
    MAX-ACCESS  read-only
    STATUS      current
    DESCRIPTION "Number of LU responses sent to mobiles that are NAKs."
    ::= { acsEntry 19 }
	

acsChannelTable OBJECT-TYPE
    SYNTAX      SEQUENCE OF AcsChannelEntry
    MAX-ACCESS  not-accessible
    STATUS      current
    DESCRIPTION "Total number of access broken down by tone set."
    ::= { recordAccess 2 }
		
acsChannelEntry OBJECT-TYPE
    SYNTAX      AcsChannelEntry
    MAX-ACCESS  not-accessible
    STATUS      current
    DESCRIPTION ""
    INDEX       { acsChannelIndex }
    ::= { acsChannelTable 1 }

AcsChannelEntry ::= SEQUENCE { 
    acsChannelSectorIndex   Unsigned32,
    acsChannelIndex         Unsigned32,
    acsChannelAccesses      Unsigned32
}

acsChannelSectorIndex OBJECT-TYPE
    SYNTAX      Unsigned32
    MAX-ACCESS  read-only
    STATUS      current
    DESCRIPTION "The sector index."
    ::= { acsChannelEntry 1 }

acsChannelIndex OBJECT-TYPE
    SYNTAX      Unsigned32
    MAX-ACCESS  read-only
    STATUS      current
    DESCRIPTION "The channel (access tone) index."
    ::= { acsChannelEntry 2 }
		
acsChannelAccesses OBJECT-TYPE
    SYNTAX      Unsigned32
    MAX-ACCESS  read-only
    STATUS      current
    DESCRIPTION "Number of accesses on this channel."
    ::= { acsChannelEntry 3 }
	

--
-- Record Disconnects
--

-- Disconnects By Type

disconnectTypeTable OBJECT-TYPE
    SYNTAX      SEQUENCE OF DisconnectTypeEntry
    MAX-ACCESS  not-accessible
    STATUS      current
    DESCRIPTION "This table contains disconnect counters by type."
    ::= { recordDisconnects 1 }
		
disconnectTypeEntry OBJECT-TYPE
    SYNTAX      DisconnectTypeEntry
    MAX-ACCESS  not-accessible
    STATUS      current
    DESCRIPTION "Record disconnect type table entries."
    INDEX       { disconnectTypeSector, disconnectTypeIndex }
    ::= { disconnectTypeTable 1 }

DisconnectTypeEntry ::= SEQUENCE { 
    disconnectTypeSector    INTEGER,
    disconnectTypeIndex     INTEGER,
    disconnectTypeNum       Unsigned32
}

disconnectTypeSector    OBJECT-TYPE
    SYNTAX      INTEGER (1..255)
    MAX-ACCESS  read-only
    STATUS      current
    DESCRIPTION "The sector to which this disconnect type refers."
    ::= { disconnectTypeEntry 1 }

disconnectTypeIndex    OBJECT-TYPE
    SYNTAX      INTEGER
    MAX-ACCESS  read-only
    STATUS      current
    DESCRIPTION "The disconnect type. Disconnect types are defined as follows:
                      0: Disconnect unknown
                     18: DDCH FER exception
                     19: ULTCH FER exception
                     20: ULTC FER exception
                     21: CLI caused drop
                     32: SRES failed
                     33: URESP timeout
                     34: Config timeout
                     35: Config2 timeout
                     36: L3 ACK/L2 Up timeout
                     37: L3 sent L2Drop
                     38: L3 sent scrub
                     39: ARQ errors
                     40: Received deregistration
                     41: Cannot process registration
                     42: L3 sent L2Reg fail
                     43: L3 sent L2Ho fail
                     44: L2FSM_TO_MS_SON_TO_SHO timeout
                     45: L2FSM_TO_PGCC_SHO_TO_SON timeout
                     46: L2FSM_TO_MS_SON_TO_SLP timeout
                     47: L2Success timeout
                     48: MS_REQ_SON_TO_SLP
                     49: MS_REQ_SHO_TO_SLP
                     50: L2FSM_TO_PGCC_SHO_TO_SON failed
                     51: L2FSM_TO_PGCC_SHO_TO_SLP failed
                    142: L2 Duplicate registration
                    147: L3 handoff notification"
    ::= { disconnectTypeEntry 2 }

disconnectTypeNum OBJECT-TYPE
    SYNTAX      Unsigned32
    MAX-ACCESS  read-only
    STATUS      current
    DESCRIPTION "Number of disconnects for this type."
    ::= { disconnectTypeEntry 3 }



END
