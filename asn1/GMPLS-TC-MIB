-- extracted from draft-ietf-ccamp-gmpls-tc-mib-00.txt
-- at Sat Jun 29 06:09:51 2002

GMPLS-TC-MIB DEFINITIONS ::= BEGIN

IMPORTS
   MODULE-IDENTITY, Unsigned32, Integer32
      FROM SNMPv2-SMI
   TEXTUAL-CONVENTION
      FROM SNMPv2-TC
   ;

gmplsTCMIB MODULE-IDENTITY
   LAST-UPDATED
      "200224060900Z"  -- 24 June 2002 9:00:00 GMT
   ORGANIZATION
      "Common Control And Management Protocols (CCAMP)
   Working Group"
   CONTACT-INFO
      "       Thomas D. Nadeau
      Postal: Cisco Systems, Inc.
              250 Apollo Drive
              Chelmsford, MA 01824
         Tel: +1-978-244-3051
       Email: tnadeau@cisco.com

              Cheenu Srinivasan
      Postal: Parama Networks, Inc.
              1030 Broad Street
              Shrewsbury, NJ 07702
         Tel: +1-732-544-9120 x731
       Email: cheenu@paramanet.com
         Tel: +1-732-544-9120x731

              Adrian Farrel
      Postal: Movaz Networks, Inc.
              7926 Jones Branch Drive
              McLean, VA 22102
         Tel: +1-703-847-1867
       Email: afarrel@movaz.com

              Edward Harrison
      Postal: Data Connection Ltd.
              100 Church Street
              Enfield, Middlesex
              EN2 6BQ, United Kingdom

Nadeau, et al.                                     [Page 4 ]
draft-ietf-ccamp-gmpls-tc-mib-00.txt               June 2002

         Tel: +44-20-8366-1177
       Email: eph@dataconnection.com

              Tim Hall
      Postal: Data Connection Ltd.
              100 Church Street
              Enfield, Middlesex
              EN2 6BQ, United Kingdom
         Tel: +44-20-8366-1177
       Email: timhall@dataconnection.com

      Email comments to the CCAMP WG Mailing List at
   ccamp@ops.ietf.org."

   DESCRIPTION
       "This MIB module defines Textual Conventions
        and OBJECT-IDENTITIES for use in documents
        defining management information bases
        (MIBs) for managing GMPLS networks."

   -- Revision history.
   REVISION
      "200224060900Z"  -- 24 June 2002 09:00:00 GMT
   DESCRIPTION
      "Initial version."
   -- Above revision history to be replaced as below.
   -- REVISION
   -- "yyyymmddhhmmZ"-- DESCRIPTION "Initial version, published as RFC xxxx"
   -- xxxx to be assigned by RFC Editor
   ::= { gmplsMIB 1 }

   -- This object identifier needs to be assigned by IANA.
   -- Note that MPLS has been assigned an ifType of 166 and that an OID
   -- of 166 has been suggested for the MPLS MIBs.
   gmplsMIB OBJECT IDENTIFIER ::= { transmission xxx }

-- Textual Conventions (sorted alphabetically).

GmplsFreeformLabel ::= TEXTUAL-CONVENTION
   STATUS      current
   DESCRIPTION
       "This value represents a freeform
        generalized MPLS Label.  This can be used
        to represent label types which are not
        standard in the drafts."
   SYNTAX OCTET STRING (SIZE (0..64))

GmplsGeneralizedLabelSubtypes ::= TEXTUAL-CONVENTION
   STATUS      current
   DESCRIPTION
       "Determines the interpretation that should
        be applied to a label given its label type
        as specified by
        GmplsGeneralizedLabelTypes."
   SYNTAX INTEGER {
      mplsLabel(1),

Nadeau, et al.                                     [Page 5 ]
draft-ietf-ccamp-gmpls-tc-mib-00.txt               June 2002

      portWavelengthLabel(2),
      freeformGeneralizedLabel(3),
      sonetLabel(4),
      sdhLabel(5),
      wavebandLabel(6)
   }

GmplsGeneralizedLabelTypes ::= TEXTUAL-CONVENTION
   STATUS      current
   DESCRIPTION
       "The label types that are defined for
        Generalized MPLS."
   SYNTAX INTEGER {
      mplsLabel(1),
      generalizedLabel(2)
   }

GmplsHopUnnumAddrTypes ::= TEXTUAL-CONVENTION
   STATUS      current
   DESCRIPTION
       "Identifies whether a hop of an explicit or
        reported route uses unnumbered addresses
        and, if so, the type of unnumbered
        address."
   SYNTAX   INTEGER {
      numbered(1),
      unnumberedIfIpV4(2),
      unnumberedIfIpV6(3)
   }

GmplsSegmentDirection ::= TEXTUAL-CONVENTION
   STATUS      current
   DESCRIPTION
       "The direction of data flow on an LSP
        segment with respect to the head of the
        LSP.

        Where an LSP is signaled using a
        conventional signaling protocol, the 'head'
        of the LSP is the source of the signaling
        (also known as the ingress) and the 'tail'
        is the destination (also known as the
        egress).

        For manually configured LSPs an arbitrary
        decision must be made about which LER is
        the 'head'."
   SYNTAX  INTEGER {
      forward(1),
      reverse(2)
   }


END

-- 
--    Copyright (C) The Internet Society (2002). All Rights
--    Reserved.
-- 
--    This document and translations of it may be copied and
--    furnished to others, and derivative works that comment on
--    or otherwise explain it or assist in its implementation
--    may be prepared, copied, published and distributed, in
--    whole or in part, without restriction of any kind,
--    provided that the above copyright notice and this
--    paragraph are included on all such copies and derivative
--    works.  However, this document itself may not be modified
--    in any way, such as by removing the copyright notice or
--    references to the Internet Society or other Internet
--    organizations, except as needed for the purpose of
--    developing Internet standards in which case the
--    procedures for copyrights defined in the Internet
--    Standards process must be followed, or as required to
--    translate it into languages other than English.
-- 
--    The limited permissions granted above are perpetual and
--    will not be revoked by the Internet Society or its
--    successors or assigns. This document and the information
--    contained herein is provided on an "AS IS" basis and THE
--    INTERNET SOCIETY AND THE INTERNET ENGINEERING TASK FORCE
--    DISCLAIMS ALL WARRANTIES, EXPRESS OR IMPLIED, INCLUDING
--    BUT NOT LIMITED TO ANY WARRANTY THAT THE USE OF THE
--    INFORMATION HEREIN WILL NOT INFRINGE ANY RIGHTS OR ANY
--    IMPLIED WARRANTIES OF MERCHANTABILITY OR FITNESS FOR A
--    PARTICULAR PURPOSE.
