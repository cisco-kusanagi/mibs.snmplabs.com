Wellfleet-SWSMDS-MIB DEFINITIONS ::= BEGIN

-- Created by mdl2asn version 3.1
-- Creation date: Wed Aug 30 16:48:30 EDT 1995


    IMPORTS

      IpAddress, Counter, Gauge, TimeTicks, Opaque, enterprises, mgmt
        FROM RFC1155-SMI
      OBJECT-TYPE
        FROM RFC-1212
      TRAP-TYPE
        FROM RFC-1215
      DisplayString, mib-2
        FROM RFC1213-MIB
      wfSmdsSwGroup
        FROM Wellfleet-COMMON-MIB;


    wfSmdsSwSubTable OBJECT-TYPE
        SYNTAX	SEQUENCE OF WfSmdsSwSubEntry
        ACCESS	not-accessible
        STATUS	mandatory
        DESCRIPTION
                "The Wellfleet SMDS Switch Circuit (SNI,
                subscriber) Record.  This record holds
                information on a per circuit (SSI, SNI,
                subscriber) basis."
        ::= { wfSmdsSwGroup 1 }

    wfSmdsSwSubEntry OBJECT-TYPE
        SYNTAX	WfSmdsSwSubEntry
        ACCESS	not-accessible
        STATUS	mandatory
        DESCRIPTION
                "Per Wellfleet circuit SMDS Switch configuration
                parameters and counters.
                This table contains Subscriber-Network Interface (SNI)
                parameters and state variables, one entry per SIP port."
        INDEX	{ wfSmdsSwSubCct }
        ::= { wfSmdsSwSubTable 1 }

    WfSmdsSwSubEntry ::= SEQUENCE {
    	    wfSmdsSwSubDelete
    		INTEGER,
    	    wfSmdsSwSubDisable
    		INTEGER,
    	    wfSmdsSwSubState
    		INTEGER,
    	    wfSmdsSwSubCct
    		INTEGER,
    	    wfSmdsSwSubDisableHrtbtPoll
    		INTEGER,
    	    wfSmdsSwSubHrtbtPollAddr
    		INTEGER,
    	    wfSmdsSwSubHrtbtPollInterval
    		INTEGER,
    	    wfSmdsSwSubHrtbtPollDownCount
    		INTEGER,
    	    wfSmdsSwSubDisableNetMgmt
    		INTEGER,
    	    wfSmdsSwSubInterfaceType
    		INTEGER,
    	    wfSmdsSwSubInterfaceIndex
    		INTEGER,
    	    wfSmdsSwSubDisableL3PduChecks
    		INTEGER,
    	    wfSmdsSwSubDisableUsageGeneration
    		INTEGER,
    	    wfSmdsSwSubDisableMIR
    		INTEGER,
    	    wfSmdsSwSubUnassignedSAs
    		Counter,
    	    wfSmdsSwSubSAScreenViolations
    		Counter,
    	    wfSmdsSwSubDAScreenViolations
    		Counter,
    	    wfSmdsSwSubNumPDUExceededMIR
    		Counter,
    	    wfSmdsSwSubSipL3ReceivedIAs
    		Counter,
    	    wfSmdsSwSubSipL3ReceivedGAs
    		Counter,
    	    wfSmdsSwSubSipL3UnrecIAs
    		Counter,
    	    wfSmdsSwSubSipL3UnrecGAs
    		Counter,
    	    wfSmdsSwSubSipL3SentIAs
    		Counter,
    	    wfSmdsSwSubSipL3SentGAs
    		Counter,
    	    wfSmdsSwSubSipL3Errors
    		Counter,
    	    wfSmdsSwSubSipL3InvAddrTypes
    		Counter,
    	    wfSmdsSwSubSipL3VersionSupport
    		INTEGER,
    	    wfSmdsSwSubSAScrnViolationOccur
    		OCTET STRING,
    	    wfSmdsSwSubDAScrnViolationOccur
    		OCTET STRING,
    	    wfSmdsSwSubUnassignedSAOccur
    		OCTET STRING,
    	    wfSmdsSwSubSAErrorOccur
    		OCTET STRING,
    	    wfSmdsSwSubDAErrorOccur
    		OCTET STRING,
    	    wfSmdsSwSubInvalidBASizeOccur
    		OCTET STRING,
    	    wfSmdsSwSubInvalidHELenOccur
    		OCTET STRING,
    	    wfSmdsSwSubInvalidHEVerOccur
    		OCTET STRING,
    	    wfSmdsSwSubInvalidHECarOccur
    		OCTET STRING,
    	    wfSmdsSwSubInvalidHEPadOccur
    		OCTET STRING,
    	    wfSmdsSwSubBEtagOccur
    		OCTET STRING,
    	    wfSmdsSwSubBAsizeNELenOccur
    		OCTET STRING,
    	    wfSmdsSwSubIncorrectLenOccur
    		OCTET STRING,
    	    wfSmdsSwSubExceededMIROccur
    		OCTET STRING,
    	    wfSmdsSwSubInBandMgmtDisable
    		INTEGER,
    	    wfSmdsSwSubInBandMgmtLocalAddr
    		OCTET STRING,
    	    wfSmdsSwSubInBandMgmtReceivedPDUs
    		Counter,
    	    wfSmdsSwSubInBandMgmtSentPDUs
    		Counter,
    	    wfSmdsSwSubInBandMgmtMaxLenErrors
    		Counter,
    	    wfSmdsSwSubInBandMgmtEncapsErrors
    		Counter,
    	    wfSmdsSwSubGAPartialResolve
    		Counter,
    	    wfSmdsSwSubDANotOnSni
    		Counter
        }

    wfSmdsSwSubDelete OBJECT-TYPE
        SYNTAX	INTEGER {
    		    created(1),
    		    deleted(2)
    		}
        ACCESS	read-write
        STATUS	mandatory
        DESCRIPTION
                "create/delete parameter, dflt = created"
        DEFVAL	{ created }
        ::= { wfSmdsSwSubEntry 1 }

    wfSmdsSwSubDisable OBJECT-TYPE
        SYNTAX	INTEGER {
    		    enabled(1),
    		    disabled(2)
    		}
        ACCESS	read-write
        STATUS	mandatory
        DESCRIPTION
                "enable/disable parameter, dflt = enabled"
        DEFVAL	{ enabled }
        ::= { wfSmdsSwSubEntry 2 }

    wfSmdsSwSubState OBJECT-TYPE
        SYNTAX	INTEGER {
    		    up(1),
    		    down(2),
    		    init(3),
    		    notpresent(4)
    		}
        ACCESS	read-only
        STATUS	mandatory
        DESCRIPTION
                "SMDS Switch state variable, Up, Down Init, Not Present"
        DEFVAL	{ notpresent }
        ::= { wfSmdsSwSubEntry 3 }

    wfSmdsSwSubCct OBJECT-TYPE
        SYNTAX	INTEGER(1..1023)
        ACCESS	read-only
        STATUS	mandatory
        DESCRIPTION
                "cct number for this instance"
        ::= { wfSmdsSwSubEntry 4 }

    wfSmdsSwSubDisableHrtbtPoll OBJECT-TYPE
        SYNTAX	INTEGER {
    		    enabled(1),
    		    disabled(2)
    		}
        ACCESS	read-write
        STATUS	mandatory
        DESCRIPTION
                "determine use of DXI heartbeat poll"
        DEFVAL	{ disabled }
        ::= { wfSmdsSwSubEntry 5 }

    wfSmdsSwSubHrtbtPollAddr OBJECT-TYPE
        SYNTAX	INTEGER {
    		    cpe(1),
    		    net(2)
    		}
        ACCESS	read-write
        STATUS	mandatory
        DESCRIPTION
                "determine if heartbeat poll messages
                are sent as as CPE or network
                (CSU/DSU) messages."
        DEFVAL	{ net }
        ::= { wfSmdsSwSubEntry 6 }

    wfSmdsSwSubHrtbtPollInterval OBJECT-TYPE
        SYNTAX	INTEGER(6..2147483647)
        ACCESS	read-write
        STATUS	mandatory
        DESCRIPTION
                "heartbeat polling messages get sent every this many
                seconds - we don't want the polling interval to be
                less than or equal to the no-acknowledgment timer."
        DEFVAL	{ 10 }
        ::= { wfSmdsSwSubEntry 7 }

    wfSmdsSwSubHrtbtPollDownCount OBJECT-TYPE
        SYNTAX	INTEGER(1..10)
        ACCESS	read-write
        STATUS	mandatory
        DESCRIPTION
                "if this many consecutive heartbeat polling messages
                go unacknowledged, log an event declaring the line down"
        DEFVAL	{ 3 }
        ::= { wfSmdsSwSubEntry 8 }

    wfSmdsSwSubDisableNetMgmt OBJECT-TYPE
        SYNTAX	INTEGER {
    		    enabled(1),
    		    disabled(2)
    		}
        ACCESS	read-write
        STATUS	mandatory
        DESCRIPTION
                "determine use of LMI network management"
        DEFVAL	{ disabled }
        ::= { wfSmdsSwSubEntry 9 }

    wfSmdsSwSubInterfaceType OBJECT-TYPE
        SYNTAX	INTEGER {
    		    sni(1),
    		    ssi(2)
    		}
        ACCESS	read-write
        STATUS	mandatory
        DESCRIPTION
                "defines whether this interface is a SNI or
                SSI."
        DEFVAL	{ sni }
        ::= { wfSmdsSwSubEntry 10 }

    wfSmdsSwSubInterfaceIndex OBJECT-TYPE
        SYNTAX	INTEGER
        ACCESS	read-write
        STATUS	mandatory
        DESCRIPTION
                "The index number for the SSI/SNI. Each SNI in the
                network has a unique id.  The value of this object
                identifies the SIP port interface for which this
                entry contains management information."
        ::= { wfSmdsSwSubEntry 11 }

    wfSmdsSwSubDisableL3PduChecks OBJECT-TYPE
        SYNTAX	INTEGER {
    		    enabled(1),
    		    disabled(2)
    		}
        ACCESS	read-write
        STATUS	mandatory
        DESCRIPTION
                "Enable/Disable L3_PDU verification.
                Default is disabled."
        DEFVAL	{ enabled }
        ::= { wfSmdsSwSubEntry 12 }

    wfSmdsSwSubDisableUsageGeneration OBJECT-TYPE
        SYNTAX	INTEGER {
    		    enabled(1),
    		    disabled(2)
    		}
        ACCESS	read-write
        STATUS	mandatory
        DESCRIPTION
                "enable/disable usage data generation.
                Default is disabled."
        DEFVAL	{ disabled }
        ::= { wfSmdsSwSubEntry 13 }

    wfSmdsSwSubDisableMIR OBJECT-TYPE
        SYNTAX	INTEGER {
    		    enabled(1),
    		    disabled(2)
    		}
        ACCESS	read-write
        STATUS	mandatory
        DESCRIPTION
                "enable/disable MIR enforcement, default is
                disabled."
        DEFVAL	{ disabled }
        ::= { wfSmdsSwSubEntry 14 }

    wfSmdsSwSubUnassignedSAs OBJECT-TYPE
        SYNTAX	Counter
        ACCESS	read-only
        STATUS	mandatory
        DESCRIPTION
                "The total number of SIP Level 3 PDUs discarded
                by the SMDS Switch because the Source Address was
                not assigned to the SNI."
        ::= { wfSmdsSwSubEntry 15 }

    wfSmdsSwSubSAScreenViolations OBJECT-TYPE
        SYNTAX	Counter
        ACCESS	read-only
        STATUS	mandatory
        DESCRIPTION
                "The number of SIP L3_PDUs that violated the
                address screen based on source address screening
                for an SNI."
        ::= { wfSmdsSwSubEntry 16 }

    wfSmdsSwSubDAScreenViolations OBJECT-TYPE
        SYNTAX	Counter
        ACCESS	read-only
        STATUS	mandatory
        DESCRIPTION
                "The total number of SIP Level 3 PDUs that
                violated the Destination Address Screening using
                either an Individual Address Screen or a
                Group Address Screen for the SNI."
        ::= { wfSmdsSwSubEntry 17 }

    wfSmdsSwSubNumPDUExceededMIR OBJECT-TYPE
        SYNTAX	Counter
        ACCESS	read-only
        STATUS	mandatory
        DESCRIPTION
                "The total number of SIP L3_PDUs that exceeded
                the MIR on this interface."
        ::= { wfSmdsSwSubEntry 18 }

    wfSmdsSwSubSipL3ReceivedIAs OBJECT-TYPE
        SYNTAX	Counter
        ACCESS	read-only
        STATUS	mandatory
        DESCRIPTION
                "The total number of individually addressed SIP Level 3
                PDUs received by the SMDS Switch from the CPE.
                The total includes only unerrored L3PDUs."
        ::= { wfSmdsSwSubEntry 19 }

    wfSmdsSwSubSipL3ReceivedGAs OBJECT-TYPE
        SYNTAX	Counter
        ACCESS	read-only
        STATUS	mandatory
        DESCRIPTION
                "The total number of group addressed SIP Level 3 PDUs
                received by the SMDS Switch from the CPE.
                The total includes only unerrored L3PDUs."
        ::= { wfSmdsSwSubEntry 20 }

    wfSmdsSwSubSipL3UnrecIAs OBJECT-TYPE
        SYNTAX	Counter
        ACCESS	read-only
        STATUS	mandatory
        DESCRIPTION
                "The number of SIP Level 3 PDUs received by the
                SMDS Switch from the CPE that have an unknown,
                valid, individual SMDS Destination Address."
        ::= { wfSmdsSwSubEntry 21 }

    wfSmdsSwSubSipL3UnrecGAs OBJECT-TYPE
        SYNTAX	Counter
        ACCESS	read-only
        STATUS	mandatory
        DESCRIPTION
                "The number of SIP Level 3 PDUs received by the
                SMDS Switch from the CPE that have an unknown,
                valid, group SMDS Destination Address."
        ::= { wfSmdsSwSubEntry 22 }

    wfSmdsSwSubSipL3SentIAs OBJECT-TYPE
        SYNTAX	Counter
        ACCESS	read-only
        STATUS	mandatory
        DESCRIPTION
                "The number of individually addressed SIP Level 3 PDUs
                that have been sent by this SMDS Switch to the CPE."
        ::= { wfSmdsSwSubEntry 23 }

    wfSmdsSwSubSipL3SentGAs OBJECT-TYPE
        SYNTAX	Counter
        ACCESS	read-only
        STATUS	mandatory
        DESCRIPTION
                "The number of group addressed SIP L3PDUs that have been
                sent by this SMDS Switch to the CPE."
        ::= { wfSmdsSwSubEntry 24 }

    wfSmdsSwSubSipL3Errors OBJECT-TYPE
        SYNTAX	Counter
        ACCESS	read-only
        STATUS	mandatory
        DESCRIPTION
                "The total number of SIP Level 3 PDUs received
                by the SMDS Switch from the CPE that were
                discovered to have protocol errors."
        ::= { wfSmdsSwSubEntry 25 }

    wfSmdsSwSubSipL3InvAddrTypes OBJECT-TYPE
        SYNTAX	Counter
        ACCESS	read-only
        STATUS	mandatory
        DESCRIPTION
                "The total number of SIP Level 3 PDUs received
                by the SMDS Switch from the CPE that had a value
                in the Source or Destination Address type subfield
                other than group or individual.  Or if the
                Source Address type subfield value indicates
                a group address."
        ::= { wfSmdsSwSubEntry 26 }

    wfSmdsSwSubSipL3VersionSupport OBJECT-TYPE
        SYNTAX	INTEGER {
    		    version(1)
    		}
        ACCESS	read-only
        STATUS	mandatory
        DESCRIPTION
                "A value which indicates the version(s) of SIP
                that this SNI supports.  The value is a sum.
                This sum initially takes the value zero.  For each
                version, V, that this interface supports, 2 raised
                to (V - 1) is added to the sum. For example, a
                port supporting versions 1 and 2 would have a
                value of (2^(1-1)+2^(2-1))=3.  The
                SipL3VersionSupport is effectively a bit mask with
                Version 1 equal to the least significant bit (LSB)."
        DEFVAL	{ version }
        ::= { wfSmdsSwSubEntry 27 }

    wfSmdsSwSubSAScrnViolationOccur OBJECT-TYPE
        SYNTAX	OCTET STRING
        ACCESS	read-only
        STATUS	mandatory
        DESCRIPTION
                "A string containing the SMDS Source Address,
                Destination Address, and Event time of the most
                recent occurance of an L3_PDU discarded as a
                result of a Source Address violation."
        ::= { wfSmdsSwSubEntry 28 }

    wfSmdsSwSubDAScrnViolationOccur OBJECT-TYPE
        SYNTAX	OCTET STRING
        ACCESS	read-only
        STATUS	mandatory
        DESCRIPTION
                "A string containing the SMDS Source Address,
                Destination Address, and Event time of the most
                recent occurance of an L3_PDU discarded as a
                result of a Destination Address violation."
        ::= { wfSmdsSwSubEntry 29 }

    wfSmdsSwSubUnassignedSAOccur OBJECT-TYPE
        SYNTAX	OCTET STRING
        ACCESS	read-only
        STATUS	mandatory
        DESCRIPTION
                "A string containing the SMDS Source Address,
                Destination Address, and Event time of the most
                recent occurance of an L3_PDU discarded as a
                result of a unassigned Source Address."
        ::= { wfSmdsSwSubEntry 30 }

    wfSmdsSwSubSAErrorOccur OBJECT-TYPE
        SYNTAX	OCTET STRING
        ACCESS	read-only
        STATUS	mandatory
        DESCRIPTION
                "A string containing the SMDS Source Address,
                Destination Address, and Event time of the most
                recent occurance of an L3_PDU discarded because
                of a Source Address Field Format error."
        ::= { wfSmdsSwSubEntry 31 }

    wfSmdsSwSubDAErrorOccur OBJECT-TYPE
        SYNTAX	OCTET STRING
        ACCESS	read-only
        STATUS	mandatory
        DESCRIPTION
                "A string containing the SMDS Source Address,
                Destination Address, and Event time of the most
                recent occurance of an L3_PDU discarded because
                of a Destination Address Field Format error."
        ::= { wfSmdsSwSubEntry 32 }

    wfSmdsSwSubInvalidBASizeOccur OBJECT-TYPE
        SYNTAX	OCTET STRING
        ACCESS	read-only
        STATUS	mandatory
        DESCRIPTION
                "A string containing the SMDS Source Address,
                Destination Address, and Event time of the most
                recent occurance of an L3_PDU discarded because
                of an invalid BASize field value."
        ::= { wfSmdsSwSubEntry 33 }

    wfSmdsSwSubInvalidHELenOccur OBJECT-TYPE
        SYNTAX	OCTET STRING
        ACCESS	read-only
        STATUS	mandatory
        DESCRIPTION
                "A string containing the SMDS Source Address,
                Destination Address, and Event time of the most
                recent occurance of an L3_PDU discarded because
                of an invalid Header Extension Length Field value."
        ::= { wfSmdsSwSubEntry 34 }

    wfSmdsSwSubInvalidHEVerOccur OBJECT-TYPE
        SYNTAX	OCTET STRING
        ACCESS	read-only
        STATUS	mandatory
        DESCRIPTION
                "A string containing the SMDS Source Address,
                Destination Address, and Event time of the most
                recent occurance of an L3_PDU discarded because
                of an invalid Header Extension Version element."
        ::= { wfSmdsSwSubEntry 35 }

    wfSmdsSwSubInvalidHECarOccur OBJECT-TYPE
        SYNTAX	OCTET STRING
        ACCESS	read-only
        STATUS	mandatory
        DESCRIPTION
                "A string containing the SMDS Source Address,
                Destination Address, and Event time of the most
                recent occurance of an L3_PDU discarded because
                of an invalid Header Extension Carrier element."
        ::= { wfSmdsSwSubEntry 36 }

    wfSmdsSwSubInvalidHEPadOccur OBJECT-TYPE
        SYNTAX	OCTET STRING
        ACCESS	read-only
        STATUS	mandatory
        DESCRIPTION
                "A string containing the SMDS Source Address,
                Destination Address, and Event time of the most
                recent occurance of an L3_PDU discarded because
                of an invalid Header Extension Pad element."
        ::= { wfSmdsSwSubEntry 37 }

    wfSmdsSwSubBEtagOccur OBJECT-TYPE
        SYNTAX	OCTET STRING
        ACCESS	read-only
        STATUS	mandatory
        DESCRIPTION
                "A string containing the SMDS Source Address,
                Destination Address, and Event time of the most
                recent occurance of an L3_PDU discarded because
                of a Beginning-End Tag mismatch."
        ::= { wfSmdsSwSubEntry 38 }

    wfSmdsSwSubBAsizeNELenOccur OBJECT-TYPE
        SYNTAX	OCTET STRING
        ACCESS	read-only
        STATUS	mandatory
        DESCRIPTION
                "A string containing the SMDS Source Address,
                Destination Address, and Event time of the most
                recent occurance of an L3_PDU discarded because
                the BAsize and Length fields are not equal."
        ::= { wfSmdsSwSubEntry 39 }

    wfSmdsSwSubIncorrectLenOccur OBJECT-TYPE
        SYNTAX	OCTET STRING
        ACCESS	read-only
        STATUS	mandatory
        DESCRIPTION
                "A string containing the SMDS Source Address,
                Destination Address, and Event time of the most
                recent occurance of an L3_PDU discarded because
                of an incorrect length."
        ::= { wfSmdsSwSubEntry 40 }

    wfSmdsSwSubExceededMIROccur OBJECT-TYPE
        SYNTAX	OCTET STRING
        ACCESS	read-only
        STATUS	mandatory
        DESCRIPTION
                "A string containing the SMDS Source Address,
                Destination Address, and Event time of the most
                recent occurance of an L3_PDU discarded because
                it exceeded the MIR."
        ::= { wfSmdsSwSubEntry 41 }

    wfSmdsSwSubInBandMgmtDisable OBJECT-TYPE
        SYNTAX	INTEGER {
    		    enabled(1),
    		    disabled(2)
    		}
        ACCESS	read-write
        STATUS	mandatory
        DESCRIPTION
                "In-Band Management enable/disable parameter.
                This attribute indicates whether the local
                WSNI (only) is enabled to run IP in Host mode,
                for in-band management purposes, in additional
                to being a switch interface.  The default is
                disabled"
        DEFVAL	{ disabled }
        ::= { wfSmdsSwSubEntry 42 }

    wfSmdsSwSubInBandMgmtLocalAddr OBJECT-TYPE
        SYNTAX	OCTET STRING
        ACCESS	read-write
        STATUS	mandatory
        DESCRIPTION
                "Special SMDS E.164 Individual address that
                identifies this local circuit.  This attribute
                is only used when the wfSmdsSwSubInBandMgmtDisable
                attribute is set to ENABLED"
        ::= { wfSmdsSwSubEntry 43 }

    wfSmdsSwSubInBandMgmtReceivedPDUs OBJECT-TYPE
        SYNTAX	Counter
        ACCESS	read-only
        STATUS	mandatory
        DESCRIPTION
                "The total number of individually addressed In-Band
                Management PDUs received by the SMDS Switch from
                the CPE.  The total includes only unerrored PDUs."
        ::= { wfSmdsSwSubEntry 44 }

    wfSmdsSwSubInBandMgmtSentPDUs OBJECT-TYPE
        SYNTAX	Counter
        ACCESS	read-only
        STATUS	mandatory
        DESCRIPTION
                "The number of individually addressed In-Band Management
                PDUs that have been sent by this SMDS Switch to the CPE."
        ::= { wfSmdsSwSubEntry 45 }

    wfSmdsSwSubInBandMgmtMaxLenErrors OBJECT-TYPE
        SYNTAX	Counter
        ACCESS	read-only
        STATUS	mandatory
        DESCRIPTION
                "The number of In-Band Management PDUs that have
                exceeded the MTU size configured for the line"
        ::= { wfSmdsSwSubEntry 46 }

    wfSmdsSwSubInBandMgmtEncapsErrors OBJECT-TYPE
        SYNTAX	Counter
        ACCESS	read-only
        STATUS	mandatory
        DESCRIPTION
                "The number of In-Band Management PDUs that have
                invalid encapsulation schemes"
        ::= { wfSmdsSwSubEntry 47 }

    wfSmdsSwSubGAPartialResolve OBJECT-TYPE
        SYNTAX	Counter
        ACCESS	read-only
        STATUS	mandatory
        DESCRIPTION
                "The number of times group addressed L3_PDU's
                could not be resolved due to congestion."
        ::= { wfSmdsSwSubEntry 48 }

    wfSmdsSwSubDANotOnSni OBJECT-TYPE
        SYNTAX	Counter
        ACCESS	read-only
        STATUS	mandatory
        DESCRIPTION
                "The number of times a L3_PDU was discarded
                at the egress because the destination
                address was not assigned to the SNI."
        ::= { wfSmdsSwSubEntry 49 }

    wfSmdsSwEndpTable OBJECT-TYPE
        SYNTAX	SEQUENCE OF WfSmdsSwEndpEntry
        ACCESS	not-accessible
        STATUS	mandatory
        DESCRIPTION
                "The Parameters for the Endpoint table. An
                Endpoint is defined as an IP address, SMDS E.164
                address pair.  Endpoint ranges should never overlap."
        ::= { wfSmdsSwGroup 2 }

    wfSmdsSwEndpEntry OBJECT-TYPE
        SYNTAX	WfSmdsSwEndpEntry
        ACCESS	not-accessible
        STATUS	mandatory
        DESCRIPTION
                "The parameters for a particular Endpoint."
        INDEX	{ wfSmdsSwEndpE164AddrHigh,
    		  wfSmdsSwEndpE164AddrDelta,
    		  wfSmdsSwEndpInterfaceIndex }
        ::= { wfSmdsSwEndpTable 1 }

    WfSmdsSwEndpEntry ::= SEQUENCE {
    	    wfSmdsSwEndpDelete
    		INTEGER,
    	    wfSmdsSwEndpE164AddrHigh
    		OCTET STRING,
    	    wfSmdsSwEndpE164AddrDelta
    		OCTET STRING,
    	    wfSmdsSwEndpInterfaceIndex
    		INTEGER
        }

    wfSmdsSwEndpDelete OBJECT-TYPE
        SYNTAX	INTEGER {
    		    created(1),
    		    deleted(2)
    		}
        ACCESS	read-write
        STATUS	mandatory
        DESCRIPTION
                "Indication to delete this endpoint entry."
        DEFVAL	{ created }
        ::= { wfSmdsSwEndpEntry 1 }

    wfSmdsSwEndpE164AddrHigh OBJECT-TYPE
        SYNTAX	OCTET STRING (SIZE (8))
        ACCESS	read-only
        STATUS	mandatory
        DESCRIPTION
                "The High end of the E.164 address range for
                this endpoint information."
        ::= { wfSmdsSwEndpEntry 2 }

    wfSmdsSwEndpE164AddrDelta OBJECT-TYPE
        SYNTAX	OCTET STRING (SIZE (8))
        ACCESS	read-only
        STATUS	mandatory
        DESCRIPTION
                "The difference between wfSmdsSwEndpE164AddrHigh
                to the beginning of the endpoint information."
        ::= { wfSmdsSwEndpEntry 3 }

    wfSmdsSwEndpInterfaceIndex OBJECT-TYPE
        SYNTAX	INTEGER
        ACCESS	read-only
        STATUS	mandatory
        DESCRIPTION
                "This number indicates which SNI
                the endpoint information refers to."
        ::= { wfSmdsSwEndpEntry 4 }

    wfSmdsSwInterfaceTable OBJECT-TYPE
        SYNTAX	SEQUENCE OF WfSmdsSwInterfaceEntry
        ACCESS	not-accessible
        STATUS	mandatory
        DESCRIPTION
                "This is the Interface Table.
                This table also holds the Maximum Information Rate
                (MIR) information."
        ::= { wfSmdsSwGroup 3 }

    wfSmdsSwInterfaceEntry OBJECT-TYPE
        SYNTAX	WfSmdsSwInterfaceEntry
        ACCESS	not-accessible
        STATUS	mandatory
        DESCRIPTION
                "This table defines the IP addresses and what
                interfaces they are associated with."
        INDEX	{ wfSmdsSwInterfaceType,
    		  wfSmdsSwInterfaceIndex }
        ::= { wfSmdsSwInterfaceTable 1 }

    WfSmdsSwInterfaceEntry ::= SEQUENCE {
    	    wfSmdsSwInterfaceDelete
    		INTEGER,
    	    wfSmdsSwInterfaceType
    		INTEGER,
    	    wfSmdsSwInterfaceIndex
    		INTEGER,
    	    wfSmdsSwInterfaceIpAddr
    		IpAddress,
    	    wfSmdsSwInterfaceMIR
    		INTEGER,
    	    wfSmdsSwInterfaceCurrentRate
    		INTEGER
        }

    wfSmdsSwInterfaceDelete OBJECT-TYPE
        SYNTAX	INTEGER {
    		    created(1),
    		    deleted(2)
    		}
        ACCESS	read-write
        STATUS	mandatory
        DESCRIPTION
                "Indication to delete this interface entry."
        DEFVAL	{ created }
        ::= { wfSmdsSwInterfaceEntry 1 }

    wfSmdsSwInterfaceType OBJECT-TYPE
        SYNTAX	INTEGER {
    		    sni(1),
    		    ssi(2)
    		}
        ACCESS	read-only
        STATUS	mandatory
        DESCRIPTION
                "This number determines whether the interface
                information refers to an SNI, SSI, or ICI."
        ::= { wfSmdsSwInterfaceEntry 2 }

    wfSmdsSwInterfaceIndex OBJECT-TYPE
        SYNTAX	INTEGER
        ACCESS	read-only
        STATUS	mandatory
        DESCRIPTION
                "This number indicates which SNI, SSI, or
                ICI the interface information refers to."
        ::= { wfSmdsSwInterfaceEntry 3 }

    wfSmdsSwInterfaceIpAddr OBJECT-TYPE
        SYNTAX	IpAddress
        ACCESS	read-write
        STATUS	mandatory
        DESCRIPTION
                "IP Address associated with the interface."
        ::= { wfSmdsSwInterfaceEntry 4 }

    wfSmdsSwInterfaceMIR OBJECT-TYPE
        SYNTAX	INTEGER
        ACCESS	read-write
        STATUS	mandatory
        DESCRIPTION
                "This number represents the MIR in octets per second."
        ::= { wfSmdsSwInterfaceEntry 5 }

    wfSmdsSwInterfaceCurrentRate OBJECT-TYPE
        SYNTAX	INTEGER
        ACCESS	read-only
        STATUS	mandatory
        DESCRIPTION
                "This number indicates the current rate of traffic flow
                to the interface.  The software updates this counter.
                When this attribute exceeds wfSmdsSwInterfaceMIR
                traffic to the interface is dropped.  Periodically
                the sofware resets this counter to zero."
        ::= { wfSmdsSwInterfaceEntry 6 }

    wfSmdsSwAssocScrnTable OBJECT-TYPE
        SYNTAX	SEQUENCE OF WfSmdsSwAssocScrnEntry
        ACCESS	not-accessible
        STATUS	mandatory
        DESCRIPTION
                "This list identifies the associated SNI
                addresses per individualand group address screen.
                Different addresses on an SNI may be associated with
                different individual and group address screens (one
                individual address screen per associated address on
                an SNI, and one group address screen per associated
                address on an SNI )."
        ::= { wfSmdsSwGroup 4 }

    wfSmdsSwAssocScrnEntry OBJECT-TYPE
        SYNTAX	WfSmdsSwAssocScrnEntry
        ACCESS	not-accessible
        STATUS	mandatory
        DESCRIPTION
                "An SNI index, group and individual screening
                list index, and the associated addresses for
                the SNI for the address screens."
        INDEX	{ wfSmdsSwAssocScrnSniIndex,
    		  wfSmdsSwAssocScrnAddrInd,
    		  wfSmdsSwAssocScrnIndivIndex,
    		  wfSmdsSwAssocScrnGrpIndex }
        ::= { wfSmdsSwAssocScrnTable 1 }

    WfSmdsSwAssocScrnEntry ::= SEQUENCE {
    	    wfSmdsSwAssocScrnDelete
    		INTEGER,
    	    wfSmdsSwAssocScrnSniIndex
    		INTEGER,
    	    wfSmdsSwAssocScrnAddrInd
    		OCTET STRING,
    	    wfSmdsSwAssocScrnIndivIndex
    		INTEGER,
    	    wfSmdsSwAssocScrnGrpIndex
    		INTEGER
        }

    wfSmdsSwAssocScrnDelete OBJECT-TYPE
        SYNTAX	INTEGER {
    		    created(1),
    		    deleted(2)
    		}
        ACCESS	read-write
        STATUS	mandatory
        DESCRIPTION
                "Indication to delete this associated screen entry."
        DEFVAL	{ created }
        ::= { wfSmdsSwAssocScrnEntry 1 }

    wfSmdsSwAssocScrnSniIndex OBJECT-TYPE
        SYNTAX	INTEGER
        ACCESS	read-only
        STATUS	mandatory
        DESCRIPTION
                "The value of this object identifies the SIP Port
                interface for which this entry contains management
                information.  The value of this object for a
                particular interface has the same value as the
                ifIndex, defined in RFC1213, for the same
                interface."
        ::= { wfSmdsSwAssocScrnEntry 2 }

    wfSmdsSwAssocScrnAddrInd OBJECT-TYPE
        SYNTAX	OCTET STRING (SIZE (8))
        ACCESS	read-only
        STATUS	mandatory
        DESCRIPTION
                "The value of this object identifies one of the
                SMDS addresses for the SNI, identified by the
                wfSmdsSwAssocScrnSniIndex that belongs to this
                individual (or group) address screen
                (wfSmdsSwAssocScrnAddrInd).  This list will
                contain both individual and group addresses,
                because this list is used for both Destination
                Address Screening and Source Address Screening; the
                destination address in the L3_PDU that is
                undergoing Source Address Screening may be either a
                group or individual address that is assigned to
                that SNI.  One screen will have a maximum of 64
                associated addresses; up to a maximum of 16
                individual addresses identifying an SNI and up to a
                maximum of 48 group addresses identifying an SNI."
        ::= { wfSmdsSwAssocScrnEntry 3 }

    wfSmdsSwAssocScrnIndivIndex OBJECT-TYPE
        SYNTAX	INTEGER(1..4)
        ACCESS	read-only
        STATUS	mandatory
        DESCRIPTION
                "The value of this object identifies the individual
                address screening list.  There is at least one
                individual address screen and at most s individual
                address screens per SNI.  The initial value of s is
                defined to be 4.  In the future more screening
                lists per SNI may be allowed.  The values of this
                object correspond to the values of wfSmdsSwIAScrnIndex
                in the wfSmdsSwIAScrnTable."
        ::= { wfSmdsSwAssocScrnEntry 4 }

    wfSmdsSwAssocScrnGrpIndex OBJECT-TYPE
        SYNTAX	INTEGER(1..4)
        ACCESS	read-only
        STATUS	mandatory
        DESCRIPTION
                "The value of this object identifies the group
                address screening list.  There is at least one
                group address screen and at most s group address
                screens per SNI.  The initial value of s is defined
                to be 4.  In the future more screening lists per
                SNI may be allowed.  The values of this object
                correspond to the values of wfSmdsSwGAScrnIndex in the
                wfSmdsSwGAScrnTable. This field applies only to
                individual addresses on the SNI because it applies
                only to destination address screening of group addresses."
        ::= { wfSmdsSwAssocScrnEntry 5 }

    wfSmdsSwIAScrnTable OBJECT-TYPE
        SYNTAX	SEQUENCE OF WfSmdsSwIAScrnEntry
        ACCESS	not-accessible
        STATUS	mandatory
        DESCRIPTION
                "This list identifies the individual addresses
                that will be screened per individual address screen
                table.  The are up to s (s is equal to 4) individual
                address screens per SNI and at least one individual
                address screen per SNI.  The Individual Address
                Screens and the Group Address Screens together
                consist of up to n addresses.  The initial value of
                n is defined as 128. In the future a value of n up
                to 2048 may be supported.  The Individual Address
                Screen is used to perform Destination Address
                Screening for individually addressed data units and
                Source Address Screening for all data units.  The
                Group Address Screen is used to perform Destination
                Address Screening for group addressed data units."
        ::= { wfSmdsSwGroup 5 }

    wfSmdsSwIAScrnEntry OBJECT-TYPE
        SYNTAX	WfSmdsSwIAScrnEntry
        ACCESS	not-accessible
        STATUS	mandatory
        DESCRIPTION
                "An SNI index, a screening list index, the
                individual addresses to be screened for the
                individual address screen, and whether the screened
                address is valid or invalid."
        INDEX	{ wfSmdsSwIAScrnSniIndex,
    		  wfSmdsSwIAScrnIndex,
    		  wfSmdsSwIAScrnAddr }
        ::= { wfSmdsSwIAScrnTable 1 }

    WfSmdsSwIAScrnEntry ::= SEQUENCE {
    	    wfSmdsSwIAScrnDelete
    		INTEGER,
    	    wfSmdsSwIAScrnSniIndex
    		INTEGER,
    	    wfSmdsSwIAScrnIndex
    		INTEGER,
    	    wfSmdsSwIAScrnAddr
    		OCTET STRING
        }

    wfSmdsSwIAScrnDelete OBJECT-TYPE
        SYNTAX	INTEGER {
    		    created(1),
    		    deleted(2)
    		}
        ACCESS	read-write
        STATUS	mandatory
        DESCRIPTION
                "Indication to delete this IA screen entry."
        DEFVAL	{ created }
        ::= { wfSmdsSwIAScrnEntry 1 }

    wfSmdsSwIAScrnSniIndex OBJECT-TYPE
        SYNTAX	INTEGER
        ACCESS	read-only
        STATUS	mandatory
        DESCRIPTION
                "The value of this object identifies the SIP Port
                interface for which this entry contains management
                information.  The value of this object for a
                particular interface has the same value as the
                ifIndex, defined in RFC1213, for the same
                interface."
        ::= { wfSmdsSwIAScrnEntry 2 }

    wfSmdsSwIAScrnIndex OBJECT-TYPE
        SYNTAX	INTEGER(1..4)
        ACCESS	read-only
        STATUS	mandatory
        DESCRIPTION
                "The value of this object identifies the individual
                address screening list.  There are at least one
                individual address screen and at most s individual
                address screens per SNI.  The initial value of s is
                defined to be 4.  In the future more screening
                lists per SNI may be allowed.  The values of this
                object correspond to the values of wfSmdsSwScrnIndex in
                the wfSmdsSwScrnTable."
        ::= { wfSmdsSwIAScrnEntry 3 }

    wfSmdsSwIAScrnAddr OBJECT-TYPE
        SYNTAX	OCTET STRING (SIZE (8))
        ACCESS	read-only
        STATUS	mandatory
        DESCRIPTION
                "The value of this object identifies one of the
                individual addresses to be screened for source and
                destination address screening for the SNI
                identified by the wfSmdsSwIAScrnSniIndex and for the
                particular individual address screen
                (wfSmdsSwIAScrnIndex)."
        ::= { wfSmdsSwIAScrnEntry 4 }

    wfSmdsSwGAScrnTable OBJECT-TYPE
        SYNTAX	SEQUENCE OF WfSmdsSwGAScrnEntry
        ACCESS	not-accessible
        STATUS	mandatory
        DESCRIPTION
                "This list identifies the group addresses that
                will be screened per group address screen table.
                The are up to s (s is equal to 4) group address
                screens per SNI and at least one group address
                screen per SNI.  The Individual Address Screen and
                the Group Address Screen together consist of up to n
                addresses.  The initial value of n is defined as
                128. In the future a value of n up to 2048 may be
                supported.  The Individual Address Screen is used to
                perform Destination Address Screening for
                individually addressed data units and Source Address
                Screening for all data units.  The Group Address
                Screen is used to perform Destination Address
                Screening for group addressed data units."
        ::= { wfSmdsSwGroup 6 }

    wfSmdsSwGAScrnEntry OBJECT-TYPE
        SYNTAX	WfSmdsSwGAScrnEntry
        ACCESS	not-accessible
        STATUS	mandatory
        DESCRIPTION
                "An SNI index, a screening list index, the group
                addresses to be screened for the group address
                screen, and whether the screened address is valid
                or invalid."
        INDEX	{ wfSmdsSwGAScrnSniIndex,
    		  wfSmdsSwGAScrnIndex,
    		  wfSmdsSwGAScrnAddr }
        ::= { wfSmdsSwGAScrnTable 1 }

    WfSmdsSwGAScrnEntry ::= SEQUENCE {
    	    wfSmdsSwGAScrnDelete
    		INTEGER,
    	    wfSmdsSwGAScrnSniIndex
    		INTEGER,
    	    wfSmdsSwGAScrnIndex
    		INTEGER,
    	    wfSmdsSwGAScrnAddr
    		OCTET STRING
        }

    wfSmdsSwGAScrnDelete OBJECT-TYPE
        SYNTAX	INTEGER {
    		    created(1),
    		    deleted(2)
    		}
        ACCESS	read-write
        STATUS	mandatory
        DESCRIPTION
                "Indication to delete this GA screen entry."
        DEFVAL	{ created }
        ::= { wfSmdsSwGAScrnEntry 1 }

    wfSmdsSwGAScrnSniIndex OBJECT-TYPE
        SYNTAX	INTEGER
        ACCESS	read-only
        STATUS	mandatory
        DESCRIPTION
                "The value of this object identifies the SIP Port
                interface for which this entry contains management
                information.  The value of this object for a
                particular interface has the same value as the
                ifIndex, defined in RFC1213, for the same
                interface."
        ::= { wfSmdsSwGAScrnEntry 2 }

    wfSmdsSwGAScrnIndex OBJECT-TYPE
        SYNTAX	INTEGER(1..4)
        ACCESS	read-only
        STATUS	mandatory
        DESCRIPTION
                "The value of this object identifies the group
                address screening list.  There is at least one
                group address screen and at most s group address
                screens per SNI.  The initial value of s is defined
                to be 4.  In the future more screening lists per
                SNI may be allowed.  The values of this object
                correspond to the values of wfSmdsSwScrnIndex in the
                wfSmdsSwSmdsScrnTable."
        ::= { wfSmdsSwGAScrnEntry 3 }

    wfSmdsSwGAScrnAddr OBJECT-TYPE
        SYNTAX	OCTET STRING (SIZE (8))
        ACCESS	read-only
        STATUS	mandatory
        DESCRIPTION
                "The value of this object identifies one of the
                group addresses to be screened for destination
                address screening for the SNI identified by the
                wfSmdsSwGAScrnSniIndex and for the particular group
                address screen (wfSmdsSwGAScrnIndex)."
        ::= { wfSmdsSwGAScrnEntry 4 }

    wfSmdsSwGATable OBJECT-TYPE
        SYNTAX	SEQUENCE OF WfSmdsSwGAEntry
        ACCESS	not-accessible
        STATUS	mandatory
        DESCRIPTION
                "A table of all group addresses in the network and
                the associated individual addresses identified by
                each group address.  A group address identifies up
                to m individual addresses.  An SMDS SS supports up
                to n group addresses.  A group address can be
                identified by up to p individual addresses.  A
                particular SNI is identified by up to 48 group
                addresses.  The initial values of m, n, and p are
                defined as 128, 1024, and 32, respectively.   In the
                future values of m and n of 2048 and 8192,
                respectively, may be supported."
        ::= { wfSmdsSwGroup 7 }

    wfSmdsSwGAEntry OBJECT-TYPE
        SYNTAX	WfSmdsSwGAEntry
        ACCESS	not-accessible
        STATUS	mandatory
        DESCRIPTION
                "A Group Address and an address in that group and
                whether that association is valid or invalid."
        INDEX	{ wfSmdsSwGASSI,
    		  wfSmdsSwGAGroupAddress,
    		  wfSmdsSwGAGroupMember }
        ::= { wfSmdsSwGATable 1 }

    WfSmdsSwGAEntry ::= SEQUENCE {
    	    wfSmdsSwGADelete
    		INTEGER,
    	    wfSmdsSwGASSI
    		INTEGER,
    	    wfSmdsSwGAGroupAddress
    		OCTET STRING,
    	    wfSmdsSwGAGroupMember
    		OCTET STRING
        }

    wfSmdsSwGADelete OBJECT-TYPE
        SYNTAX	INTEGER {
    		    created(1),
    		    deleted(2)
    		}
        ACCESS	read-write
        STATUS	mandatory
        DESCRIPTION
                "Indication to delete this group address entry."
        DEFVAL	{ created }
        ::= { wfSmdsSwGAEntry 1 }

    wfSmdsSwGASSI OBJECT-TYPE
        SYNTAX	INTEGER
        ACCESS	read-only
        STATUS	mandatory
        DESCRIPTION
                "The SSI associated with this Group Address.
                An SSI of 0 is used to indicate that all interfaces
                can use the group address.  An SSI other than 0
                indicates that only the SSI, or an SNI associated
                with the SSI should use the group."
        ::= { wfSmdsSwGAEntry 2 }

    wfSmdsSwGAGroupAddress OBJECT-TYPE
        SYNTAX	OCTET STRING (SIZE (8))
        ACCESS	read-only
        STATUS	mandatory
        DESCRIPTION
                "A Group Address."
        ::= { wfSmdsSwGAEntry 3 }

    wfSmdsSwGAGroupMember OBJECT-TYPE
        SYNTAX	OCTET STRING (SIZE (8))
        ACCESS	read-only
        STATUS	mandatory
        DESCRIPTION
                "An individual SMDS address that belongs to this
                Group Address."
        ::= { wfSmdsSwGAEntry 4 }

    wfSmdsSwCurUsageTable OBJECT-TYPE
        SYNTAX	SEQUENCE OF WfSmdsSwCurUsageEntry
        ACCESS	not-accessible
        STATUS	mandatory
        DESCRIPTION
                "This table contains the Current Usage Data.
                This is the interface between Billing and Switching.
                The Switch gates create these records.  The Billing gates
                collect them to create billing data."
        ::= { wfSmdsSwGroup 8 }

    wfSmdsSwCurUsageEntry OBJECT-TYPE
        SYNTAX	WfSmdsSwCurUsageEntry
        ACCESS	not-accessible
        STATUS	mandatory
        DESCRIPTION
                "The usage data for the current usage period
                indexed by destination,source address."
        INDEX	{ wfSmdsSwCurUsageSni,
    		  wfSmdsSwCurUsageDestAddr,
    		  wfSmdsSwCurUsageSrcAddr }
        ::= { wfSmdsSwCurUsageTable 1 }

    WfSmdsSwCurUsageEntry ::= SEQUENCE {
    	    wfSmdsSwCurUsageDelete
    		INTEGER,
    	    wfSmdsSwCurUsageSni
    		INTEGER,
    	    wfSmdsSwCurUsageDestAddr
    		OCTET STRING,
    	    wfSmdsSwCurUsageSrcAddr
    		OCTET STRING,
    	    wfSmdsSwCurUsageGrpIndAddr
    		OCTET STRING,
    	    wfSmdsSwCurUsageNumL3Pdu
    		Counter,
    	    wfSmdsSwCurUsageNumOctet
    		Counter,
    	    wfSmdsSwCurUsageToBeDeleted
    		INTEGER
        }

    wfSmdsSwCurUsageDelete OBJECT-TYPE
        SYNTAX	INTEGER {
    		    created(1),
    		    deleted(2)
    		}
        ACCESS	read-write
        STATUS	obsolete
        DESCRIPTION
                "Indication to delete this current usage entry."
        DEFVAL	{ created }
        ::= { wfSmdsSwCurUsageEntry 1 }

    wfSmdsSwCurUsageSni OBJECT-TYPE
        SYNTAX	INTEGER(1..65535)
        ACCESS	read-only
        STATUS	mandatory
        DESCRIPTION
                "The SNI number of the interface generating the
                usage information"
        ::= { wfSmdsSwCurUsageEntry 2 }

    wfSmdsSwCurUsageDestAddr OBJECT-TYPE
        SYNTAX	OCTET STRING (SIZE (8))
        ACCESS	read-only
        STATUS	mandatory
        DESCRIPTION
                "The destination address of a SMDS group or
                individual E.164 address."
        ::= { wfSmdsSwCurUsageEntry 3 }

    wfSmdsSwCurUsageSrcAddr OBJECT-TYPE
        SYNTAX	OCTET STRING (SIZE (8))
        ACCESS	read-only
        STATUS	mandatory
        DESCRIPTION
                "The source address of a SMDS individual
                E.164 address."
        ::= { wfSmdsSwCurUsageEntry 4 }

    wfSmdsSwCurUsageGrpIndAddr OBJECT-TYPE
        SYNTAX	OCTET STRING
        ACCESS	read-only
        STATUS	mandatory
        DESCRIPTION
                "When the destination address of an L3_PDU is
                a group address, this attribute is set to one of
                the E.164 individual addresses that is in the
                group address and on the destination SNI."
        ::= { wfSmdsSwCurUsageEntry 5 }

    wfSmdsSwCurUsageNumL3Pdu OBJECT-TYPE
        SYNTAX	Counter
        ACCESS	read-only
        STATUS	mandatory
        DESCRIPTION
                "This number represents the number of billable
                L3_PDUs counted by the circuit during the most recent
                collection interval."
        ::= { wfSmdsSwCurUsageEntry 6 }

    wfSmdsSwCurUsageNumOctet OBJECT-TYPE
        SYNTAX	Counter
        ACCESS	read-only
        STATUS	mandatory
        DESCRIPTION
                "This number represents the number of billable
                octets counted by the circuit during the most recent
                collection interval."
        ::= { wfSmdsSwCurUsageEntry 7 }

    wfSmdsSwCurUsageToBeDeleted OBJECT-TYPE
        SYNTAX	INTEGER {
    		    created(1),
    		    deleted(2)
    		}
        ACCESS	read-only
        STATUS	mandatory
        DESCRIPTION
                "Indication to billing to delete
                this current usage entry."
        DEFVAL	{ created }
        ::= { wfSmdsSwCurUsageEntry 8 }

    wfSmdsSwUsage	OBJECT IDENTIFIER ::= { wfSmdsSwGroup 9 }

    wfSmdsSwUsageEnable OBJECT-TYPE
        SYNTAX	INTEGER {
    		    enabled(1),
    		    disabled(2)
    		}
        ACCESS	read-write
        STATUS	mandatory
        DESCRIPTION
                "Enable/Disable SMDS_SW billing."
        DEFVAL	{ enabled }
        ::= { wfSmdsSwUsage 1 }

    wfSmdsSwUsageVolume OBJECT-TYPE
        SYNTAX	INTEGER(0..14)
        ACCESS	read-write
        STATUS	mandatory
        DESCRIPTION
                "Indicates the file system volume number to which the
                billing usage data files will be written.  The volume
                number corresponds to the slot number on which the
                volume resides.
                Note: Value 0 has the special meaning that no
                      'Store' and 'Flush' operations will take
                      place.  This translates to no Billing data
                      will be written to the local file system.
                      'Update' operations will still be performed on
                      each local slot.  Full Billing statistics
                      will still be available in the wfSmdsSwUsageTable
                      MIB."
        ::= { wfSmdsSwUsage 2 }

    wfSmdsSwUsageVolumeBackup OBJECT-TYPE
        SYNTAX	INTEGER(0..14)
        ACCESS	read-write
        STATUS	mandatory
        DESCRIPTION
                "Indicates the backup volume if wfSmdsSwUsageVolume
                becomes inoperative.
                Note: This feature is not implemented in this release."
        ::= { wfSmdsSwUsage 3 }

    wfSmdsSwUsageDirectory OBJECT-TYPE
        SYNTAX	DisplayString
        ACCESS	read-write
        STATUS	mandatory
        DESCRIPTION
                "The name of the directory where the billing usage data
                files are stored. "
        ::= { wfSmdsSwUsage 4 }

    wfSmdsSwUsageFilePrefix OBJECT-TYPE
        SYNTAX	DisplayString
        ACCESS	read-write
        STATUS	mandatory
        DESCRIPTION
                "The base name of billing usage data files."
        ::= { wfSmdsSwUsage 5 }

    wfSmdsSwUsageTimerInterval OBJECT-TYPE
        SYNTAX	INTEGER(1..60)
        ACCESS	read-write
        STATUS	mandatory
        DESCRIPTION
                "This number determines the timer interval (number
                of seconds) unit for the Billing process to perform
                its various timer driven tasks. i.e. updating billing
                usage data, writing billing usage data to file system
                and file system management activities."
        DEFVAL	{ 1 }
        ::= { wfSmdsSwUsage 6 }

    wfSmdsSwUsageUpdateInterval OBJECT-TYPE
        SYNTAX	INTEGER(1..2147483647)
        ACCESS	read-write
        STATUS	mandatory
        DESCRIPTION
                "This number specifies the interval (number of minutes)
                for the Billing process to collect and update billing
                usage data in the wfSmdsSwUsage MIB.
                Note: When converted to seconds, this must be a multiple
                of wfSmdsSwUsageTimerInterval. "
        DEFVAL	{ 10 }
        ::= { wfSmdsSwUsage 7 }

    wfSmdsSwUsageStoreInterval OBJECT-TYPE
        SYNTAX	INTEGER(1..2147483647)
        ACCESS	read-write
        STATUS	mandatory
        DESCRIPTION
                "This number specifies the interval (number of minutes)
                for the Billing process to write billing usage data on
                to the file system from the wfSmdsSwUsage MIB.
                Note: When converted to seconds, this must be a multiple
                of wfSmdsSwUsageTimerInterval. "
        DEFVAL	{ 10 }
        ::= { wfSmdsSwUsage 8 }

    wfSmdsSwUsageFlushInterval OBJECT-TYPE
        SYNTAX	INTEGER(1..2147483647)
        ACCESS	read-write
        STATUS	mandatory
        DESCRIPTION
                "This number specifies the interval (number of minutes)
                for the Billing process to write billing usage data on
                to the file system from the wfSmdsSwUsage MIB followed
                by zeroing the wfSmdsSwUsage MIB.
                Note: When converted to seconds, this must be a multiple of
                wfSmdsSwUsageTimerInterval. "
        DEFVAL	{ 60 }
        ::= { wfSmdsSwUsage 9 }

    wfSmdsSwUsageCleanupInterval OBJECT-TYPE
        SYNTAX	INTEGER(1..2147483647)
        ACCESS	read-write
        STATUS	mandatory
        DESCRIPTION
                "This is the interval (number of minutes) for the Billing
                process to check and delete old billing usage data files.
                Note: When converted to seconds, this must be a multilple
                of wfSmdsSwUsageTimerInterval. "
        DEFVAL	{ 60 }
        ::= { wfSmdsSwUsage 10 }

    wfSmdsSwUsageLocalTimeZone OBJECT-TYPE
        SYNTAX	INTEGER
        ACCESS	read-only
        STATUS	mandatory
        DESCRIPTION
                "Indicates local time zone of the switch"
        ::= { wfSmdsSwUsage 11 }

    wfSmdsSwUsageUpdateTimeStamp OBJECT-TYPE
        SYNTAX	TimeTicks
        ACCESS	read-only
        STATUS	mandatory
        DESCRIPTION
                "Time stamp of last wfSmdsSwUsageUpdateInterval timer
                expiration or the starting time of the current
                wfSmdsSwUsageUpdateInterval.  This value is number
                of seconds since midnight Jan 1, 1976 (GMT). "
        ::= { wfSmdsSwUsage 12 }

    wfSmdsSwUsageStoreTimeStamp OBJECT-TYPE
        SYNTAX	TimeTicks
        ACCESS	read-only
        STATUS	mandatory
        DESCRIPTION
                "Time stamp of last wfSmdsSwUsageStoreInterval
                timer expiration or the starting time of the current
                wfSmdsSwUsageStoreInterval.  This value is number
                of seconds since midnight Jan. 1, 1976 (GMT). "
        ::= { wfSmdsSwUsage 13 }

    wfSmdsSwUsageFlushTimeStamp OBJECT-TYPE
        SYNTAX	TimeTicks
        ACCESS	read-only
        STATUS	mandatory
        DESCRIPTION
                "Time stamp of last wfSmdsSwUsageFlushInterval
                timer expiration or the starting time of the current
                wfSmdsSwUsageFlushInterval.  This value is
                number of seconds since midnight Jan. 1, 1976 (GMT). "
        ::= { wfSmdsSwUsage 14 }

    wfSmdsSwUsageCleanupTimeStamp OBJECT-TYPE
        SYNTAX	TimeTicks
        ACCESS	read-only
        STATUS	mandatory
        DESCRIPTION
                "Time stamp of last wfSmdsSwUsageCleanupInterval
                timer expiration or the starting time of the current
                wfSmdsSwUsageCleanupInterval.  This value is number
                of seconds since midnight Jan. 1, 1976 (GMT). "
        ::= { wfSmdsSwUsage 15 }

    wfSmdsSwUsageUpdateData OBJECT-TYPE
        SYNTAX	INTEGER
        ACCESS	read-write
        STATUS	mandatory
        DESCRIPTION
                "Setting this attribute to a non-zero value will cause
                an immediate updating of the billing usage data.
                Once activated, this attribute should be reset to zero
                to allow subsequent activations. "
        ::= { wfSmdsSwUsage 16 }

    wfSmdsSwUsageStoreData OBJECT-TYPE
        SYNTAX	INTEGER
        ACCESS	read-write
        STATUS	mandatory
        DESCRIPTION
                "Setting this attribute to a non-zero value will cause
                an immediate updating and writing of the billing
                usage data. Once activated, this attribute should
                be reset to zero to allow subsequent activations. "
        ::= { wfSmdsSwUsage 17 }

    wfSmdsSwUsageFlushData OBJECT-TYPE
        SYNTAX	INTEGER
        ACCESS	read-write
        STATUS	mandatory
        DESCRIPTION
                "Setting this attribute to a non-zero value will cause
                an immediate updating and writing of the billing usage
                data and followed by zeroing the wfSmdsSwBillingUsage
                MIB. Once activated, this attribute should be reset
                to zero to allow subsequent activations. "
        ::= { wfSmdsSwUsage 18 }

    wfSmdsSwUsageFileCleanup OBJECT-TYPE
        SYNTAX	INTEGER
        ACCESS	read-write
        STATUS	mandatory
        DESCRIPTION
                "Setting this attribute to a non-zero value will cause
                an immediate checking and deleting old billing usage
                data files. Once activated, this attribute should
                be reset to zero to allow subsequent activations. "
        ::= { wfSmdsSwUsage 19 }

    wfSmdsSwUsageState OBJECT-TYPE
        SYNTAX	INTEGER {
    		    up(1),
    		    down(2),
    		    init(3),
    		    notpresent(4)
    		}
        ACCESS	read-only
        STATUS	mandatory
        DESCRIPTION
                "current state of SMDS_SW billing."
        DEFVAL	{ notpresent }
        ::= { wfSmdsSwUsage 20 }

    wfSmdsSwUsageCurVolume OBJECT-TYPE
        SYNTAX	INTEGER(0..14)
        ACCESS	read-only
        STATUS	mandatory
        DESCRIPTION
                "current file system volume number used. This
                number is the same as wfSmdsSwUsageVolume except
                when the user sets wfSmdsSwUsageVolume to an
                invalid number."
        ::= { wfSmdsSwUsage 21 }

    wfSmdsSwUsageCurVolumeBackup OBJECT-TYPE
        SYNTAX	INTEGER(0..14)
        ACCESS	read-only
        STATUS	mandatory
        DESCRIPTION
                "curent backup file system volume number used. This
                number is the same as wfSmdsSwUsageVolumeBackUp except
                when the user sets wfSmdsSwUsageVolume to an
                invalid number.
                Note: This feature is not implemented in this release."
        ::= { wfSmdsSwUsage 22 }

    wfSmdsSwUsageCurDirectory OBJECT-TYPE
        SYNTAX	DisplayString
        ACCESS	read-only
        STATUS	mandatory
        DESCRIPTION
                "current directory name used. This number is the
                same as wfSmdsSwUsageDirectory except when the user
                sets wfSmdsSwUsageDirectory to an invalid name."
        ::= { wfSmdsSwUsage 23 }

    wfSmdsSwUsageCurFilePrefix OBJECT-TYPE
        SYNTAX	DisplayString
        ACCESS	read-only
        STATUS	mandatory
        DESCRIPTION
                "current base file name used. This number is the
                same as wfSmdsSwUsageFilePrefix except when the user
                sets wfSmdsSwUsageFilePrefix to an invalid name."
        ::= { wfSmdsSwUsage 24 }

    wfSmdsSwUsageCurTimerInterval OBJECT-TYPE
        SYNTAX	INTEGER(1..60)
        ACCESS	read-only
        STATUS	mandatory
        DESCRIPTION
                "current timer interval number used. This number is
                the same as wfSmdsSwUsageTimerInterval except when the
                user sets wfSmdsSwUsageTimerInterval to an invalid value."
        DEFVAL	{ 1 }
        ::= { wfSmdsSwUsage 25 }

    wfSmdsSwUsageCurUpdateInterval OBJECT-TYPE
        SYNTAX	INTEGER(1..2147483647)
        ACCESS	read-only
        STATUS	mandatory
        DESCRIPTION
                "current update interval number used. This number is
                the same as wfSmdsSwUsageUpdateInterval except when the
                user sets wfSmdsSwUsageUpdateInterval to an invalid value."
        DEFVAL	{ 10 }
        ::= { wfSmdsSwUsage 26 }

    wfSmdsSwUsageCurStoreInterval OBJECT-TYPE
        SYNTAX	INTEGER(1..2147483647)
        ACCESS	read-only
        STATUS	mandatory
        DESCRIPTION
                "current store timer interval number used. This
                number is the same as wfSmdsSwUsageStoreInterval
                except when the user sets wfSmdsSwUsageStoreInterval
                to an invalid value."
        DEFVAL	{ 10 }
        ::= { wfSmdsSwUsage 27 }

    wfSmdsSwUsageCurFlushInterval OBJECT-TYPE
        SYNTAX	INTEGER(1..2147483647)
        ACCESS	read-only
        STATUS	mandatory
        DESCRIPTION
                "current flush timer interval number used. This
                number is the same as wfSmdsSwUsageFlushInterval
                except when the user sets wfSmdsSwUsageFlushInterval
                to an invalid value."
        DEFVAL	{ 60 }
        ::= { wfSmdsSwUsage 28 }

    wfSmdsSwUsageCurCleanupInterval OBJECT-TYPE
        SYNTAX	INTEGER(1..2147483647)
        ACCESS	read-only
        STATUS	mandatory
        DESCRIPTION
                "current file cleanup timer interval number used. This
                number is the same as wfSmdsSwUsageCleanupInterval
                except when the user sets wfSmdsSwUsageCleanupInterval
                to an invalid value."
        DEFVAL	{ 60 }
        ::= { wfSmdsSwUsage 29 }

    wfSmdsSwUsageDebug OBJECT-TYPE
        SYNTAX	INTEGER {
    		    enabled(1),
    		    disabled(2)
    		}
        ACCESS	read-write
        STATUS	mandatory
        DESCRIPTION
                "Enable/Disable printing of debug edl (trap)
                messages.
                NOTE:  Do not enable this attribute in operational enviornment
                       as it will likely flood the logging facility.  This
                       attribute is reserved for specialized debugging in a
                       controlled lab enviornment."
        DEFVAL	{ disabled }
        ::= { wfSmdsSwUsage 30 }

    wfSmdsSwUsageCurDebug OBJECT-TYPE
        SYNTAX	INTEGER {
    		    enabled(1),
    		    disabled(2)
    		}
        ACCESS	read-only
        STATUS	mandatory
        DESCRIPTION
                "current debug value used. This value is the
                same as wfSmdsSwUsageDebug except when the user
                sets wfSmdsSwUsageDeubg to an invalid value."
        DEFVAL	{ disabled }
        ::= { wfSmdsSwUsage 31 }

    wfSmdsSwUsageSwitchId OBJECT-TYPE
        SYNTAX	INTEGER
        ACCESS	read-only
        STATUS	mandatory
        DESCRIPTION
                "switch id used in the billing usage data file."
        ::= { wfSmdsSwUsage 32 }

    wfSmdsSwUsageNumEntries OBJECT-TYPE
        SYNTAX	INTEGER
        ACCESS	read-only
        STATUS	mandatory
        DESCRIPTION
                "number of entries in wfSmdsSwUsageTable"
        ::= { wfSmdsSwUsage 33 }

    wfSmdsSwUsageTable OBJECT-TYPE
        SYNTAX	SEQUENCE OF WfSmdsSwUsageEntry
        ACCESS	not-accessible
        STATUS	mandatory
        DESCRIPTION
                "The Billing Usage Table."
        ::= { wfSmdsSwGroup 10 }

    wfSmdsSwUsageEntry OBJECT-TYPE
        SYNTAX	WfSmdsSwUsageEntry
        ACCESS	not-accessible
        STATUS	mandatory
        DESCRIPTION
                "The parameters for Billing Usage."
        INDEX	{ wfSmdsSwUsageSni,
    		  wfSmdsSwUsageDestAddr,
    		  wfSmdsSwUsageSrcAddr }
        ::= { wfSmdsSwUsageTable 1 }

    WfSmdsSwUsageEntry ::= SEQUENCE {
    	    wfSmdsSwUsageDelete
    		INTEGER,
    	    wfSmdsSwUsageSni
    		INTEGER,
    	    wfSmdsSwUsageDestAddr
    		OCTET STRING,
    	    wfSmdsSwUsageSrcAddr
    		OCTET STRING,
    	    wfSmdsSwUsageStartTimeStampHigh
    		INTEGER,
    	    wfSmdsSwUsageStartTimeStampLow
    		INTEGER,
    	    wfSmdsSwUsageEndTimeStampHigh
    		INTEGER,
    	    wfSmdsSwUsageEndTimeStampLow
    		INTEGER,
    	    wfSmdsSwUsageSentL3PduHigh
    		INTEGER,
    	    wfSmdsSwUsageSentL3PduLow
    		INTEGER,
    	    wfSmdsSwUsageSentOctetHigh
    		INTEGER,
    	    wfSmdsSwUsageSentOctetLow
    		INTEGER,
    	    wfSmdsSwUsageLastL3PduHigh
    		INTEGER,
    	    wfSmdsSwUsageLastL3PduLow
    		INTEGER,
    	    wfSmdsSwUsageLastOctetHigh
    		INTEGER,
    	    wfSmdsSwUsageLastOctetLow
    		INTEGER,
    	    wfSmdsSwUsageGrpIndAddr
    		OCTET STRING
        }

    wfSmdsSwUsageDelete OBJECT-TYPE
        SYNTAX	INTEGER {
    		    created(1),
    		    deleted(2)
    		}
        ACCESS	read-only
        STATUS	mandatory
        DESCRIPTION
                "Indicates status of this entry. SMDS_SW_USAGE_CREATED
                is the normal case.  SMDS_SW_USAGE_DELETED means this
                billing instance will be deleted at the end of
                the next wfSmdsSwUsageFlush period after this
                billing record is written out to the file system."
        DEFVAL	{ created }
        ::= { wfSmdsSwUsageEntry 1 }

    wfSmdsSwUsageSni OBJECT-TYPE
        SYNTAX	INTEGER
        ACCESS	read-only
        STATUS	mandatory
        DESCRIPTION
                "The circuit number of the interface generating the
                usage information"
        ::= { wfSmdsSwUsageEntry 2 }

    wfSmdsSwUsageDestAddr OBJECT-TYPE
        SYNTAX	OCTET STRING (SIZE (8))
        ACCESS	read-only
        STATUS	mandatory
        DESCRIPTION
                "Instance identifier; the destination address of an L3_PDU.
                The SMDS Switch collects usage data based on the
                destination/source address pair."
        ::= { wfSmdsSwUsageEntry 3 }

    wfSmdsSwUsageSrcAddr OBJECT-TYPE
        SYNTAX	OCTET STRING (SIZE (8))
        ACCESS	read-only
        STATUS	mandatory
        DESCRIPTION
                "Instance identifier; the source address of an L3_PDU.
                The SMDS Switch collects usage data based on the
                destination/source address pair."
        ::= { wfSmdsSwUsageEntry 4 }

    wfSmdsSwUsageStartTimeStampHigh OBJECT-TYPE
        SYNTAX	INTEGER
        ACCESS	read-only
        STATUS	mandatory
        DESCRIPTION
                "Time stamp of the starting time (the high 32 bits)
                of last billing usage interval.  This value is the
                number of 1/100th seconds since
                midnight Jan 1, 1976 (GMT)."
        ::= { wfSmdsSwUsageEntry 5 }

    wfSmdsSwUsageStartTimeStampLow OBJECT-TYPE
        SYNTAX	INTEGER
        ACCESS	read-only
        STATUS	mandatory
        DESCRIPTION
                "Time stamp of the starting time (the low 32 bits)
                of last billing usage interval.  This value is the
                number of 1/100th seconds since
                midnight Jan 1, 1976 (GMT)."
        ::= { wfSmdsSwUsageEntry 6 }

    wfSmdsSwUsageEndTimeStampHigh OBJECT-TYPE
        SYNTAX	INTEGER
        ACCESS	read-only
        STATUS	mandatory
        DESCRIPTION
                "Time stamp of the ending time (the high 32 bits)
                of last billing usage interval.  This value is the
                number of 1/100th seconds since
                midnight Jan 1, 1976 (GMT)."
        ::= { wfSmdsSwUsageEntry 7 }

    wfSmdsSwUsageEndTimeStampLow OBJECT-TYPE
        SYNTAX	INTEGER
        ACCESS	read-only
        STATUS	mandatory
        DESCRIPTION
                "Time stamp of the ending time (the low 32 bits)
                of last billing usage interval.  This value is the
                number of 1/100th seconds since
                midnight Jan 1, 1976 (GMT)."
        ::= { wfSmdsSwUsageEntry 8 }

    wfSmdsSwUsageSentL3PduHigh OBJECT-TYPE
        SYNTAX	INTEGER
        ACCESS	read-only
        STATUS	mandatory
        DESCRIPTION
                "Number (the high 32 bits) of L3_PDUs
                sent to the CPE between
                wfSmdsSwUsageStartTimeStamp and
                wfSmdsSwUsageEndTimeStamp."
        ::= { wfSmdsSwUsageEntry 9 }

    wfSmdsSwUsageSentL3PduLow OBJECT-TYPE
        SYNTAX	INTEGER
        ACCESS	read-only
        STATUS	mandatory
        DESCRIPTION
                "Number (the low 32 bits) of L3_PDUs
                sent to the CPE between
                wfSmdsSwUsageStartTimeStamp and
                wfSmdsSwUsageEndTimeStamp."
        ::= { wfSmdsSwUsageEntry 10 }

    wfSmdsSwUsageSentOctetHigh OBJECT-TYPE
        SYNTAX	INTEGER
        ACCESS	read-only
        STATUS	mandatory
        DESCRIPTION
                "Number (the high 32 bits) of octets
                sent to the CPE between
                wfSmdsSwUsageStartTimeStamp and
                wfSmdsSwUsageEndTimeStamp."
        ::= { wfSmdsSwUsageEntry 11 }

    wfSmdsSwUsageSentOctetLow OBJECT-TYPE
        SYNTAX	INTEGER
        ACCESS	read-only
        STATUS	mandatory
        DESCRIPTION
                "Number (the low 32 bits) of octets
                sent to the CPE between
                wfSmdsSwUsageStartTimeStamp and
                wfSmdsSwUsageEndTimeStamp."
        ::= { wfSmdsSwUsageEntry 12 }

    wfSmdsSwUsageLastL3PduHigh OBJECT-TYPE
        SYNTAX	INTEGER
        ACCESS	read-only
        STATUS	mandatory
        DESCRIPTION
                "The (high 32 bits) value of
                wfSmdsSwCurUsageNumL3Pdu value at
                wfSmdsSwUsageEndTimeStamp.
                Note:  Since wfSmdsSwCurUsageNumL3Pdu
                is a 32-bit COUNTER, this is really a counter
                keeping track of number of times
                wfSmdsSwCurUsageNumL3Pdu has wrapped around."
        ::= { wfSmdsSwUsageEntry 13 }

    wfSmdsSwUsageLastL3PduLow OBJECT-TYPE
        SYNTAX	INTEGER
        ACCESS	read-only
        STATUS	mandatory
        DESCRIPTION
                "The (low 32 bits) value of
                wfSmdsSwCurUsageNumL3Pdu value at
                wfSmdsSwUsageEndTimeStamp."
        ::= { wfSmdsSwUsageEntry 14 }

    wfSmdsSwUsageLastOctetHigh OBJECT-TYPE
        SYNTAX	INTEGER
        ACCESS	read-only
        STATUS	mandatory
        DESCRIPTION
                "The (high 32 bits) value of
                wfSmdsSwCurUsageNumOctets value at
                wfSmdsSwUsageEndTimeStamp.
                Note:  Since wfSmdsSwCurUsageNumOctets
                is a 32-bit COUNTER, this is really a counter
                keeping track of number of times
                wfSmdsSwCurUsageNumOctets has wrapped around."
        ::= { wfSmdsSwUsageEntry 15 }

    wfSmdsSwUsageLastOctetLow OBJECT-TYPE
        SYNTAX	INTEGER
        ACCESS	read-only
        STATUS	mandatory
        DESCRIPTION
                "The (low 32 bits) value of
                wfSmdsSwCurUsageNumOctets value at
                wfSmdsSwUsageEndTimeStamp."
        ::= { wfSmdsSwUsageEntry 16 }

    wfSmdsSwUsageGrpIndAddr OBJECT-TYPE
        SYNTAX	OCTET STRING
        ACCESS	read-only
        STATUS	mandatory
        DESCRIPTION
                "When the destination address of an L3_PDU is
                a group address, this attribute is set to one of
                the E.164 individual addresses that is in the
                group address and on the destination SNI."
        ::= { wfSmdsSwUsageEntry 17 }

    wfSmdsSwSsiSniTable OBJECT-TYPE
        SYNTAX	SEQUENCE OF WfSmdsSwSsiSniEntry
        ACCESS	not-accessible
        STATUS	mandatory
        DESCRIPTION
                "The Parameters for the SSI/SNI Object.
                This object associates SNI's with SSI's for
                Bellcore TR-TSV-001239 compliance."
        ::= { wfSmdsSwGroup 11 }

    wfSmdsSwSsiSniEntry OBJECT-TYPE
        SYNTAX	WfSmdsSwSsiSniEntry
        ACCESS	not-accessible
        STATUS	mandatory
        DESCRIPTION
                "The parameters for a particular SSI/SNI."
        INDEX	{ wfSmdsSwSsiSniSSI,
    		  wfSmdsSwSsiSniSNI }
        ::= { wfSmdsSwSsiSniTable 1 }

    WfSmdsSwSsiSniEntry ::= SEQUENCE {
    	    wfSmdsSwSsiSniDelete
    		INTEGER,
    	    wfSmdsSwSsiSniSSI
    		INTEGER,
    	    wfSmdsSwSsiSniSNI
    		INTEGER
        }

    wfSmdsSwSsiSniDelete OBJECT-TYPE
        SYNTAX	INTEGER {
    		    created(1),
    		    deleted(2)
    		}
        ACCESS	read-write
        STATUS	mandatory
        DESCRIPTION
                "Indication to delete this SSI/SNI entry."
        DEFVAL	{ created }
        ::= { wfSmdsSwSsiSniEntry 1 }

    wfSmdsSwSsiSniSSI OBJECT-TYPE
        SYNTAX	INTEGER
        ACCESS	read-only
        STATUS	mandatory
        DESCRIPTION
                "An SSI."
        ::= { wfSmdsSwSsiSniEntry 2 }

    wfSmdsSwSsiSniSNI OBJECT-TYPE
        SYNTAX	INTEGER
        ACCESS	read-only
        STATUS	mandatory
        DESCRIPTION
                "An SNI."
        ::= { wfSmdsSwSsiSniEntry 3 }

    END  -- Wellfleet-SWSMDS-MIB
