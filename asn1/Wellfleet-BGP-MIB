Wellfleet-BGP-MIB DEFINITIONS ::= BEGIN

-- Created by mdl2asn version 3.1
-- Creation date: Wed Aug 30 16:38:26 EDT 1995


    IMPORTS

      IpAddress, Counter, Gauge
        FROM RFC1155-SMI
      DisplayString
        FROM RFC1213-MIB
      OBJECT-TYPE
        FROM RFC-1212
      wfBgpGroup
        FROM Wellfleet-COMMON-MIB;


    wfBgpGeneralGroup     OBJECT IDENTIFIER ::= { wfBgpGroup 1 }
    wfBgp		OBJECT IDENTIFIER ::= { wfBgpGeneralGroup 1 }
    wfBgp3Group           OBJECT IDENTIFIER ::= { wfBgpGroup 2 }
    wfBgp4Group           OBJECT IDENTIFIER ::= { wfBgpGroup 3 }


    wfBgpDelete OBJECT-TYPE
        SYNTAX	INTEGER {
    		    created(1),
    		    deleted(2)
    		}
        ACCESS	read-write
        STATUS	mandatory
        DESCRIPTION
                "Create/Delete parameter for determining whether or not BGP is
                configured on this router."
        DEFVAL	{ created }
        ::= { wfBgp 1 }

    wfBgpDisable OBJECT-TYPE
        SYNTAX	INTEGER {
    		    enabled(1),
    		    disabled(2)
    		}
        ACCESS	read-write
        STATUS	mandatory
        DESCRIPTION
                "Enable/Disable parameter for determining whether or not to allow any
                versions of BGP to start up."
        DEFVAL	{ enabled }
        ::= { wfBgp 2 }

    wfBgpState OBJECT-TYPE
        SYNTAX	INTEGER {
    		    up(1),
    		    down(2),
    		    init(3),
    		    invalid(4),
    		    notpresent(5)
    		}
        ACCESS	read-only
        STATUS	mandatory
        DESCRIPTION
                "the administrative state of BGP"
        DEFVAL	{ notpresent }
        ::= { wfBgp 3 }

    wfBgpIdentifier OBJECT-TYPE
        SYNTAX	IpAddress
        ACCESS	read-write
        STATUS	mandatory
        DESCRIPTION
                "The BGP Identifier for this router."
        ::= { wfBgp 4 }

    wfBgpLocalAs OBJECT-TYPE
        SYNTAX	INTEGER(0..65535)
        ACCESS	read-write
        STATUS	mandatory
        DESCRIPTION
                "The Autonomous System (AS) that this router belongs to."
        ::= { wfBgp 5 }

    wfBgpEbgpDebugSwitch OBJECT-TYPE
        SYNTAX	INTEGER {
    		    enabled(1),
    		    disabled(2)
    		}
        ACCESS	read-write
        STATUS	mandatory
        DESCRIPTION
                "If this debug switch is enabled, BGP will not enforce the rule
                that requires each EBGP peer to be on a directly attached network."
        DEFVAL	{ disabled }
        ::= { wfBgp 6 }

    wfBgpVersion OBJECT-TYPE
        SYNTAX	OCTET STRING
        ACCESS	read-only
        STATUS	mandatory
        DESCRIPTION
                "Vector of supported BGP protocol version numbers.
                Each peer negotiates the version from this vector.
                Versions are identified via the string of bits
                contained within this attribute. The first octet
                contains bits 0 to 7, the second octet contains
                bits 8 to 15, and so on, with the most significant
                bit referring to the lowest bit number in the octet
                (e.g., the MSB of the first octet refers to bit 0).
                If a bit, i, is present and set, then the version (i+1)
                of the BGP is supported."
        ::= { wfBgp 7 }

    wfBgpIntraAsIbgpRouting OBJECT-TYPE
        SYNTAX	INTEGER {
    		    enabled(1),
    		    disabled(2)
    		}
        ACCESS	read-write
        STATUS	mandatory
        DESCRIPTION
                "If this switch is enabled, BGP will perform
                Intra-AS IBGP routing."
        DEFVAL	{ enabled }
        ::= { wfBgp 8 }

    wfIbgpFromProtocols OBJECT-TYPE
        SYNTAX	INTEGER {
    		    bgp(1),
    		    all(2)
    		}
        ACCESS	read-write
        STATUS	mandatory
        DESCRIPTION
                "if Intra-AS IBGP routing is enabled, this attribute
                spcifies if non-BGP external routes can be propogated
                via IBGP."
        DEFVAL	{ bgp }
        ::= { wfBgp 9 }

    wfBgpIntAdvTimer OBJECT-TYPE
        SYNTAX	INTEGER(1..2147483647)
        ACCESS	read-write
        STATUS	mandatory
        DESCRIPTION
                "the minimum time interval, in seconds, between injections
                of EBGP routes into the IP routing table. default is 5.
                Can't be zero"
        DEFVAL	{ 5 }
        ::= { wfBgp 10 }

    wfBgpUsedRoutes OBJECT-TYPE
        SYNTAX	Counter
        ACCESS	read-only
        STATUS	mandatory
        DESCRIPTION
                "the number of received BGP routes that have been submitted
                for possible inclusion in the IP routing table."
        ::= { wfBgp 11 }

    wfBgpTotalRoutes OBJECT-TYPE
        SYNTAX	Counter
        ACCESS	read-only
        STATUS	mandatory
        DESCRIPTION
                "the total number of BGP routes currently maintained."
        ::= { wfBgp 12 }

    wfBgpTotalPaths OBJECT-TYPE
        SYNTAX	Counter
        ACCESS	read-only
        STATUS	mandatory
        DESCRIPTION
                "the total number of BGP path attributes blocks currently
                maintained."
        ::= { wfBgp 13 }

    wfBgpMaxRedundantIbgpRoutes OBJECT-TYPE
        SYNTAX	INTEGER(0..255)
        ACCESS	read-write
        STATUS	mandatory
        DESCRIPTION
                "Specifies the maximum number of IBGP routes
                to the same destination to be stored. At this
                point at least one route is stored even if
                zero is specified.
                If set to BGP_MAX_REDUNDANT_RTS_MAXIMUM,
                no limit will be imposed."
        DEFVAL	{ 255 }
        ::= { wfBgp 14 }

    wfBgpRouteRequestSwitch OBJECT-TYPE
        SYNTAX	INTEGER {
    		    enabled(1),
    		    disabled(2)
    		}
        ACCESS	read-write
        STATUS	mandatory
        DESCRIPTION
                "If this switch is enabled and at least one
                connection to IBGP route server is enabled,
                    alternate routes to a destination which became
                    unreachable will be requested from the Route
                    Server."
        DEFVAL	{ enabled }
        ::= { wfBgp 15 }

    wfBgpConnCollisionDetect OBJECT-TYPE
        SYNTAX	INTEGER {
    		    enabled(1),
    		    disabled(2)
    		}
        ACCESS	read-write
        STATUS	mandatory
        DESCRIPTION
                "If this switch is enabled, redundant BGP connections
                to the same router will be detected and disallowed,
                i.e. only one BGP connection to the same router will
                be maintained."
        DEFVAL	{ enabled }
        ::= { wfBgp 16 }

    wfBgpRsTopology OBJECT-TYPE
        SYNTAX	INTEGER {
    		    none(1),
    		    client(2),
    		    mesh(3),
    		    tree(4)
    		}
        ACCESS	read-write
        STATUS	mandatory
        DESCRIPTION
                "Specifies IBGP Route Server connection topology:
                none(Non-RS), RC, full-mesh, or tree. To enable Route Server mode
                full-mesh or tree topology must be selected."
        DEFVAL	{ none }
        ::= { wfBgp 17 }

    wfBgpClusterIdentifier OBJECT-TYPE
        SYNTAX	Gauge(0..4294967295)
        ACCESS	read-write
        STATUS	mandatory
        DESCRIPTION
                "If RS Server, cluster Identifer for this server"
        ::= { wfBgp 18 }

    wfBgpDynamicPolChangeSupport OBJECT-TYPE
        SYNTAX        INTEGER {
                  enabled(1),
                  disabled(2)
              }
        ACCESS        read-write
        STATUS        mandatory
        DESCRIPTION
                "If this switch is enabled, when a BGP policy rule changes
                 all affected routes are dynamically re-evaluated according
                 to the new policy specification.

                 If this switch is disabled, all bgp connections are restarted."
        DEFVAL        { enabled }
        ::= { wfBgp 19 }

     wfBgpSoloistSlots OBJECT-TYPE
        SYNTAX  Gauge
        ACCESS  read-write
        STATUS  mandatory
        DESCRIPTION
                "Slot mask for which slots BGP is eligible
                to run on.  The MSBit represents slot 1, the
                next most significant bit represents slot 2,
                and so on...  Slots can be 1-14.
                Default is all slots on a BCN."
        DEFVAL  { 4294705152 }
        ::= { wfBgp 20 }
 
     wfBgpSoloistSlot OBJECT-TYPE
        SYNTAX  INTEGER
        ACCESS  read-only
        STATUS  mandatory
        DESCRIPTION
                "Slot on which BGP runs in Soloist mode. Slots
		 can be 1-14. Zero means that BGP is not in a
		 Soloist mode. Default is zero."
        DEFVAL  { 0 }
        ::= { wfBgp 21 }
 
    wfBgpSubnetAggregation OBJECT-TYPE
        SYNTAX        INTEGER {
                  enabled(1),
                  disabled(2)
              }
        ACCESS        read-write
        STATUS        mandatory
        DESCRIPTION
                "If this switch is enabled, non-BGP originated subnet
               routes are aggregated to their corresponding natural
               network routes for advertisement to bgp peers. 
               Advertisement of BGP originated routes is not affected
               by this switch."
        DEFVAL        { enabled }
        ::= { wfBgp 22 }

    wfBgpBlackHoleSupport     OBJECT-TYPE
        SYNTAX  INTEGER {
                    disabled(1),
                    drop(2),
                    reject(3)
                }
        ACCESS  read-write
        STATUS  mandatory
        DESCRIPTION
              "If this switch is disabled BGP doesn't submit a 'black-hole' route
              into IP routing table for an aggregate route advertised
              to a BGP peer. For action 'drop' packet will be dropped and for
              'reject' - 'ICMP Destination Unreachable' will be send back."
        DEFVAL  { disabled }
        ::= { wfBgp 23 }

    wfBgpMedComparison     OBJECT-TYPE
        SYNTAX  INTEGER {
                  enabled(1),
                  disabled(2)
                }
        ACCESS  read-write
        STATUS  mandatory
        DESCRIPTION
              "If this switch is disabled BGP, the Multi-Exit Discriminator (MED)
              route attribute is not considered in the route selection
              process." 
        DEFVAL  { enabled }
        ::= { wfBgp 24 }

    wfBgpIbgpReflection     OBJECT-TYPE
        SYNTAX  INTEGER {
                  enabled(1),
                  disabled(2)
                }
        ACCESS  read-write
        STATUS  mandatory
        DESCRIPTION
              "Enables/Disables reflecting of BGP routes to IBGP peers." 
        DEFVAL  { disabled }
        ::= { wfBgp 25 }

    wfBgpIbgpEcmpMethod     OBJECT-TYPE
        SYNTAX  INTEGER {
                  disabled(1),
                  route-balance(2),
                  traffic-balance(3)
                }
        ACCESS  read-write
        STATUS  mandatory
        DESCRIPTION
              "Method to use IGP ECMP routing information for an IBGP peering.
              route-balance method distributes a set of destination networks
              that share the same IBGP Next Hop among available ECMP routes.
              Each IBGP network has one route submitted to IP RTM.
              traffic-balance uses all avaiable IGP ECMP routes. Each IBGP
              network submitted to IP RTM number of times equal to number
              IGP ECMP routes to IBGP Next Hop."
        DEFVAL  { disabled }
        ::= { wfBgp 26 }

    wfBgpLocalPrefCalc     OBJECT-TYPE
        SYNTAX  INTEGER {
                  enabled(1),
                  disabled(2)
                }
        ACCESS  read-write
        STATUS  mandatory
        DESCRIPTION
              "Enable/disable local_pref calculation"
        DEFVAL  { enabled }
        ::= { wfBgp 27 }

    wfBgpConfedIdentifier OBJECT-TYPE
        SYNTAX  INTEGER
        ACCESS  read-write
        STATUS  mandatory
        DESCRIPTION
                "The BGP Confederation Identifier for this router.
                 NIL means this AS is not a member of any confederation"
        DEFVAL  { 0 }
        ::= { wfBgp 28 }

   wfBgpConfedPeers OBJECT-TYPE
        SYNTAX  OCTET STRING
        ACCESS  read-write
        STATUS  mandatory
        DESCRIPTION
                " Peer list of this BGP speaker to other member sub_ASs
                  within the same confederation, NIL means no peer from 
		  this speaker to neighbor ASs that are members of this 
		  local confederation"
        ::= { wfBgp 29 }

    wfBgpIgpInterAction OBJECT-TYPE
        SYNTAX  INTEGER (0..32767)
        ACCESS  read-write
        STATUS  mandatory
        DESCRIPTION
                "Bit map for BGP/IGP interaction control:
                bit 15                                bit 0
                +---------------------------------------+
                |                                       |
                +---------------------------------------+
		bit0: eBGP to OSPF
		bit1: eBGP to RIP
		bit2 - bit15: Reserved
		value 0 means no interaction"
        DEFVAL  { 0 }
        ::= { wfBgp 30 }
 
    wfBgp3		OBJECT IDENTIFIER ::= { wfBgp3Group 1 }

    wfBgp3Delete OBJECT-TYPE
        SYNTAX	INTEGER {
    		    created(1),
    		    deleted(2)
    		}
        ACCESS	read-write
        STATUS	mandatory
        DESCRIPTION
                "Create/Delete parameter for determining whether or not BGP3 is
                configured on this router."
        DEFVAL	{ created }
        ::= { wfBgp3 1 }

    wfBgp3Disable OBJECT-TYPE
        SYNTAX	INTEGER {
    		    enabled(1),
    		    disabled(2)
    		}
        ACCESS	read-write
        STATUS	mandatory
        DESCRIPTION
                "Enable/Disable parameter for determining whether or not to start-up
                BGP3."
        DEFVAL	{ enabled }
        ::= { wfBgp3 2 }

    wfBgp3State OBJECT-TYPE
        SYNTAX	INTEGER {
    		    up(1),
    		    down(2),
    		    init(3),
    		    invalid(4),
    		    notpresent(5)
    		}
        ACCESS	read-only
        STATUS	mandatory
        DESCRIPTION
                "the administrative state of BGP-3"
        DEFVAL	{ notpresent }
        ::= { wfBgp3 3 }

    wfBgp3IntraAsIbgpRouting OBJECT-TYPE
        SYNTAX	INTEGER {
    		    enabled(1),
    		    disabled(2)
    		}
        ACCESS	read-write
        STATUS	obsolete
        DESCRIPTION
                "If this switch is enabled, BGP-3 will perform
                Intra-AS IBGP routing."
        DEFVAL	{ enabled }
        ::= { wfBgp3 4 }

    wfBgp3IntAdvTimer OBJECT-TYPE
        SYNTAX	INTEGER(1..2147483647)
        ACCESS	read-write
        STATUS	obsolete
        DESCRIPTION
                "the minimum time interval, in seconds, between injections
                of EBGP routes into the IP routing table.  default is 5.
                can't be zero"
        DEFVAL	{ 5 }
        ::= { wfBgp3 5 }

    wfBgp3RipRules OBJECT-TYPE
        SYNTAX	INTEGER {
    		    enabled(1),
    		    disabled(2)
    		}
        ACCESS	read-write
        STATUS	obsolete
        DESCRIPTION
                "if enabled, IBGP routes that are also reachable via
                a RIP route will be consider 'reachable' and will be used.
                the use of this is highly discouraged."
        DEFVAL	{ disabled }
        ::= { wfBgp3 6 }

    wfBgp3UsedRoutes OBJECT-TYPE
        SYNTAX	Counter
        ACCESS	read-only
        STATUS	obsolete
        DESCRIPTION
                "the number of received BGP-3 routes that have been submitted
                for possible inclusion in the IP routing table."
        ::= { wfBgp3 7 }

    wfBgp3TotalRoutes OBJECT-TYPE
        SYNTAX	Counter
        ACCESS	read-only
        STATUS	obsolete
        DESCRIPTION
                "the total number of BGP-3 routes currently maintained."
        ::= { wfBgp3 8 }

    wfBgp4		OBJECT IDENTIFIER ::= { wfBgp4Group 1 }

    wfBgp4Delete OBJECT-TYPE
        SYNTAX	INTEGER {
    		    created(1),
    		    deleted(2)
    		}
        ACCESS	read-write
        STATUS	mandatory
        DESCRIPTION
                "Create/Delete parameter for determining whether or not BGP-4 is
                configured on this router."
        DEFVAL	{ created }
        ::= { wfBgp4 1 }

    wfBgp4Disable OBJECT-TYPE
        SYNTAX	INTEGER {
    		    enabled(1),
    		    disabled(2)
    		}
        ACCESS	read-write
        STATUS	mandatory
        DESCRIPTION
                "Enable/Disable parameter for determining whether or
                not to start-up BGP-4."
        DEFVAL	{ enabled }
        ::= { wfBgp4 2 }

    wfBgp4State OBJECT-TYPE
        SYNTAX	INTEGER {
    		    up(1),
    		    down(2),
    		    init(3),
    		    invalid(4),
    		    notpresent(5)
    		}
        ACCESS	read-only
        STATUS	mandatory
        DESCRIPTION
                "the administrative state of BGP-4"
        DEFVAL	{ notpresent }
        ::= { wfBgp4 3 }

    wfBgpPeerTable OBJECT-TYPE
        SYNTAX	SEQUENCE OF WfBgpPeerEntry
        ACCESS	not-accessible
        STATUS	mandatory
        DESCRIPTION
                "The BGP Peer table contains configuration and statistical information
                regarding this router's BGP peers"
        ::= { wfBgpGeneralGroup 2 }

    wfBgpPeerEntry OBJECT-TYPE
        SYNTAX	WfBgpPeerEntry
        ACCESS	not-accessible
        STATUS	mandatory
        DESCRIPTION
                "An entry in the BGP-Peer table"
        INDEX	{ wfBgpPeerLocalAddr,
    		  wfBgpPeerRemoteAddr }
        ::= { wfBgpPeerTable 1 }

    WfBgpPeerEntry ::= SEQUENCE {
    	    wfBgpPeerDelete
    		INTEGER,
    	    wfBgpPeerDisable
    		INTEGER,
    	    wfBgpPeerState
    		INTEGER,
    	    wfBgpPeerLocalAddr
    		IpAddress,
    	    wfBgpPeerLocalPort
    		INTEGER,
    	    wfBgpPeerRemoteAddr
    		IpAddress,
    	    wfBgpPeerRemotePort
    		INTEGER,
    	    wfBgpPeerMinVersion
    		INTEGER,
    	    wfBgpPeerMaxVersion
    		INTEGER,
    	    wfBgpPeerRemoteAs
    		INTEGER,
    	    wfBgpPeerExtAdvTimer
    		INTEGER,
    	    wfBgpPeerConnectRetry
    		INTEGER,
    	    wfBgpPeerCfgHoldtime
    		INTEGER,
    	    wfBgpPeerHoldtime
    		INTEGER,
    	    wfBgpPeerCfgKeepAlive
    		INTEGER,
    	    wfBgpPeerKeepAlive
    		INTEGER,
    	    wfBgpPeerPathAttrSwitch
    		INTEGER,
    	    wfBgpPeerIdentifier
    		IpAddress,
    	    wfBgpPeerConnState
    		INTEGER,
    	    wfBgpPeerNegotiatedVersion
    		INTEGER,
    	    wfBgpPeerInUpdates
    		Counter,
    	    wfBgpPeerOutUpdates
    		Counter,
    	    wfBgpPeerInTotalMessages
    		Counter,
    	    wfBgpPeerOutTotalMessages
    		Counter,
    	    wfBgpPeerLastError
    		OCTET STRING,
    	    wfBgpPeerTotalRoutes
    		Counter,
    	    wfBgpPeerFsmEstablishedTransitions
    		Counter,
    	    wfBgpPeerFsmEstablishedTime
    		Gauge,
    	    wfBgpPeerInUpdateElapsedTime
    		Gauge,
    	    wfBgpPeerMinASOriginationInterval
    		INTEGER,
    	    wfBgpPeerLocalAS
    		INTEGER,
    	    wfBgpPeerMaxUpdateSize
    		INTEGER,
    	    wfBgpPeerRouteEchoSwitch
    		INTEGER,
    	    wfBgpPeerDiscardDuplicateRouteSwitch
    		INTEGER,
    	    wfBgpPeerRSMode
    		INTEGER,
    	    wfBgpPeerRSIdentifier
    		INTEGER,
    	    wfBgpPeerCfgDelayGranularity
    		INTEGER,
    	    wfBgpPeerDelayGranularity
                INTEGER,
            wfBgpPeerLastErrorSrc
    		INTEGER,
	    wfBgpPeerNexthopSelf
		INTEGER,
            wfBgpPeerASLoopDetect
                INTEGER,
	    wfBgpPeerBgpEcmpMethod
                INTEGER,
            wfBgpPeerDampenedRoutes
                INTEGER,
            wfBgpPeerTTL
                INTEGER,
            wfBgpPeerTcpAuthentication
                INTEGER,
            wfBgpPeerTcpMd5KeyStorage
                INTEGER,
            wfBgpPeerTcpMd5Key
                OCTET STRING
        }

    wfBgpPeerDelete OBJECT-TYPE
        SYNTAX	INTEGER {
    		    created(1),
    		    deleted(2)
    		}
        ACCESS	read-write
        STATUS	mandatory
        DESCRIPTION
                "Create/Delete: if set to delete, the peer connection is removed"
        DEFVAL	{ created }
        ::= { wfBgpPeerEntry 1 }

    wfBgpPeerDisable OBJECT-TYPE
        SYNTAX	INTEGER {
    		    enabled(1),
    		    disabled(2)
    		}
        ACCESS	read-write
        STATUS	mandatory
        DESCRIPTION
                "Enable/Disable: controls whether the peer connection is enabled
                or disabled"
        DEFVAL	{ enabled }
        ::= { wfBgpPeerEntry 2 }

    wfBgpPeerState OBJECT-TYPE
        SYNTAX	INTEGER {
    		    up(1),
    		    down(2),
    		    init(3),
    		    invalid(4),
    		    notpresent(5)
    		}
        ACCESS	read-only
        STATUS	mandatory
        DESCRIPTION
                "the administrative state of the peer connection on this interface"
        DEFVAL	{ notpresent }
        ::= { wfBgpPeerEntry 3 }

    wfBgpPeerLocalAddr OBJECT-TYPE
        SYNTAX	IpAddress
        ACCESS	read-only
        STATUS	mandatory
        DESCRIPTION
                "the local interface address"
        ::= { wfBgpPeerEntry 4 }

    wfBgpPeerLocalPort OBJECT-TYPE
        SYNTAX	INTEGER
        ACCESS	read-only
        STATUS	mandatory
        DESCRIPTION
                "the local TCP port number"
        ::= { wfBgpPeerEntry 5 }

    wfBgpPeerRemoteAddr OBJECT-TYPE
        SYNTAX	IpAddress
        ACCESS	read-only
        STATUS	mandatory
        DESCRIPTION
                "the peer's interface address"
        ::= { wfBgpPeerEntry 6 }

    wfBgpPeerRemotePort OBJECT-TYPE
        SYNTAX	INTEGER
        ACCESS	read-only
        STATUS	mandatory
        DESCRIPTION
                "the peer's TCP port number"
        ::= { wfBgpPeerEntry 7 }

    wfBgpPeerMinVersion OBJECT-TYPE
        SYNTAX	INTEGER {
    		    bgp3(3),
    		    bgp4(4)
    		}
        ACCESS	read-write
        STATUS	mandatory
        DESCRIPTION
                "the minimum BGP version number supported on this connection.
                Default is 4."
        DEFVAL	{ bgp4 }
        ::= { wfBgpPeerEntry 8 }

    wfBgpPeerMaxVersion OBJECT-TYPE
        SYNTAX	INTEGER {
    		    bgp3(3),
    		    bgp4(4)
    		}
        ACCESS	read-write
        STATUS	mandatory
        DESCRIPTION
                "the maximum BGP version number supported on this connection
                Default is 4."
        DEFVAL	{ bgp4 }
        ::= { wfBgpPeerEntry 9 }

    wfBgpPeerRemoteAs OBJECT-TYPE
        SYNTAX	INTEGER
        ACCESS	read-write
        STATUS	mandatory
        DESCRIPTION
                "the configured peer's AS number. this must be filled in.
                the AS received in the open message must match this one."
        ::= { wfBgpPeerEntry 10 }

    wfBgpPeerExtAdvTimer OBJECT-TYPE
        SYNTAX	INTEGER(1..2147483647)
        ACCESS	read-write
        STATUS	mandatory
        DESCRIPTION
                "Time interval in seconds for the MinRouteAdvertisementInterval
                BGP timer. Default is 30.  Can't be zero"
        DEFVAL	{ 30 }
        ::= { wfBgpPeerEntry 11 }

    wfBgpPeerConnectRetry OBJECT-TYPE
        SYNTAX	INTEGER(1..2147483647)
        ACCESS	read-write
        STATUS	mandatory
        DESCRIPTION
                "the ConnectRetry timer, in seconds. this is the time between
                TCP connection attempts."
        DEFVAL	{ 120 }
        ::= { wfBgpPeerEntry 12 }

    wfBgpPeerCfgHoldtime OBJECT-TYPE
        SYNTAX	INTEGER(3..2147483647)
        ACCESS	read-write
        STATUS	mandatory
        DESCRIPTION
                "the configured Holdtime timer, in seconds. this is the maximum
                time that the peer can wait without receiving a KEEPALIVE from
                this speaker. if no hold timer is to be used (for an SVC), zero
                should be entered.  otherwise, the value must be 3 or greater.
                this value is sent in the OPEN message.  upon receipt of an
                OPEN, the received hold time is compared to this value.
                if both are zero, no hold timer will be run and periodic
                keepalives will not be sent.  otherwise, the minimum
                of the two timers will be used.  if this results in a
                hold timer of less than 3, 3 will be used."
        DEFVAL	{ 90 }
        ::= { wfBgpPeerEntry 13 }

    wfBgpPeerHoldtime OBJECT-TYPE
        SYNTAX	INTEGER
        ACCESS	read-only
        STATUS	mandatory
        DESCRIPTION
                "the Holdtime timer value that was negotiated and is in use"
        ::= { wfBgpPeerEntry 14 }

    wfBgpPeerCfgKeepAlive OBJECT-TYPE
        SYNTAX	INTEGER(1..2147483647)
        ACCESS	read-write
        STATUS	mandatory
        DESCRIPTION
                "the configured KeepAlive timer, in seconds. this is the interval
                between sending KEEPALIVE messages.  if the hold timer was set to
                zero, this is ignored.  otherwise, the KeepAlive timer will
                be set to the minimum of this value and 1/3 of the hold timer."
        DEFVAL	{ 30 }
        ::= { wfBgpPeerEntry 15 }

    wfBgpPeerKeepAlive OBJECT-TYPE
        SYNTAX	INTEGER
        ACCESS	read-only
        STATUS	mandatory
        DESCRIPTION
                "the value used for the KeepAlive timer"
        ::= { wfBgpPeerEntry 16 }

    wfBgpPeerPathAttrSwitch OBJECT-TYPE
        SYNTAX	INTEGER {
    		    enabled(1),
    		    disabled(2)
    		}
        ACCESS	read-write
        STATUS	obsolete
        DESCRIPTION
                "controls whether the wfBgp3PathAttrTable (and the
                bgpRcvdPathAttrTable) will be maintained."
        DEFVAL	{ enabled }
        ::= { wfBgpPeerEntry 17 }

    wfBgpPeerIdentifier OBJECT-TYPE
        SYNTAX	IpAddress
        ACCESS	read-only
        STATUS	mandatory
        DESCRIPTION
                "the BGP ID of the Peer"
        ::= { wfBgpPeerEntry 18 }

    wfBgpPeerConnState OBJECT-TYPE
        SYNTAX	INTEGER {
    		    idle(1),
    		    connect(2),
    		    active(3),
    		    opensent(4),
    		    openconfirm(5),
    		    established(6)
    		}
        ACCESS	read-only
        STATUS	mandatory
        DESCRIPTION
                "the state of the BGP connection FSM"
        DEFVAL	{ idle }
        ::= { wfBgpPeerEntry 19 }

    wfBgpPeerNegotiatedVersion OBJECT-TYPE
        SYNTAX	INTEGER
        ACCESS	read-only
        STATUS	mandatory
        DESCRIPTION
                "the negotiated version of BGP running between the two peers"
        ::= { wfBgpPeerEntry 20 }

    wfBgpPeerInUpdates OBJECT-TYPE
        SYNTAX	Counter
        ACCESS	read-only
        STATUS	mandatory
        DESCRIPTION
                "the number of BGP UPDATE messages received on this connection.
                This object should be initialized to zero when the connection
                is established."
        ::= { wfBgpPeerEntry 21 }

    wfBgpPeerOutUpdates OBJECT-TYPE
        SYNTAX	Counter
        ACCESS	read-only
        STATUS	mandatory
        DESCRIPTION
                "the number of BGP UPDATE messages transmitted on this connection.
                This object should be initialized to zero when the connection is
                established."
        ::= { wfBgpPeerEntry 22 }

    wfBgpPeerInTotalMessages OBJECT-TYPE
        SYNTAX	Counter
        ACCESS	read-only
        STATUS	mandatory
        DESCRIPTION
                "the total number of messages received from the remote peer on this
                connection. This object should be initialized to zero when the
                connection is established."
        ::= { wfBgpPeerEntry 23 }

    wfBgpPeerOutTotalMessages OBJECT-TYPE
        SYNTAX	Counter
        ACCESS	read-only
        STATUS	mandatory
        DESCRIPTION
                "the total number of messages transmitted from the remote peer
                on this connection. This object should be initialized to zero
                when the connection is established."
        ::= { wfBgpPeerEntry 24 }

    wfBgpPeerLastError OBJECT-TYPE
        SYNTAX	OCTET STRING
        ACCESS	read-only
        STATUS	mandatory
        DESCRIPTION
                "the last error code and subcode seen by this peer on this
                connection. If no error has occurred, this field is zero.
                Otherwise, the first byte of this two byte OCTET STRING contains
                the error code; the second contains the subcode."
        ::= { wfBgpPeerEntry 25 }

    wfBgpPeerTotalRoutes OBJECT-TYPE
        SYNTAX	Counter
        ACCESS	read-only
        STATUS	mandatory
        DESCRIPTION
                "the total number of routes that were received from this
                peer that we are currently maintaining."
        ::= { wfBgpPeerEntry 26 }

    wfBgpPeerFsmEstablishedTransitions OBJECT-TYPE
        SYNTAX	Counter
        ACCESS	read-only
        STATUS	mandatory
        DESCRIPTION
                "The total number of times the BGP FSM transitioned into
                the established state."
        ::= { wfBgpPeerEntry 27 }

    wfBgpPeerFsmEstablishedTime OBJECT-TYPE
        SYNTAX	Gauge
        ACCESS	read-only
        STATUS	mandatory
        DESCRIPTION
                "This timer indicates how long (in seconds) this peer has been
                in the Established state or how long since this peer was last
                in the Established state. It is set to zero when a new peer is
                configured or the router is booted."
        ::= { wfBgpPeerEntry 28 }

    wfBgpPeerInUpdateElapsedTime OBJECT-TYPE
        SYNTAX	Gauge
        ACCESS	read-only
        STATUS	mandatory
        DESCRIPTION
                "Elapsed time in seconds since the last BGP UPDATE message was
                received from the peer.  Each time wfBgpPeerInUpdates is
                incremented, the value of this object is set to zero (0)."
        ::= { wfBgpPeerEntry 29 }

    wfBgpPeerMinASOriginationInterval OBJECT-TYPE
        SYNTAX	INTEGER(1..2147483647)
        ACCESS	read-write
        STATUS	mandatory
        DESCRIPTION
                "Time interval in seconds for the MinASOriginationInterval timer.
                The default value for this timer is 15 seconds. Can't be zero."
        DEFVAL	{ 15 }
        ::= { wfBgpPeerEntry 30 }

    wfBgpPeerLocalAS OBJECT-TYPE
        SYNTAX	INTEGER(0..65535)
        ACCESS	read-write
        STATUS	mandatory
        DESCRIPTION
                "If configured, specifies the AS Number that is sent in OPEN message
                to this peer. If zero, the AS Number specified with wfBgpLocalAS
                attribute is used."
        ::= { wfBgpPeerEntry 31 }

    wfBgpPeerMaxUpdateSize OBJECT-TYPE
        SYNTAX	INTEGER(64..4096)
        ACCESS	read-write
        STATUS	mandatory
        DESCRIPTION
                "Specifies the maximum size (in bytes) of UPDATE message that can be
                sent to this peer.  Note that, if the message size that is needed
                to advertise a single route is greater than the configured maximum
                message size,  the acctual message size can exceed the configured
                value."
        DEFVAL	{ 800 }
        ::= { wfBgpPeerEntry 32 }

    wfBgpPeerRouteEchoSwitch OBJECT-TYPE
        SYNTAX	INTEGER {
    		    enabled(1),
    		    disabled(2)
    		}
        ACCESS	read-write
        STATUS	mandatory
        DESCRIPTION
                "The switch controls route echoing. If enabled, a BGP route
                that is selected for forwarding is advertised back to
                the peer from which the route was received."
        DEFVAL	{ disabled }
        ::= { wfBgpPeerEntry 33 }

    wfBgpPeerDiscardDuplicateRouteSwitch OBJECT-TYPE
        SYNTAX	INTEGER {
    		    enabled(1),
    		    disabled(2)
    		}
        ACCESS	read-write
        STATUS	mandatory
        DESCRIPTION
                "Indicates if duplicate routes with the identical path attributes
                should be discarded. Should be enabled only when peering with
                an IBGP Route Server."
        DEFVAL	{ disabled }
        ::= { wfBgpPeerEntry 34 }

    wfBgpPeerRSMode OBJECT-TYPE
        SYNTAX	INTEGER {
    		    none(1),
    		    server-client(2),
    		    server-internal(3),
    		    server-external(4),
		    reflector-client(5),
		    reflector-internal(6),
		    reflector-external(7)
    		}
        ACCESS	read-write
        STATUS	mandatory
        DESCRIPTION
                "Indicates the Route Reflector / Route Server Mode of BGP peer:
                (1) - not a Route Server or Route Reflector connection;
                (2) - peer is a Route Server client;
                (3) - peer is a Route Server in the same RS cluster;
                (4) - peer is a Route Server in a different RS cluster;
                (5) - peer is a Route Reflector client;
                (6) - peer is a Route Reflector in the same RR cluster;
                (7) - peer is a Route Reflector in a different RR cluster."
        DEFVAL	{ none }
        ::= { wfBgpPeerEntry 35 }

    wfBgpPeerRSIdentifier OBJECT-TYPE
        SYNTAX	INTEGER(0..65535)
        ACCESS	read-write
        STATUS	obsolete
        DESCRIPTION
                "if wfBgpPeerRSMode is BGP_PEER_RS_MODE_INTERNAL or
                BGP_PEER_RS_MODE_RS_EXTERNAL, specifies the RS Identifier
                that is send in IDENTIFICATION message."
        ::= { wfBgpPeerEntry 36 }

    wfBgpPeerCfgDelayGranularity OBJECT-TYPE
        SYNTAX	INTEGER(1..2147483647)
        ACCESS	read-write
        STATUS	mandatory
        DESCRIPTION
                "the configured delay granularity in seconds."
        DEFVAL	{ 30 }
        ::= { wfBgpPeerEntry 37 }

    wfBgpPeerDelayGranularity OBJECT-TYPE
        SYNTAX	INTEGER
        ACCESS	read-only
        STATUS	mandatory
        DESCRIPTION
                "the delay granularity in use"
        ::= { wfBgpPeerEntry 38 }

    wfBgpPeerLastErrorSrc OBJECT-TYPE
        SYNTAX        INTEGER(0..2)
        ACCESS  read-only
        STATUS        mandatory
        DESCRIPTION
                "The source of the last error notification received/sent \
                ( 1 = recv / 2 = sent ).  A null is present if no errors \
                have occured."
        ::= { wfBgpPeerEntry 39 }

    wfBgpPeerNexthopSelf OBJECT-TYPE
	SYNTAX  INTEGER {
			enabled(1),
			disabled(2)
		}
	ACCESS        read-write
	STATUS        mandatory
	DESCRIPTION
		"Disable the use of third party advertisements"
	DEFVAL        { disabled }
	::= { wfBgpPeerEntry 40 }

    wfBgpPeerASLoopDetect OBJECT-TYPE
        SYNTAX  INTEGER {
                enabled(1),
                disabled(2)
        }
        ACCESS  read-write
        STATUS  mandatory
        DESCRIPTION
                "Designates whether the router will kill a peering \
                session if a Loop is detected in the AS Path."
        DEFVAL  { enabled }
        ::= { wfBgpPeerEntry 41 }


    wfBgpPeerBgpEcmpMethod OBJECT-TYPE
        SYNTAX  INTEGER {
		disabled(1),
		route-balance(2),
		traffic-balance(3)
	}
        ACCESS  read-write
        STATUS  mandatory
        DESCRIPTION
		"Defines a method to use IGP ECMP routing information.
                route-balance method distributes a set of destination networks
                that share the same BGP Next Hop among available ECMP routes.
                Each BGP network has one route submitted to IP RTM.
                traffic-balance uses all avaiable IGP ECMP routes. Each BGP
                network submitted to IP RTM number of times equal to number
                IGP ECMP routes to BGP Next Hop.
		This parameter is similar to wfBgpIbgpEcmpMethod but
		is applicable only to EBGP peer connections. IBGP
		peer connection selects ECMP method according to
		wfBgpIbgpEcmpMethod value."
	DEFVAL	{ disabled }
	::= { wfBgpPeerEntry 42 }

    wfBgpPeerDampenedRoutes OBJECT-TYPE
        SYNTAX  INTEGER(1..2147483647)
        ACCESS  read-only
        STATUS  mandatory
        DESCRIPTION
                "Number of routes from this peer that are suppressed due to
                 flap dampening."
        ::= { wfBgpPeerEntry 43 }

    wfBgpPeerTTL OBJECT-TYPE
        SYNTAX  INTEGER(0..255)
        ACCESS  read-write
        STATUS  mandatory
        DESCRIPTION
                "Configurable Time-To-Live field to be used for this
                 peer connection. Unless wfBgpEbgpDebugSwitch is set,
                 a TTL of 1 is used for external BGP connections.
                 A value of zero (default) indicate to use wfIpBaseDefaultTTL
                 as the TTL value for this peer connection."
        DEFVAL  { 0 }
        ::= { wfBgpPeerEntry 44 }

    wfBgpPeerTcpAuthentication OBJECT-TYPE
        SYNTAX  INTEGER {
                none(1),
                md5(2)
        }
        ACCESS  read-write
        STATUS  mandatory
        DESCRIPTION
                "Indicates if BGP TCP Authentication is enabled\
                 none(1) - no authentication\
                 md5(2)  - MD5 authentication enabled"
        DEFVAL  { none }
        ::= { wfBgpPeerEntry 45 }

    wfBgpPeerTcpMd5KeyStorage OBJECT-TYPE
        SYNTAX  INTEGER {
                clear-text(1),
                encrypted(2)
        }
        ACCESS  read-write
        STATUS  mandatory
        DESCRIPTION
                "Indicates how the wfBgpPeerTcpMd5Key is stored \
                 in the MIB and configuration file. \
                 clear-text(1) - the key is stored unencrypted \
                 encrypted(2)  - the key is stored encrypted"
        DEFVAL  { clear-text }
        ::= { wfBgpPeerEntry 46 }

    wfBgpPeerTcpMd5Key OBJECT-TYPE
        SYNTAX  OCTET STRING
        ACCESS  read-write
        STATUS  mandatory
        DESCRIPTION
                "if nil,     no key configured\
                 if not nil, BGP TCP MD5 authentication key stored in \
                             wfBgpPeerTcpMd5KeyStorage format"
        ::= { wfBgpPeerEntry 47 }


    wfBgpVirtualPeerTable OBJECT-TYPE
        SYNTAX	SEQUENCE OF WfBgpVirtualPeerEntry
        ACCESS	not-accessible
        STATUS	mandatory
        DESCRIPTION
                "The BGP Virtual Peer table contains configuration and statistical information
                regarding this router's Virtual peers learned via the Route Server"
        ::= { wfBgpGeneralGroup 6 }

    wfBgpVirtualPeerEntry OBJECT-TYPE
        SYNTAX	WfBgpVirtualPeerEntry
        ACCESS	not-accessible
        STATUS	mandatory
        DESCRIPTION
                "An entry in the BGP-Virtual-Peer table"
        INDEX	{ wfBgpVirtualPeerIdentifier,
    		  wfBgpVirtualPeerLocalAddr,
    		  wfBgpVirtualPeerRemoteAddr }
        ::= { wfBgpVirtualPeerTable 1 }

    WfBgpVirtualPeerEntry ::= SEQUENCE {
    	    wfBgpVirtualPeerLocalAddr
    		IpAddress,
    	    wfBgpVirtualPeerRemoteAddr
    		IpAddress,
    	    wfBgpVirtualPeerIdentifier
    		IpAddress,
    	    wfBgpVirtualPeerInUpdates
    		Counter,
    	    wfBgpVirtualPeerTotalRoutes
    		Counter,
    	    wfBgpVirtualPeerInUpdateElapsedTime
    		Gauge
        }

    wfBgpVirtualPeerLocalAddr OBJECT-TYPE
        SYNTAX	IpAddress
        ACCESS	read-only
        STATUS	mandatory
        DESCRIPTION
                "the local interface address"
        ::= { wfBgpVirtualPeerEntry 1 }

    wfBgpVirtualPeerRemoteAddr OBJECT-TYPE
        SYNTAX	IpAddress
        ACCESS	read-only
        STATUS	mandatory
        DESCRIPTION
                "the peer's interface address"
        ::= { wfBgpVirtualPeerEntry 2 }

    wfBgpVirtualPeerIdentifier OBJECT-TYPE
        SYNTAX	IpAddress
        ACCESS	read-only
        STATUS	mandatory
        DESCRIPTION
                "the BGP ID of the Peer"
        ::= { wfBgpVirtualPeerEntry 3 }

    wfBgpVirtualPeerInUpdates OBJECT-TYPE
        SYNTAX	Counter
        ACCESS	read-only
        STATUS	mandatory
        DESCRIPTION
                "the number of BGP UPDATE messages received on this connection.
                This object should be initialized to zero when the connection
                is established."
        ::= { wfBgpVirtualPeerEntry 4 }

    wfBgpVirtualPeerTotalRoutes OBJECT-TYPE
        SYNTAX	Counter
        ACCESS	read-only
        STATUS	mandatory
        DESCRIPTION
                "the total number of routes that were received from this
                peer that we are currently maintaining."
        ::= { wfBgpVirtualPeerEntry 5 }

    wfBgpVirtualPeerInUpdateElapsedTime OBJECT-TYPE
        SYNTAX	Gauge
        ACCESS	read-only
        STATUS	mandatory
        DESCRIPTION
                "Elapsed time in seconds since the last BGP UPDATE message was
                received from the peer.  Each time wfBgpVirtualPeerInUpdates is
                incremented, the value of this object is set to zero (0)."
        ::= { wfBgpVirtualPeerEntry 6 }

    wfBgpAsWeightTable OBJECT-TYPE
        SYNTAX	SEQUENCE OF WfBgpAsWeightEntry
        ACCESS	not-accessible
        STATUS	mandatory
        DESCRIPTION
                "The BGP AS weight table contains weights for autonomous systems for use
                in best-route calculations"
        ::= { wfBgpGeneralGroup 3 }

    wfBgpAsWeightEntry OBJECT-TYPE
        SYNTAX	WfBgpAsWeightEntry
        ACCESS	not-accessible
        STATUS	mandatory
        DESCRIPTION
                "An entry in the BGP AS weight table"
        INDEX	{ wfBgpAsWeightNumber }
        ::= { wfBgpAsWeightTable 1 }

    WfBgpAsWeightEntry ::= SEQUENCE {
    	    wfBgpAsWeightDelete
    		INTEGER,
    	    wfBgpAsWeightDisable
    		INTEGER,
    	    wfBgpAsWeightState
    		INTEGER,
    	    wfBgpAsWeightNumber
    		INTEGER,
    	    wfBgpAsWeightValue
    		INTEGER,
    	    wfBgpAsWeightValue2
    		INTEGER,
    	    wfBgpAsWeightValue3
    		INTEGER,
    	    wfBgpAsWeightValue4
    		INTEGER,
    	    wfBgpAsWeightValue5
    		INTEGER,
    	    wfBgpAsWeightValue6
    		INTEGER,
    	    wfBgpAsWeightValue7
    		INTEGER,
    	    wfBgpAsWeightValue8
    		INTEGER
        }

    wfBgpAsWeightDelete OBJECT-TYPE
        SYNTAX	INTEGER {
    		    created(1),
    		    deleted(2)
    		}
        ACCESS	read-write
        STATUS	mandatory
        DESCRIPTION
                "Create/Delete: if set to delete, the AS entry is
                removed from this table"
        DEFVAL	{ created }
        ::= { wfBgpAsWeightEntry 1 }

    wfBgpAsWeightDisable OBJECT-TYPE
        SYNTAX	INTEGER {
    		    enabled(1),
    		    disabled(2)
    		}
        ACCESS	read-write
        STATUS	mandatory
        DESCRIPTION
                "Enable/Disable: controls whether the AS entry is
                enabled or disabled"
        DEFVAL	{ enabled }
        ::= { wfBgpAsWeightEntry 2 }

    wfBgpAsWeightState OBJECT-TYPE
        SYNTAX	INTEGER {
    		    up(1),
    		    down(2),
    		    init(3),
    		    invalid(4),
    		    notpresent(5)
    		}
        ACCESS	read-only
        STATUS	mandatory
        DESCRIPTION
                "the state of this AS weight entry"
        DEFVAL	{ notpresent }
        ::= { wfBgpAsWeightEntry 3 }

    wfBgpAsWeightNumber OBJECT-TYPE
        SYNTAX	INTEGER(0..65535)
        ACCESS	read-only
        STATUS	mandatory
        DESCRIPTION
                "the AS number"
        ::= { wfBgpAsWeightEntry 4 }

    wfBgpAsWeightValue OBJECT-TYPE
        SYNTAX	INTEGER(1..15)
        ACCESS	read-write
        STATUS	mandatory
        DESCRIPTION
                "the class-1 value to assign to this AS"
        DEFVAL	{ 8 }
        ::= { wfBgpAsWeightEntry 5 }

    wfBgpAsWeightValue2 OBJECT-TYPE
        SYNTAX	INTEGER {
    		    default2(8)
    		}
        ACCESS	read-write
        STATUS	mandatory
        DESCRIPTION
                "the class-2 value to assign to this AS"
        DEFVAL	{ default2 }
        ::= { wfBgpAsWeightEntry 6 }

    wfBgpAsWeightValue3 OBJECT-TYPE
        SYNTAX	INTEGER {
    		    default3(8)
    		}
        ACCESS	read-write
        STATUS	mandatory
        DESCRIPTION
                "the class-3 value to assign to this AS"
        DEFVAL	{ default3 }
        ::= { wfBgpAsWeightEntry 7 }

    wfBgpAsWeightValue4 OBJECT-TYPE
        SYNTAX	INTEGER {
    		    default4(8)
    		}
        ACCESS	read-write
        STATUS	mandatory
        DESCRIPTION
                "the class-4 value to assign to this AS"
        DEFVAL	{ default4 }
        ::= { wfBgpAsWeightEntry 8 }

    wfBgpAsWeightValue5 OBJECT-TYPE
        SYNTAX	INTEGER {
    		    default5(8)
    		}
        ACCESS	read-write
        STATUS	mandatory
        DESCRIPTION
                "the class-5 value to assign to this AS"
        DEFVAL	{ default5 }
        ::= { wfBgpAsWeightEntry 9 }

    wfBgpAsWeightValue6 OBJECT-TYPE
        SYNTAX	INTEGER {
    		    default6(8)
    		}
        ACCESS	read-write
        STATUS	mandatory
        DESCRIPTION
                "the class-6 value to assign to this AS"
        DEFVAL	{ default6 }
        ::= { wfBgpAsWeightEntry 10 }

    wfBgpAsWeightValue7 OBJECT-TYPE
        SYNTAX	INTEGER {
    		    default7(8)
    		}
        ACCESS	read-write
        STATUS	mandatory
        DESCRIPTION
                "the class-7 value to assign to this AS"
        DEFVAL	{ default7 }
        ::= { wfBgpAsWeightEntry 11 }

    wfBgpAsWeightValue8 OBJECT-TYPE
        SYNTAX	INTEGER {
    		    default8(8)
    		}
        ACCESS	read-write
        STATUS	mandatory
        DESCRIPTION
                "the class-8 value to assign to this AS"
        DEFVAL	{ default8 }
        ::= { wfBgpAsWeightEntry 12 }

    wfBgp3PathAttrTable OBJECT-TYPE
        SYNTAX	SEQUENCE OF WfBgp3PathAttrEntry
        ACCESS	not-accessible
        STATUS	obsolete
        DESCRIPTION
                "The BGP3 received path attribute table contains information about paths to
                destination networks received by all peers.
                This table is deprecated and replaced with  wfBgpPathAttrTable"
        ::= { wfBgp3Group 2 }

    wfBgp3PathAttrEntry OBJECT-TYPE
        SYNTAX	WfBgp3PathAttrEntry
        ACCESS	not-accessible
        STATUS	obsolete
        DESCRIPTION
                "An entry in the BGP-3 Path Attribute Table"
        INDEX	{ wfBgp3PathAttrDestNetwork,
    		  wfBgp3PathAttrPeer }
        ::= { wfBgp3PathAttrTable 1 }

    WfBgp3PathAttrEntry ::= SEQUENCE {
    	    wfBgp3PathAttrPeer
    		IpAddress,
    	    wfBgp3PathAttrDestNetwork
    		IpAddress,
    	    wfBgp3PathAttrOrigin
    		INTEGER,
    	    wfBgp3PathAttrASPath
    		OCTET STRING,
    	    wfBgp3PathAttrNextHop
    		IpAddress,
    	    wfBgp3PathAttrInterASMetric
    		INTEGER,
    	    wfBgp3PathAttrASPathWeight
    		INTEGER,
    	    wfBgp3PathAttrBgpPreference
    		INTEGER,
    	    wfBgp3PathAttrBest
    		INTEGER
        }

    wfBgp3PathAttrPeer OBJECT-TYPE
        SYNTAX	IpAddress
        ACCESS	read-only
        STATUS	obsolete
        DESCRIPTION
                "the BGP identifier of the peer where the path information was
                learned."
        ::= { wfBgp3PathAttrEntry 1 }

    wfBgp3PathAttrDestNetwork OBJECT-TYPE
        SYNTAX	IpAddress
        ACCESS	read-only
        STATUS	obsolete
        DESCRIPTION
                "the address of the destination network."
        ::= { wfBgp3PathAttrEntry 2 }

    wfBgp3PathAttrOrigin OBJECT-TYPE
        SYNTAX	INTEGER {
    		    igp(1),
    		    egp(2),
    		    incomplete(3)
    		}
        ACCESS	read-only
        STATUS	obsolete
        DESCRIPTION
                "the ultimate origin of the path information:
                igp (1) -- network is interior;
                egp (2) -- network learned via EGP;
                incomplete (3) -- undetermined."
        ::= { wfBgp3PathAttrEntry 3 }

    wfBgp3PathAttrASPath OBJECT-TYPE
        SYNTAX	OCTET STRING
        ACCESS	read-only
        STATUS	obsolete
        DESCRIPTION
                "the set of ASes that must be traversed to reach the network. Each AS
                is represented as a pair of octets according to the following
                algorithm:
                   first-byte-of-pair = ASNumber / 256;
                   second-byte-of-pair = ASNumber & 255;"
        ::= { wfBgp3PathAttrEntry 4 }

    wfBgp3PathAttrNextHop OBJECT-TYPE
        SYNTAX	IpAddress
        ACCESS	read-only
        STATUS	obsolete
        DESCRIPTION
                "the address of the border router that should be used as the
                next-hop for the destination network."
        ::= { wfBgp3PathAttrEntry 5 }

    wfBgp3PathAttrInterASMetric OBJECT-TYPE
        SYNTAX	INTEGER
        ACCESS	read-only
        STATUS	obsolete
        DESCRIPTION
                "the optional inter-AS metric. if this attribute has not been
                provided for this route, the value for this object is 0."
        ::= { wfBgp3PathAttrEntry 6 }

    wfBgp3PathAttrASPathWeight OBJECT-TYPE
        SYNTAX	INTEGER
        ACCESS	read-only
        STATUS	obsolete
        DESCRIPTION
                "the calculated AS path weight"
        ::= { wfBgp3PathAttrEntry 7 }

    wfBgp3PathAttrBgpPreference OBJECT-TYPE
        SYNTAX	INTEGER
        ACCESS	read-only
        STATUS	obsolete
        DESCRIPTION
                "the preference that is used to calculate this route with
                other BGP routes to the same destination"
        ::= { wfBgp3PathAttrEntry 8 }

    wfBgp3PathAttrBest OBJECT-TYPE
        SYNTAX	INTEGER {
    		    false(1),
    		    true(2)
    		}
        ACCESS	read-only
        STATUS	obsolete
        DESCRIPTION
                "an indication of whether or not this was chosen as the best route
                to the destination"
        DEFVAL	{ false }
        ::= { wfBgp3PathAttrEntry 9 }

    wfBgpPathAttrTable OBJECT-TYPE
        SYNTAX	SEQUENCE OF WfBgpPathAttrEntry
        ACCESS	not-accessible
        STATUS	obsolete
        DESCRIPTION
                "The BGP received path attribute table contains information about paths to
                destination networks received by all peers."
        ::= { wfBgpGeneralGroup 4 }

    wfBgpPathAttrEntry OBJECT-TYPE
        SYNTAX	WfBgpPathAttrEntry
        ACCESS	not-accessible
        STATUS	obsolete
        DESCRIPTION
                "An entry in the BGP Path Attribute Table"
        INDEX	{ wfBgpPathAttrIpAddrPrefix,
    		  wfBgpPathAttrIpAddrPrefixLen,
    		  wfBgpPathAttrPeer }
        ::= { wfBgpPathAttrTable 1 }

    WfBgpPathAttrEntry ::= SEQUENCE {
    	    wfBgpPathAttrIpAddrPrefix
    		IpAddress,
    	    wfBgpPathAttrIpAddrPrefixLen
    		INTEGER,
    	    wfBgpPathAttrPeer
    		IpAddress,
    	    wfBgpPathAttrOrigin
    		INTEGER,
    	    wfBgpPathAttrASPathSegment
    		OCTET STRING,
    	    wfBgpPathAttrNextHop
    		IpAddress,
    	    wfBgpPathAttrMultiExitDisc
    		INTEGER,
    	    wfBgpPathAttrLocalPref
    		INTEGER,
    	    wfBgpPathAttrAtomicAggregate
    		INTEGER,
    	    wfBgpPathAttrAggregatorAS
    		INTEGER,
    	    wfBgpPathAttrAggregatorAddr
    		IpAddress,
    	    wfBgpPathAttrCalcLocalPref
    		INTEGER,
    	    wfBgpPathAttrBest
    		INTEGER,
    	    wfBgpPathAttrUnknown
    		OCTET STRING,
    	    wfBgpPathAttrImporterID
    		IpAddress,
    	    wfBgpPathAttrClusterID
    		OCTET STRING,
    	    wfBgpPathAttrCommunity
                OCTET STRING,
            wfBgpPathAttrCalcMED
                INTEGER
        }

    wfBgpPathAttrIpAddrPrefix OBJECT-TYPE
        SYNTAX	IpAddress
        ACCESS	read-only
        STATUS	obsolete
        DESCRIPTION
                "the IP address of the destination (sub)network."
        ::= { wfBgpPathAttrEntry 1 }

    wfBgpPathAttrIpAddrPrefixLen OBJECT-TYPE
        SYNTAX	INTEGER
        ACCESS	read-only
        STATUS	obsolete
        DESCRIPTION
                "Length in bits of the IP address prefix in
                the destination (sub)network address."
        ::= { wfBgpPathAttrEntry 2 }

    wfBgpPathAttrPeer OBJECT-TYPE
        SYNTAX	IpAddress
        ACCESS	read-only
        STATUS	obsolete
        DESCRIPTION
                "the IP address of the peer where the path information was
                learned."
        ::= { wfBgpPathAttrEntry 3 }

    wfBgpPathAttrOrigin OBJECT-TYPE
        SYNTAX	INTEGER {
    		    igp(1),
    		    egp(2),
    		    incomplete(3)
    		}
        ACCESS	read-only
        STATUS	obsolete
        DESCRIPTION
                "the ultimate origin of the path information:
                igp (1) -- network is interior;
                egp (2) -- network learned via EGP;
                incomplete (3) -- undetermined."
        ::= { wfBgpPathAttrEntry 4 }

    wfBgpPathAttrASPathSegment OBJECT-TYPE
        SYNTAX	OCTET STRING
        ACCESS	read-only
        STATUS	obsolete
        DESCRIPTION
                "The sequence of AS path segments. Each AS path
                segment is represented by a triple <type, length, value>.

                 The type is a 1-octet field which has two possible values:
                  1 AS_SET: unordered set of ASs a route in the UPDATE
                 message has traversed
                  2 AS_SEQUENCE: ordered set of ASs a route in the UPDATE
                message has traversed.

                The length is a 1-octet field containing the number of ASs
                in the value field.

                The value field contains one or more AS numbers, each AS is
                represented in the octet string as a pair of octets according
                to the following algorithm:
                   first-byte-of-pair = ASNumber / 256;
                   second-byte-of-pair = ASNumber & 255;"
        ::= { wfBgpPathAttrEntry 5 }

    wfBgpPathAttrNextHop OBJECT-TYPE
        SYNTAX	IpAddress
        ACCESS	read-only
        STATUS	obsolete
        DESCRIPTION
                "the address of the border router that should be used as the
                next-hop for the destination network."
        ::= { wfBgpPathAttrEntry 6 }

    wfBgpPathAttrMultiExitDisc OBJECT-TYPE
        SYNTAX	INTEGER
        ACCESS	read-only
        STATUS	obsolete
        DESCRIPTION
                "The optional inter-AS metric. If this attribute has not been
                provided for this route, the value for this object is -1."
        ::= { wfBgpPathAttrEntry 7 }

    wfBgpPathAttrLocalPref OBJECT-TYPE
        SYNTAX	INTEGER
        ACCESS	read-only
        STATUS	obsolete
        DESCRIPTION
                "the originating BGP speaker's degree of preference
                for advertised route (-1..2147483647); if this attribute
                       has not been provided for this route, the value for this
                       object is -1."
        ::= { wfBgpPathAttrEntry 8 }

    wfBgpPathAttrAtomicAggregate OBJECT-TYPE
        SYNTAX	INTEGER {
    		    false(1),
    		    true(2)
    		}
        ACCESS	read-only
        STATUS	obsolete
        DESCRIPTION
                "indicates whether or not the local system has selected a less
                specific route without selecting a more specific route"
        ::= { wfBgpPathAttrEntry 9 }

    wfBgpPathAttrAggregatorAS OBJECT-TYPE
        SYNTAX	INTEGER
        ACCESS	read-only
        STATUS	obsolete
        DESCRIPTION
                "The AS number of the last BGP speaker that performed route
                aggregation. A value of zero (0) indicates the absence of
                this attribute."
        ::= { wfBgpPathAttrEntry 10 }

    wfBgpPathAttrAggregatorAddr OBJECT-TYPE
        SYNTAX	IpAddress
        ACCESS	read-only
        STATUS	obsolete
        DESCRIPTION
                "The BGP ID of the last BGP speaker that performed route
                aggregation.  A value of 0.0.0.0 indicates the absence
                of this attribute."
        ::= { wfBgpPathAttrEntry 11 }

    wfBgpPathAttrCalcLocalPref OBJECT-TYPE
        SYNTAX	INTEGER
        ACCESS	read-only
        STATUS	obsolete
        DESCRIPTION
                "The degree of preference calculated by the receiving
                BGP speaker for an advertised route (-1..2147483647).
                A value of -1 indicates the absence of this attribute"
        ::= { wfBgpPathAttrEntry 12 }

    wfBgpPathAttrBest OBJECT-TYPE
        SYNTAX	INTEGER {
    		    false(1),
    		    true(2),
    		    bestused(3),
    		    used(4)
    		}
        ACCESS	read-only
        STATUS	obsolete
        DESCRIPTION
                "an indication of whether or not this was chosen as
                the best bgp rout to the destination and whether or not
                it was chosen as a forwarding IP route"
        DEFVAL	{ false }
        ::= { wfBgpPathAttrEntry 13 }

    wfBgpPathAttrUnknown OBJECT-TYPE
        SYNTAX	OCTET STRING
        ACCESS	read-only
        STATUS	obsolete
        DESCRIPTION
                "One or more path attributes not understood
                by this BGP speaker.  Size zero (0) indicates
                the absence of such attribute(s).  Octets
                beyond the maximum size (255), if any, are not
                recorded by this object."
        ::= { wfBgpPathAttrEntry 14 }

    wfBgpPathAttrImporterID OBJECT-TYPE
        SYNTAX	IpAddress
        ACCESS	read-only
        STATUS	obsolete
        DESCRIPTION
                "For RS, the BGP ID of the border router that imported this route"
        ::= { wfBgpPathAttrEntry 15 }

    wfBgpPathAttrClusterID OBJECT-TYPE
        SYNTAX	OCTET STRING
        ACCESS	read-only
        STATUS	obsolete
        DESCRIPTION
                "For RS, the sequence of Cluter IDs of the Clusters.
                Size zero (0) indicates the absence of such attribute(s)."
        ::= { wfBgpPathAttrEntry 16 }

    wfBgpPathAttrCommunity OBJECT-TYPE
        SYNTAX	OCTET STRING
        ACCESS	read-only
        STATUS	obsolete
        DESCRIPTION
                "List of BGP communities. Each community is
                4 bytes long.  Size zero (0) indicates
                the absence of community attribute.  Octets
                beyond the maximum size (255), if any, are not
                recorded by this object."
        ::= { wfBgpPathAttrEntry 17 }

    wfBgpPathAttrCalcMED OBJECT-TYPE
        SYNTAX        INTEGER
        ACCESS        read-only
        STATUS        obsolete
        DESCRIPTION
                "The Multi Exit Disc. calculated by the receiving
                BGP speaker for an advertised route (-1...2G)"
        ::= { wfBgpPathAttrEntry 18 }

    wfBgpDbgTable OBJECT-TYPE
        SYNTAX	SEQUENCE OF WfBgpDbgEntry
        ACCESS	not-accessible
        STATUS	mandatory
        DESCRIPTION
                "BGP debug table contains objects that controls generation of BGP
                debug information"
        ::= { wfBgpGeneralGroup 5 }

    wfBgpDbgEntry OBJECT-TYPE
        SYNTAX	WfBgpDbgEntry
        ACCESS	not-accessible
        STATUS	mandatory
        DESCRIPTION
                "a table entry"
        INDEX	{ wfBgpDbgLocAddr,
    		  wfBgpDbgRemoteAddr }
        ::= { wfBgpDbgTable 1 }

    WfBgpDbgEntry ::= SEQUENCE {
    	    wfBgpDbgCreate
    		INTEGER,
    	    wfBgpDbgLocAddr
    		IpAddress,
    	    wfBgpDbgRemoteAddr
    		IpAddress,
    	    wfBgpDbgMsgLevel
    		INTEGER,
    	    wfBgpDbgMsgTraceSwitch
    		INTEGER,
    	    wfBgpDbgLogCode
    		INTEGER,
    	    wfBgpDbgLogCodeDisable
    		INTEGER,
    	    wfBgpDbgCodes
    		OCTET STRING,
    	    wfBgpDbgBootCodes
    		OCTET STRING
        }

    wfBgpDbgCreate OBJECT-TYPE
        SYNTAX	INTEGER {
    		    create(1),
    		    delete(2)
    		}
        ACCESS	read-write
        STATUS	mandatory
        DESCRIPTION
                "Create/Delete parameter. Default is created."
        DEFVAL	{ create }
        ::= { wfBgpDbgEntry 1 }

    wfBgpDbgLocAddr OBJECT-TYPE
        SYNTAX	IpAddress
        ACCESS	read-only
        STATUS	mandatory
        DESCRIPTION
                "The peer's local address.
                If 0.0.0.0, debug attributes are applied to all peers
                to specified Remote Address or with specified BGP version"
        ::= { wfBgpDbgEntry 2 }

    wfBgpDbgRemoteAddr OBJECT-TYPE
        SYNTAX	IpAddress
        ACCESS	read-write
        STATUS	mandatory
        DESCRIPTION
                "The peer's Remote Address .
                If 0.0.0.0, debug attrubutes are applied to all configured
                peers from specified Local Address;
                if 255.255.255.255, debug attrubutes are applied to BGP4 gate
                only."
        ::= { wfBgpDbgEntry 3 }

    wfBgpDbgMsgLevel OBJECT-TYPE
        SYNTAX	INTEGER {
    		    all(2031616),
    		    debug(65536),
    		    info(131072),
    		    warning(262144),
    		    fault(524288),
    		    trace(1048576)
    		}
        ACCESS	read-write
        STATUS	mandatory
        DESCRIPTION
                "BGP log messages level.
                To control certain level of log messages
                             BGP_DBG_MSG_ALL         0x001f0000 - 2031616
                             BGP_DBG_MSG_DEBUG       0x00010000 -   65536
                             BGP_DBG_MSG_INFO        0x00020000 -  131072
                             BGP_DBG_MSG_WARNING     0x00040000 -  262144
                             BGP_DBG_MSG_FAULT       0x00080000 -  524288
                             BGP_DBG_MSG_TRACE       0x00100000 - 1048576"
        DEFVAL	{ all }
        ::= { wfBgpDbgEntry 4 }

    wfBgpDbgMsgTraceSwitch OBJECT-TYPE
        SYNTAX	INTEGER {
    		    disabled(1),
    		    open(16),
    		    update(32),
    		    notification(64),
    		    keepalive(128)
    		}
        ACCESS	read-write
        STATUS	mandatory
        DESCRIPTION
                "controls whether BGP messages that are exchanged on this
                connection are dumped to the log.
                BGP_DBG_MSG_DUMP_REC_OPEN enables tracing of OPEN messages
                BGP_DBG_MSG_DUMP_REC_UPDATE - UPDATE messages
                BGP_DBG_MSG_DUMP_REC_NOTIFICATION - NOTIFICATION and
                BGP_DBG_MSG_DUMP_REC_KEEPALIVE - KEEPALIVE
                on logical OR basis
                             BGP_DBG_MSG_DUMP_DISABLED               1
                             BGP_DBG_MSG_DUMP_REC_OPEN               0x10 - 16
                             BGP_DBG_MSG_DUMP_REC_UPDATE             0x20 - 32
                             BGP_DBG_MSG_DUMP_REC_NOTIFICATION       0x40 - 64
                             BGP_DBG_MSG_DUMP_REC_KEEPALIVE          0x80 - 128"
        DEFVAL	{ disabled }
        ::= { wfBgpDbgEntry 5 }

    wfBgpDbgLogCode OBJECT-TYPE
        SYNTAX	INTEGER
        ACCESS	read-write
        STATUS	mandatory
        DESCRIPTION
                "Indicates that a debug log message which corresponds
                to the value of this attributes should be or should be not
                sent to the log.
                    Affects wfBgpDbgCodes only. In order to save combined
                    list of messages you have to set wfBgpDbgBootCodes directly
                    as copy of wfBgpDbgCodes"
        ::= { wfBgpDbgEntry 6 }

    wfBgpDbgLogCodeDisable OBJECT-TYPE
        SYNTAX	INTEGER {
    		    enabled(1),
    		    disabled(2)
    		}
        ACCESS	read-write
        STATUS	mandatory
        DESCRIPTION
                "Indicates that a debug log message defined in wfBgpDbgCode
                will be or will be not logged"
        DEFVAL	{ enabled }
        ::= { wfBgpDbgEntry 7 }

    wfBgpDbgCodes OBJECT-TYPE
        SYNTAX	OCTET STRING
        ACCESS	read-only
        STATUS	mandatory
        DESCRIPTION
                "Vector of enabled debug messages (to check only).
                Messages are identified via the string of bits
                contained within this attribute. The first octet
                contains bits 0 to 7, the second octet contains
                bits 8 to 15, and so on, with the most significant
                bit referring to the lowest bit number in the octet
                (e.g., the MSB of the first octet refers to bit 0).
                If a bit, i, is present and set, then the DEBUG log
                message with the code (i) is enabled."
        ::= { wfBgpDbgEntry 8 }

    wfBgpDbgBootCodes OBJECT-TYPE
        SYNTAX	OCTET STRING
        ACCESS	read-write
        STATUS	mandatory
        DESCRIPTION
                "User-defined vector of enabled debug messages at boot moment.
                Coded as instance above"
        ::= { wfBgpDbgEntry 9 }

    wfBgpPathAttributeTable OBJECT-TYPE
        SYNTAX	SEQUENCE OF WfBgpPathAttributeEntry
        ACCESS	not-accessible
        STATUS	mandatory
        DESCRIPTION
                "The BGP received path attribute table contains information about paths to
                destination networks received by all peers."
        ::= { wfBgpGeneralGroup 7 }

    wfBgpPathAttributeEntry OBJECT-TYPE
        SYNTAX	WfBgpPathAttributeEntry
        ACCESS	not-accessible
        STATUS	mandatory
        DESCRIPTION
                "An entry in the BGP Path Attribute Table"
        INDEX	{ wfBgpPathAttributeIpAddrPrefix,
    		  wfBgpPathAttributeIpAddrPrefixLen,
                  wfBgpPathAttributeImporterID,
    		  wfBgpPathAttributePeer }
        ::= { wfBgpPathAttributeTable 1 }

    WfBgpPathAttributeEntry ::= SEQUENCE {
    	    wfBgpPathAttributeIpAddrPrefix
    		IpAddress,
    	    wfBgpPathAttributeIpAddrPrefixLen
    		INTEGER,
    	    wfBgpPathAttributeImporterID
    		IpAddress,
    	    wfBgpPathAttributePeer
    		IpAddress,
    	    wfBgpPathAttributeOrigin
    		INTEGER,
    	    wfBgpPathAttributeASPathSegment
    		OCTET STRING,
    	    wfBgpPathAttributeNextHop
    		IpAddress,
    	    wfBgpPathAttributeMultiExitDisc
    		INTEGER,
    	    wfBgpPathAttributeLocalPref
    		INTEGER,
    	    wfBgpPathAttributeAtomicAggregate
    		INTEGER,
    	    wfBgpPathAttributeAggregatorAS
    		INTEGER,
    	    wfBgpPathAttributeAggregatorAddr
    		IpAddress,
    	    wfBgpPathAttributeCalcLocalPref
    		INTEGER,
    	    wfBgpPathAttributeBest
    		INTEGER,
    	    wfBgpPathAttributeUnknown
    		OCTET STRING,
    	    wfBgpPathAttributeClusterID
    		OCTET STRING,
    	    wfBgpPathAttributeCommunity
                OCTET STRING,
            wfBgpPathAttributeCalcMED
                INTEGER,
            wfBgpPathAttributeFlapPenalty
                INTEGER,
            wfBgpPathAttributeFlapCount
                INTEGER,
            wfBgpPathAttributeRouteDampened
                INTEGER
        }

    wfBgpPathAttributeIpAddrPrefix OBJECT-TYPE
        SYNTAX	IpAddress
        ACCESS	read-only
        STATUS	mandatory
        DESCRIPTION
                "the IP address of the destination (sub)network."
        ::= { wfBgpPathAttributeEntry 1 }

    wfBgpPathAttributeIpAddrPrefixLen OBJECT-TYPE
        SYNTAX	INTEGER
        ACCESS	read-only
        STATUS	mandatory
        DESCRIPTION
                "Length in bits of the IP address prefix in
                the destination (sub)network address."
        ::= { wfBgpPathAttributeEntry 2 }

    wfBgpPathAttributeImporterID OBJECT-TYPE
        SYNTAX	IpAddress
        ACCESS	read-only
        STATUS	mandatory
        DESCRIPTION
                "For RS, the BGP ID of the border router that imported this route"
        ::= { wfBgpPathAttributeEntry 3 }

    wfBgpPathAttributePeer OBJECT-TYPE
        SYNTAX	IpAddress
        ACCESS	read-only
        STATUS	mandatory
        DESCRIPTION
                "the IP address of the peer where the path information was
                learned."
        ::= { wfBgpPathAttributeEntry 4 }

    wfBgpPathAttributeOrigin OBJECT-TYPE
        SYNTAX	INTEGER {
    		    igp(1),
    		    egp(2),
    		    incomplete(3)
    		}
        ACCESS	read-only
        STATUS	mandatory
        DESCRIPTION
                "the ultimate origin of the path information:
                igp (1) -- network is interior;
                egp (2) -- network learned via EGP;
                incomplete (3) -- undetermined."
        ::= { wfBgpPathAttributeEntry 5 }

    wfBgpPathAttributeASPathSegment OBJECT-TYPE
        SYNTAX	OCTET STRING
        ACCESS	read-only
        STATUS	mandatory
        DESCRIPTION
                "The sequence of AS path segments. Each AS path
                segment is represented by a triple <type, length, value>.

                 The type is a 1-octet field which has two possible values:
                  1 AS_SET: unordered set of ASs a route in the UPDATE
                 message has traversed
                  2 AS_SEQUENCE: ordered set of ASs a route in the UPDATE
                message has traversed.

                The length is a 1-octet field containing the number of ASs
                in the value field.

                The value field contains one or more AS numbers, each AS is
                represented in the octet string as a pair of octets according
                to the following algorithm:
                   first-byte-of-pair = ASNumber / 256;
                   second-byte-of-pair = ASNumber & 255;"
        ::= { wfBgpPathAttributeEntry 6 }

    wfBgpPathAttributeNextHop OBJECT-TYPE
        SYNTAX	IpAddress
        ACCESS	read-only
        STATUS	mandatory
        DESCRIPTION
                "the address of the border router that should be used as the
                next-hop for the destination network."
        ::= { wfBgpPathAttributeEntry 7 }

    wfBgpPathAttributeMultiExitDisc OBJECT-TYPE
        SYNTAX	INTEGER
        ACCESS	read-only
        STATUS	mandatory
        DESCRIPTION
                "The optional inter-AS metric. If this attribute has not been
                provided for this route, the value for this object is -1."
        ::= { wfBgpPathAttributeEntry 8 }

    wfBgpPathAttributeLocalPref OBJECT-TYPE
        SYNTAX	INTEGER
        ACCESS	read-only
        STATUS	mandatory
        DESCRIPTION
                "the originating BGP speaker's degree of preference
                for advertised route (-1..2147483647); if this attribute
                       has not been provided for this route, the value for this
                       object is -1."
        ::= { wfBgpPathAttributeEntry 9 }

    wfBgpPathAttributeAtomicAggregate OBJECT-TYPE
        SYNTAX	INTEGER {
    		    false(1),
    		    true(2)
    		}
        ACCESS	read-only
        STATUS	mandatory
        DESCRIPTION
                "indicates whether or not the local system has selected a less
                specific route without selecting a more specific route"
        ::= { wfBgpPathAttributeEntry 10 }

    wfBgpPathAttributeAggregatorAS OBJECT-TYPE
        SYNTAX	INTEGER
        ACCESS	read-only
        STATUS	mandatory
        DESCRIPTION
                "The AS number of the last BGP speaker that performed route
                aggregation. A value of zero (0) indicates the absence of
                this attribute."
        ::= { wfBgpPathAttributeEntry 11 }

    wfBgpPathAttributeAggregatorAddr OBJECT-TYPE
        SYNTAX	IpAddress
        ACCESS	read-only
        STATUS	mandatory
        DESCRIPTION
                "The BGP ID of the last BGP speaker that performed route
                aggregation.  A value of 0.0.0.0 indicates the absence
                of this attribute."
        ::= { wfBgpPathAttributeEntry 12 }

    wfBgpPathAttributeCalcLocalPref OBJECT-TYPE
        SYNTAX	INTEGER
        ACCESS	read-only
        STATUS	mandatory
        DESCRIPTION
                "The degree of preference calculated by the receiving
                BGP speaker for an advertised route (-1..2147483647).
                A value of -1 indicates the absence of this attribute"
        ::= { wfBgpPathAttributeEntry 13 }

    wfBgpPathAttributeBest OBJECT-TYPE
        SYNTAX	INTEGER {
    		    false(1),
    		    true(2),
    		    bestused(3),
    		    used(4)
    		}
        ACCESS	read-only
        STATUS	mandatory
        DESCRIPTION
                "an indication of whether or not this was chosen as
                the best bgp rout to the destination and whether or not
                it was chosen as a forwarding IP route"
        DEFVAL	{ false }
        ::= { wfBgpPathAttributeEntry 14 }

    wfBgpPathAttributeUnknown OBJECT-TYPE
        SYNTAX	OCTET STRING
        ACCESS	read-only
        STATUS	mandatory
        DESCRIPTION
                "One or more path attributes not understood
                by this BGP speaker.  Size zero (0) indicates
                the absence of such attribute(s).  Octets
                beyond the maximum size (255), if any, are not
                recorded by this object."
        ::= { wfBgpPathAttributeEntry 15 }

    wfBgpPathAttributeClusterID OBJECT-TYPE
        SYNTAX	OCTET STRING
        ACCESS	read-only
        STATUS	mandatory
        DESCRIPTION
                "For RS, the sequence of Cluter IDs of the Clusters.
                Size zero (0) indicates the absence of such attribute(s)."
        ::= { wfBgpPathAttributeEntry 16 }

    wfBgpPathAttributeCommunity OBJECT-TYPE
        SYNTAX	OCTET STRING
        ACCESS	read-only
        STATUS	mandatory
        DESCRIPTION
                "List of BGP communities. Each community is
                4 bytes long.  Size zero (0) indicates
                the absence of community attribute.  Octets
                beyond the maximum size (255), if any, are not
                recorded by this object."
        ::= { wfBgpPathAttributeEntry 17 }

    wfBgpPathAttributeCalcMED OBJECT-TYPE
        SYNTAX        INTEGER
        ACCESS        read-only
        STATUS        mandatory
        DESCRIPTION
                "The Multi Exit Disc. calculated by the receiving
                BGP speaker for an advertised route (-1...2G)"
        ::= { wfBgpPathAttributeEntry 18 }

    wfBgpPathAttributeFlapPenalty OBJECT-TYPE
        SYNTAX  INTEGER
        ACCESS  read-only
        STATUS  mandatory
        DESCRIPTION
                "Penalty value based on number of route flaps"
        ::= { wfBgpPathAttributeEntry 19 }

    wfBgpPathAttributeFlapCount OBJECT-TYPE
        SYNTAX  INTEGER
        ACCESS  read-only
        STATUS  mandatory
        DESCRIPTION
                "Number of times a route flapped since the last time the penaltywas reset to zero"
        ::= { wfBgpPathAttributeEntry 20}

    wfBgpPathAttributeRouteDampened OBJECT-TYPE
        SYNTAX  INTEGER {
                    announced(1),
                    suppressed(2)
                }
        ACCESS  read-only
        STATUS  mandatory
        DESCRIPTION
                "Shows whether this route is currently suppressed from being announced"
        ::= { wfBgpPathAttributeEntry 21 }


    wfBgpRouteFlapDampeningTable OBJECT-TYPE
        SYNTAX  SEQUENCE OF WfBgpRouteFlapDampeningEntry
        ACCESS  not-accessible
        STATUS  mandatory
        DESCRIPTION
                "Table of wfBgpRouteFlapDampeningEntry"
        ::= { wfBgpGeneralGroup 8 }

    wfBgpRouteFlapDampeningEntry OBJECT-TYPE
        SYNTAX  WfBgpRouteFlapDampeningEntry
        ACCESS  not-accessible
        STATUS  mandatory
        DESCRIPTION
                "An entry in the Route Flap Dampening table"
        INDEX   { wfBgpRouteFlapDampeningIndex }
        ::= { wfBgpRouteFlapDampeningTable 1 }

    WfBgpRouteFlapDampeningEntry ::= SEQUENCE {
            wfBgpRouteFlapDampeningDelete
                INTEGER,
            wfBgpRouteFlapDampeningIndex
                INTEGER,
            wfBgpRouteFlapDampeningName
                DisplayString,
            wfBgpRouteFlapDampeningCutoffThreshold
                INTEGER,
            wfBgpRouteFlapDampeningReuseThreshold
                INTEGER,
            wfBgpRouteFlapDampeningReachableDecay
                INTEGER,
            wfBgpRouteFlapDampeningUnreachableDecay
                INTEGER,
            wfBgpRouteFlapDampeningMaxHoldDown
                INTEGER,
            wfBgpRouteFlapDampeningMemoryLimit
                INTEGER
            }

     wfBgpRouteFlapDampeningDelete OBJECT-TYPE
        SYNTAX  INTEGER {
                    created(1),
                    deleted(2)
                }
        ACCESS  read-write
        STATUS  mandatory
        DESCRIPTION
                "Create/Delete: if set to delete, the entry is removed"
        DEFVAL  { created }
        ::= { wfBgpRouteFlapDampeningEntry 1 }

    wfBgpRouteFlapDampeningIndex OBJECT-TYPE
        SYNTAX  INTEGER 
        ACCESS  read-only
        STATUS  mandatory
        DESCRIPTION
                "Index number of this entry in wfBgpRouteFlapDampeningTable"
        ::= { wfBgpRouteFlapDampeningEntry 2 }

    wfBgpRouteFlapDampeningName OBJECT-TYPE
        SYNTAX  DisplayString
        ACCESS  read-write
        STATUS  mandatory
        DESCRIPTION
                "Name of this template"
        ::= { wfBgpRouteFlapDampeningEntry 3 }

    wfBgpRouteFlapDampeningCutoffThreshold OBJECT-TYPE
        SYNTAX  INTEGER (1..20000)
        ACCESS  read-write
        STATUS  mandatory
        DESCRIPTION
                "Value of penalty over which a route is suppressed. 
                 Expressed in number of withdrawals"
        DEFVAL  { 2000 }
        ::= { wfBgpRouteFlapDampeningEntry 4 }

    wfBgpRouteFlapDampeningReuseThreshold OBJECT-TYPE
        SYNTAX  INTEGER (1..20000)
        ACCESS  read-write
        STATUS  mandatory
        DESCRIPTION
                "Value of penalty below which a route is unsuppressed. 
                 Expressed in number of withdrawals"
        DEFVAL  { 750 }
        ::= { wfBgpRouteFlapDampeningEntry 5 }

    wfBgpRouteFlapDampeningReachableDecay OBJECT-TYPE
        SYNTAX  INTEGER (1..45) 
        ACCESS  read-write
        STATUS  mandatory
        DESCRIPTION
                "Duration in minutes after which the penalty value is 
                 reduced to half when the route is reachable. 
                 Default is 5 minutes"
        DEFVAL  { 5 }
        ::= { wfBgpRouteFlapDampeningEntry 6 }

    wfBgpRouteFlapDampeningUnreachableDecay OBJECT-TYPE
        SYNTAX  INTEGER (1..45)
        ACCESS  read-write
        STATUS  mandatory
        DESCRIPTION
                "Duration in minutes after which the penalty value is 
                 reduced to half when the route is unreachable. 
                 Default is 15 minutes."
        DEFVAL  { 15}
        ::= { wfBgpRouteFlapDampeningEntry 7 }

    wfBgpRouteFlapDampeningMaxHoldDown OBJECT-TYPE
        SYNTAX  INTEGER (1..60)
        ACCESS  read-write
        STATUS  mandatory
        DESCRIPTION
                "Maximum time a route remains suppressed. 
                 Expressed in number seconds. Default is 45 minutes"
        DEFVAL  { 45}
        ::= { wfBgpRouteFlapDampeningEntry 8 }

    wfBgpRouteFlapDampeningMemoryLimit OBJECT-TYPE
        SYNTAX  INTEGER (1..60)
        ACCESS  read-write
        STATUS  mandatory
        DESCRIPTION
                "If the state of a route(reachable/unreachable) 
                 remains stable for this duration, the penalty is cleared 
                 and the route unsuppressed. 
                 Expressed in number of minutes. Default is 45 minutes"
        DEFVAL  { 45 }
        ::= { wfBgpRouteFlapDampeningEntry 9 }

    END  -- Wellfleet-BGP-MIB
