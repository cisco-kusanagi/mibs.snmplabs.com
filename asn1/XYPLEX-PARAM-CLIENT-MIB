XYPLEX-PARAM-CLIENT-MIB DEFINITIONS ::= BEGIN
            
                    IMPORTS
                            enterprises, Counter
                                    FROM RFC1155-SMI
                            DisplayString
                                    FROM RFC1158-MIB
                            OBJECT-TYPE
                                    FROM RFC1212-CONCISE-MIB
                            DateTime, AddressType
                                    FROM XYPLEX-SYSTEM-MIB;
            
            xyplex         OBJECT IDENTIFIER ::= { enterprises 33 }
            paramClient    OBJECT IDENTIFIER ::= { xyplex 7 }
            
            --  This MIB module uses the extended OBJECT-TYPE macro as
            --  defined in [9]
            
            --  this is the MIB module for clients of Xyplex parameter
            --  service
            
            -- Textual Conventions, duplicated from the Xyplex System
            -- MIB to satisfy MIB compilers





















            
            
            
            
            
            
            -- the Parameter Client group
            
            -- Implementation of this group is mandatory for all Xyplex
            -- systems that use the Xyplex parameter service
            
            paramClientLoaderName OBJECT-TYPE
                SYNTAX DisplayString
                ACCESS read-only
                STATUS mandatory
                DESCRIPTION
                    "The name of the system that most recently provided 
                    this system's stored parameters.  Corresponds 
                    directly to the name value labeled 'Loaded From:' in 
                    the PARAMETER SERVER display."
                ::= { paramClient 1 }
            
            paramClientLoaderAddressType OBJECT-TYPE
                SYNTAX AddressType
                ACCESS read-only
                STATUS mandatory
                DESCRIPTION
                    "The type of network address contained in 
                    paramClientLoaderAddress.  'unknown' means no 
                    address has been defined.  'other' means no other 
                    type value applies.  'local' means there is no 
                    address and parameters were loaded from local 
                    storage.  'ip' is an Internet IP address.  
                    'ethernet' is an 802.3 MAC address.  Corresponds 
                    indirectly to the address value labeled 'Loaded 
                    From:' in the PARAMETER SERVER display."
                ::= { paramClient 2 }
            
            paramClientLoaderAddress OBJECT-TYPE
                SYNTAX OCTET STRING
                ACCESS read-only
                STATUS mandatory
                DESCRIPTION
                    "The network address of the system that most 
                    recently provided this system's stored parameters.  
                    Corresponds directly to the address value labeled 
                    'Loaded From:' in the PARAMETER SERVER display."
                ::= { paramClient 3 }
            
            paramClientParameterVersion OBJECT-TYPE
                SYNTAX INTEGER
                ACCESS read-write

            
            
            
            
            
            
                STATUS mandatory
                DESCRIPTION
                    "The version number of the parameters as stored in 
                    this system's local memory.  Corresponds directly to 
                    SERVER PARAMETER VERSION and the value labeled 'Last 
                    Update Version:' in the PARAMETER SERVER display."
                ::= { paramClient 4 }
            
            paramClientUpdateTime OBJECT-TYPE
                SYNTAX DateTime
                ACCESS read-only
                STATUS mandatory
                DESCRIPTION
                    "This system's local date and time when it last 
                    attempted to store parameters with a parameter 
                    server.  Corresponds directly to the values labeled 
                    'Last Update Date:' and 'Last Update Time:' in the 
                    PARAMETER SERVER display."
                ::= { paramClient 5 }
            
            paramClientServerCheck OBJECT-TYPE
                SYNTAX INTEGER { disabled(1), enabled(2) }
                ACCESS read-write
                STATUS mandatory
                DESCRIPTION
                    "Control over whether or not this system is allowed 
                    to check for additional parameter servers.  
                    'enabled' allows checking.  Corresponds directly to 
                    PARAMETER SERVER CHECK and the presence of PARAMETER 
                    POLLING under the label 'Enabled Characteristics' in 
                    the SERVER CHARACTERISTICS display."
                ::= { paramClient 6 }
            
            paramClientCheckInterval OBJECT-TYPE
                SYNTAX INTEGER (1..120)
                ACCESS read-write
                STATUS mandatory
                DESCRIPTION
                    "The number of minutes between checks for additional 
                    parameter servers.  Corresponds directly to 
                    PARAMETER SERVER CHECK TIMER and the value labeled 
                    'Check Timer:' in the PARAMETER SERVER display."
                ::= { paramClient 7 }
            
            paramClientCheckNow OBJECT-TYPE
                SYNTAX INTEGER { ready(1), execute(2) }

            
            
            
            
            
            
                ACCESS read-write
                STATUS mandatory
                DESCRIPTION
                    "Control to cause this system to immediately check 
                    for additional parameter servers.  The agent always 
                    returns 'ready' for this value.  Setting the value 
                    to 'ready' has no effect.  Setting it to 'execute' 
                    causes a check to be started.  Corresponds to the 
                    CHECK PARAMETER SERVER command."
                ::= { paramClient 8 }
            
            paramClientServerLimit OBJECT-TYPE
                SYNTAX INTEGER (1..8)
                ACCESS read-write
                STATUS mandatory
                DESCRIPTION
                    "The maximum number of parameter servers this system 
                    is allowed to remember at the same time.  
                    Corresponds directly to PARAMETER SERVER LIMIT and 
                    the value labeled 'Parameter Server Limit:' in the 
                    PARAMETER SERVER display."
                ::= { paramClient 9 }
            
            paramClientRetransmitInterval OBJECT-TYPE
                SYNTAX INTEGER (1..30)
                ACCESS read-write
                STATUS mandatory
                DESCRIPTION
                    "The number of minutes between this system's 
                    attempts to store new parameters with a server that 
                    has not acknowledged previous attempts.  Corresponds 
                    directly to PARAMETER SERVER RETRANSMIT TIMER and 
                    the value labeled 'Retransmit Timer: in the 
                    PARAMETER SERVER display."
                ::= { paramClient 10 }
            
            paramClientRetransmitLimit OBJECT-TYPE
                SYNTAX INTEGER (1..100)
                ACCESS read-write
                STATUS mandatory
                DESCRIPTION
                    "The maximum number of attempts by this system to 
                    store new parameters with a server that has not 
                    acknowledged previous attempts.  Corresponds 
                    directly to PARAMETER SERVER RETRANSMIT LIMIT and 
                    the value labeled 'Retransmit Limit:' in the 

            
            
            
            
            
            
                            PARAMETER SERVER display."
                ::= { paramClient 11 }
            
            paramClientState OBJECT-TYPE
                SYNTAX INTEGER { other(1), idle(2), internal1(3),
                                 internal2(4), internal3(5),
                                 internal4(6), internal5(7),
                                 internal6(8), internal7(9),
                                 internal8(10), hold(11),  retry(12)}
                ACCESS read-only
                STATUS mandatory
                DESCRIPTION
                    "This system's state with regard to update attempts.  
                    The value meanings are:
            
                    other       none of the following
                    idle        no update in progress
                    internal    internal state of no meaning to manager
                    hold        holding to keep from updating too often
                    retry       waiting to retry after failure
            
                    Corresponds directly to the value labeled 'Storage 
                    State:' in the PARAMETER SERVER display."
                ::= { paramClient 12 }
            
            paramClientProtocolErrors OBJECT-TYPE
                SYNTAX Counter
                ACCESS read-only
                STATUS mandatory
                DESCRIPTION
                    "The number of invalid parameter service protocol 
                    messages received by this system.  Corresponds 
                    directly to the value labeled 'Bad Parameter 
                    Messages:' in the PARAMETER SERVER display."
                ::= { paramClient 13 }
            
            paramClientServerRejects OBJECT-TYPE
                SYNTAX Counter
                ACCESS read-only
                STATUS mandatory
                DESCRIPTION
                    "The number of parameter servers this system 
                    rejected due to exceeding paramClientServerLimit.  
                    Corresponds directly to the value labeled 'Rejected 
                    Servers:' in the PARAMETER SERVER display."
                ::= { paramClient 14 }

            
            
            
            
            
            
            
            paramClientServerNumber OBJECT-TYPE
                SYNTAX INTEGER
                ACCESS read-only
                STATUS mandatory
                DESCRIPTION
                    "The number of parameter servers known to this 
                    system, indicating the number of entries in 
                    serverTable.  Corresponds directly to the value 
                    labeled 'Parameter Servers:' in the PARAMETER SERVER 
                    display."
                ::= { paramClient 15 }


































            
            
            
            
            
            
            -- the Parameter Server table
            
            paramServerTable OBJECT-TYPE
                SYNTAX SEQUENCE OF ParamServerEntry
                ACCESS not-accessible
                STATUS mandatory
                DESCRIPTION
                    "A list of parameter server entries.  The number of 
                    entries is given by the value of 
                    paramClientServerNumber."
                ::= { paramClient 16 }
            
            paramServerEntry OBJECT-TYPE
                SYNTAX ParamServerEntry
                ACCESS not-accessible
                STATUS mandatory
                DESCRIPTION
                    "Status and parameter values for a parameter 
                    server."
                INDEX { paramServerName }
                ::= { paramServerTable 1 }
            
            ParamServerEntry ::=
                SEQUENCE {
                    paramServerName
                        DisplayString,
                    paramServerEntryStatus
                        INTEGER,
                    paramServerAddressType
                        INTEGER,
                    paramServerAddress
                        OCTET STRING,
                    paramServerStoredVersion
                        INTEGER,
                    paramServerStoredTime
                        DateTime,
                    paramServerStoredStatus
                        INTEGER,
                    paramServerStoredFailure
                        INTEGER
                }
            
            paramServerName OBJECT-TYPE
                SYNTAX DisplayString (SIZE (16))
                ACCESS read-write
                STATUS mandatory

            
            
            
            
            
            
                DESCRIPTION
                    "The server's name, unique within this system.  
                    Always 16 characters, null padded on the end.  
                    Corresponds directly to the name used to create the 
                    entry and the value labeled 'Name' in the PARAMETER 
                    SERVER display."
                ::= { paramServerEntry 1 }
            
            paramServerEntryStatus OBJECT-TYPE
                SYNTAX INTEGER { invalid(1), valid(2) }
                ACCESS read-write
                STATUS mandatory
                DESCRIPTION
                    "The status of the entry.  Set to 'invalid' to 
                    remove the entry, which corresponds directly to the 
                    CLEAR/PURGE PARAMETER SERVER command.  Actual 
                    removal of the entry is implementation specific."
                DEFVAL { valid }
                ::= { paramServerEntry 2 }
            
            paramServerAddressType OBJECT-TYPE
                SYNTAX AddressType
                ACCESS read-write
                STATUS mandatory
                DESCRIPTION
                    "The type of network address contained in 
                    paramServerAddress.  'unknown' means no address has 
                    been defined.  'other' means no other type value 
                    applies.  'local' means there is no address and 
                    parameters were loaded from local storage.  'ip' is 
                    an Internet IP address.  'ethernet' is an 802.3 MAC 
                    address.  Corresponds indirectly to the value 
                    labeled 'Address' in the PARAMETER SERVER display."
                DEFVAL { unknown }
                ::= { paramServerEntry 3 }
            
            paramServerAddress OBJECT-TYPE
                SYNTAX OCTET STRING
                ACCESS read-write
                STATUS mandatory
                DESCRIPTION
                    "The server's network address.  Corresponds directly 
                    to the value labeled 'Address' in the PARAMETER 
                    SERVER display."
                DEFVAL { null }  -- 'null' indicates zero length
                ::= { paramServerEntry 4 }

            
            
            
            
            
            
            
            paramServerStoredVersion OBJECT-TYPE
                SYNTAX INTEGER
                ACCESS read-only
                STATUS mandatory
                DESCRIPTION
                    "Parameter version number currently stored at the 
                    server.  Corresponds directly to the value labeled 
                    'Version' in the PARAMETER SERVER display."
                DEFVAL { 0 }
                ::= { paramServerEntry 5 }
            
            paramServerStoredTime OBJECT-TYPE
                SYNTAX DateTime
                ACCESS read-only
                STATUS mandatory
                DESCRIPTION
                    "The server's date and time when it stored the 
                    parameters of version paramServerStoredVersion.  
                    Corresponds directly to the value labeled 'Date' in 
                    the PARAMETER SERVER display."
                DEFVAL { 0 }
                ::= { paramServerEntry 6 }
            
            paramServerStoredStatus OBJECT-TYPE
                SYNTAX INTEGER { unknown(1), current(2), ahead(3),
                                 behind(4), failing(5), failed(6),
                                 query(7) }
                ACCESS read-only
                STATUS mandatory
                DESCRIPTION
                    "Status of this system's parameters with respect to 
                    the server.  Corresponds directly to the value 
                    labeled 'Status' in the PARAMETER SERVER display.  
                    The value meanings are:
            
                    ahead     server version newer than system's
                    behind    server version older than system's
                    current   up to date
                    failed    system no longer attempting update
                    failing   system trying to update but failing
                    query     attempting to determine version
                    unknown   version not known
                    "
                DEFVAL { unknown }
                ::= { paramServerEntry 7 }

            
            
            
            
            
            
            
            paramServerStoredFailure OBJECT-TYPE
                SYNTAX INTEGER { other(1), none(2), protocolOut(3),
                                 open(4), read(5), write(6), 
            resource(7),
                                 protocolIn(8), response(9),
                                 close(10), delete(11), rename(12),
                                 fileData(13) }
                ACCESS read-only
                STATUS mandatory
                DESCRIPTION
                    "When paramServerStoredStatus is 'failed' or 
                    'failing', the reason for the most recent failure.  
                    Corresponds directly to the value labeled 'Reason' 
                    in the PARAMETER SERVER display.  The value meanings 
                    are:
            
                    other        none of the following
                    none         no failure
                    protocolOut  invalid protocol message to server
                    open         file open error at server
                    read         file read error at server
                    write        file write error at server
                    resource     resource lack at server (e.g. disk)
                    protocolIn   invalid protocol message from server
                    response     no response from server
                    close        file close error at server
                    delete       file delete error at server
                    rename       file rename error at server
                    fileData     bad parameter data stored at server
                    "
                DEFVAL { none }
                ::= { paramServerEntry 8 }
            
END
