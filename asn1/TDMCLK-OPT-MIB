-- Version 2.15.1.1, modified 2001-05-31 17:28:51-04 

        TDMCLK-OPT-MIB DEFINITIONS ::= BEGIN

        IMPORTS
				enterprises FROM RFC1155-SMI
            OBJECT-TYPE
                FROM RFC-1212;

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

          cdx6500Statistics OBJECT IDENTIFIER ::= { cdx6500 3 }
 cdx6500StatOtherStatsGroup OBJECT IDENTIFIER ::= { cdx6500Statistics 2 }
       cdx6500STTdmClkGroup OBJECT IDENTIFIER ::= { cdx6500StatOtherStatsGroup 13 } 


        DisplayString ::= OCTET STRING
        -- This data type is used to model textual information taken
        -- from the NVT ASCII character set.  By convention, objects
        -- with this syntax are declared as having SIZE (0..255)

        -- The TDM CLOCK  group

        cdx6500TdmClkTable OBJECT-TYPE
            SYNTAX SEQUENCE OF Cdx6500TdmClkCfgEntry
            ACCESS not-accessible
            STATUS mandatory
            DESCRIPTION
                "A list of Configuration parameters that makeup
                 the TDM Clock Table."
        ::= { cdx6500CfgGeneralGroup 24 }

        cdx6500TdmClkCfgEntry OBJECT-TYPE
            SYNTAX Cdx6500TdmClkCfgEntry 
            ACCESS not-accessible
            STATUS mandatory
            DESCRIPTION
                "Each entry contains the Configuration parameters for
                 each Tdm clock table."
            INDEX { cdx6500TdmClkEntryNumber }
        ::= { cdx6500TdmClkTable 1 }

        Cdx6500TdmClkCfgEntry ::=
            SEQUENCE {
                cdx6500TdmClkEntryNumber 
                    INTEGER,
                cdx6500TdmClkPriority
                    INTEGER
                }

        cdx6500TdmClkEntryNumber OBJECT-TYPE
            SYNTAX INTEGER 
            ACCESS read-only
            STATUS mandatory
            DESCRIPTION
                "This identifies the particular TDM Network Clock Table
                 entry being configured. The number of instances
                 defined by this entry depends on the configured value
                 of the Maximum TDM Network Clock Entry parameter in the
                 Node record (upto a maximum of 1024 entries). "
        ::= { cdx6500TdmClkCfgEntry 1 }

        cdx6500TdmClkPriority OBJECT-TYPE
            SYNTAX INTEGER
            ACCESS read-only
            STATUS mandatory
            DESCRIPTION
                "The Network Clock Priority determines the order 
                 in which the network clock will be chosen
		   0 : Interface will not supply the network clock.
                   1 - 3: Interface priority for supplying 
			  the network clock."
        ::= { cdx6500TdmClkCfgEntry 2 }

        -- the TDM Clock Statistics Group for a restoral port

       tdmClkStatus  OBJECT-TYPE
            SYNTAX DisplayString (SIZE(0..255))
            ACCESS read-only
            STATUS optional
            DESCRIPTION
                "The Status of Current Network Clock." 
        ::= { cdx6500STTdmClkGroup 1 }

       tdmClkRegisteredTDMTable OBJECT-TYPE
            SYNTAX SEQUENCE OF TdmClkRegisteredTDMEntry 
            ACCESS not-accessible
            STATUS mandatory
            DESCRIPTION
                 "The Table of registered TDM Number."
        ::= { cdx6500STTdmClkGroup 2 }

        tdmClkRegisteredTDMEntry OBJECT-TYPE
            SYNTAX TdmClkRegisteredTDMEntry 
            ACCESS not-accessible
            STATUS mandatory
            DESCRIPTION
                "Each entry contains the Registered TDM Number." 
            INDEX { cdx6500TdmClkEntryNumber }
        ::= { tdmClkRegisteredTDMTable 1 }

        TdmClkRegisteredTDMEntry ::=
            SEQUENCE {
                tdmClkRegisteredTDMEntryNumber
                    INTEGER,
                tdmClkRegisteredTDM 
                    DisplayString
                }

        tdmClkRegisteredTDMEntryNumber OBJECT-TYPE
            SYNTAX INTEGER 
            ACCESS read-only
            STATUS mandatory
            DESCRIPTION
                "This identifies the particular tdmClkRegisteredTDMNumTable."
        ::= { tdmClkRegisteredTDMEntry 1 }
 
       tdmClkRegisteredTDM OBJECT-TYPE
            SYNTAX DisplayString 
            ACCESS read-only
            STATUS optional
            DESCRIPTION
                "Current Registered TDM Number."
        ::= { tdmClkRegisteredTDMEntry 2 }

    END
