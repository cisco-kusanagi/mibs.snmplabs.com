--			Ascend mibb52test MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBB52TEST-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibb52TestProfile  OBJECT IDENTIFIER ::= { configuration 56}

	-- The mibb52TestProfile table
	--
	-- This table contains parameters for the mibb52TestProfile profile
	--

    mibb52TestProfileTable	OBJECT-TYPE
	SYNTAX		SEQUENCE OF Mibb52TestProfileEntry
	ACCESS		not-accessible
	STATUS		mandatory
	DESCRIPTION	"A list of mibb52TestProfile profile entries."
	::= { mibb52TestProfile 1 }

    mibb52TestProfileEntry	OBJECT-TYPE
	SYNTAX		Mibb52TestProfileEntry
	ACCESS		not-accessible
	STATUS		mandatory
	DESCRIPTION	"A mibb52TestProfile entry containing objects that
			 maps to the parameters of mibb52TestProfile profile."
	INDEX		{ b52TestProfile-Index-o }
	::= { mibb52TestProfileTable 1 }

    Mibb52TestProfileEntry ::=
	SEQUENCE {
	    b52TestProfile-Index-o
		INTEGER,
	    b52TestProfile-TftpBootType
		INTEGER,
	    b52TestProfile-TftpBootHostName
		DisplayString,
	    b52TestProfile-TftpBootBaseName
		DisplayString,
	    b52TestProfile-Action-o
		INTEGER
	}

    b52TestProfile-Index-o	OBJECT-TYPE
	SYNTAX	INTEGER
	ACCESS	read-only
	STATUS	mandatory
	DESCRIPTION	""
	::= { mibb52TestProfileEntry 1 }

    b52TestProfile-TftpBootType	OBJECT-TYPE
	SYNTAX	INTEGER {
		    none (1),
		    tftpBootFirst (2),
		    tftpBootSecond (3)
		}
	ACCESS	read-write
	STATUS	mandatory
	DESCRIPTION	"TFTP Boot type"
	::= { mibb52TestProfileEntry 2 }

    b52TestProfile-TftpBootHostName	OBJECT-TYPE
	SYNTAX	DisplayString
	ACCESS	read-write
	STATUS	mandatory
	DESCRIPTION	"Name of the TFTP boot server we should use."
	::= { mibb52TestProfileEntry 3 }

    b52TestProfile-TftpBootBaseName	OBJECT-TYPE
	SYNTAX	DisplayString
	ACCESS	read-write
	STATUS	mandatory
	DESCRIPTION	"Base filename for the TFTP boot files we should use."
	::= { mibb52TestProfileEntry 4 }

    b52TestProfile-Action-o	OBJECT-TYPE
	SYNTAX	INTEGER {
		    noAction (1),
		    createProfile (2),
		    deleteProfile (3)
		}
	ACCESS	read-write
	STATUS	mandatory
	DESCRIPTION	""
	::= { mibb52TestProfileEntry 5 }

END
