TERAWAVE-terads1-MIB DEFINITIONS ::= BEGIN
        -- Created by sml2mib compiler 
        IMPORTS

 enterprises,  OBJECT-TYPE,  Counter,  Gauge,  TimeTicks
        FROM RFC1155-SMI
		  Gauge32 FROM SNMPv2-SMI;

terawave OBJECT IDENTIFIER ::=  { enterprises 4513 }

teraDs1Group OBJECT IDENTIFIER ::=  { terawave 11 }

     -- teradsx1CurrentTable

teradsx1CurrentTable OBJECT-TYPE
     SYNTAX SEQUENCE OF Teradsx1CurrentTableEntryType
     ACCESS not-accessible
     STATUS mandatory
     DESCRIPTION
          " table teradsx1CurrentTable"
     ::= { teraDs1Group 1 }

teradsx1CurrentTableEntry OBJECT-TYPE
          SYNTAX Teradsx1CurrentTableEntryType
          ACCESS not-accessible
          STATUS mandatory
          DESCRIPTION
               " table entry teradsx1CurrentTableEntry "
          INDEX {                   teradsx1CurrentIndex }
     ::= { teradsx1CurrentTable 1 }

Teradsx1CurrentTableEntryType ::= SEQUENCE {
          teradsx1CurrentIndex   
             INTEGER,
          teradsx1CurrentESs   
             INTEGER,
          teradsx1CurrentSESs   
             INTEGER,
          teradsx1CurrentSEFSs   
             INTEGER,
          teradsx1CurrentUASs   
             INTEGER,
          teradsx1CurrentCSSs   
             Gauge32,
          teradsx1CurrentPCVs   
             Gauge32,
          teradsx1CurrentLESs   
             Gauge32,
          teradsx1CurrentBESs   
             Gauge32,
          teradsx1CurrentDMs   
             Gauge32,
          teradsx1CurrentLCVs   
             Gauge32,
          teradsx1CurrentLOF   
             Gauge32,
          teradsx1CurrentYELLOW   
             Gauge32,
          teradsx1CurrentAIS   
             Gauge32,
          teraStandarddsx1CurrentLOF   
             Gauge32,
          teraStandarddsx1CurrentYELLOW   
             Gauge32,
          teraStandarddsx1CurrentAIS   
             Gauge32,
          teraStandarddsx1CurrentLOSs   
             Gauge32
}

teradsx1CurrentIndex OBJECT-TYPE
          SYNTAX INTEGER
          ACCESS read-only
          STATUS mandatory
          DESCRIPTION
               ""
          ::= { teradsx1CurrentTableEntry 1 }

teradsx1CurrentESs OBJECT-TYPE
          SYNTAX INTEGER
          ACCESS read-only
          STATUS mandatory
          DESCRIPTION
               ""
          ::= { teradsx1CurrentTableEntry 2 }

teradsx1CurrentSESs OBJECT-TYPE
          SYNTAX INTEGER
          ACCESS read-only
          STATUS mandatory
          DESCRIPTION
               ""
          ::= { teradsx1CurrentTableEntry 3 }

teradsx1CurrentSEFSs OBJECT-TYPE
          SYNTAX INTEGER
          ACCESS read-only
          STATUS mandatory
          DESCRIPTION
               ""
          ::= { teradsx1CurrentTableEntry 4 }

teradsx1CurrentUASs OBJECT-TYPE
          SYNTAX INTEGER
          ACCESS read-only
          STATUS mandatory
          DESCRIPTION
               ""
          ::= { teradsx1CurrentTableEntry 5 }

teradsx1CurrentCSSs OBJECT-TYPE
          SYNTAX Gauge32
          ACCESS read-only
          STATUS mandatory
          DESCRIPTION
               ""
          ::= { teradsx1CurrentTableEntry 6 }

teradsx1CurrentPCVs OBJECT-TYPE
          SYNTAX Gauge32
          ACCESS read-only
          STATUS mandatory
          DESCRIPTION
               ""
          ::= { teradsx1CurrentTableEntry 7 }

teradsx1CurrentLESs OBJECT-TYPE
          SYNTAX Gauge32
          ACCESS read-only
          STATUS mandatory
          DESCRIPTION
               ""
          ::= { teradsx1CurrentTableEntry 8 }

teradsx1CurrentBESs OBJECT-TYPE
          SYNTAX Gauge32
          ACCESS read-only
          STATUS mandatory
          DESCRIPTION
               ""
          ::= { teradsx1CurrentTableEntry 9 }

teradsx1CurrentDMs OBJECT-TYPE
          SYNTAX Gauge32
          ACCESS read-only
          STATUS mandatory
          DESCRIPTION
               ""
          ::= { teradsx1CurrentTableEntry 10 }

teradsx1CurrentLCVs OBJECT-TYPE
          SYNTAX Gauge32
          ACCESS read-only
          STATUS mandatory
          DESCRIPTION
               ""
          ::= { teradsx1CurrentTableEntry 11 }

teradsx1CurrentLOF OBJECT-TYPE
          SYNTAX Gauge32
          ACCESS read-only
          STATUS mandatory
          DESCRIPTION
               ""
          ::= { teradsx1CurrentTableEntry 12 }

teradsx1CurrentYELLOW OBJECT-TYPE
          SYNTAX Gauge32
          ACCESS read-only
          STATUS mandatory
          DESCRIPTION
               ""
          ::= { teradsx1CurrentTableEntry 13 }

teradsx1CurrentAIS OBJECT-TYPE
          SYNTAX Gauge32
          ACCESS read-only
          STATUS mandatory
          DESCRIPTION
               ""
          ::= { teradsx1CurrentTableEntry 14 }

teraStandarddsx1CurrentLOF OBJECT-TYPE
          SYNTAX Gauge32
          ACCESS read-only
          STATUS mandatory
          DESCRIPTION
               ""
          ::= { teradsx1CurrentTableEntry 15 }

teraStandarddsx1CurrentYELLOW OBJECT-TYPE
          SYNTAX Gauge32
          ACCESS read-only
          STATUS mandatory
          DESCRIPTION
               ""
          ::= { teradsx1CurrentTableEntry 16 }

teraStandarddsx1CurrentAIS OBJECT-TYPE
          SYNTAX Gauge32
          ACCESS read-only
          STATUS mandatory
          DESCRIPTION
               ""
          ::= { teradsx1CurrentTableEntry 17 }

teraStandarddsx1CurrentLOSs OBJECT-TYPE
          SYNTAX Gauge32
          ACCESS read-only
          STATUS mandatory
          DESCRIPTION
               ""
          ::= { teradsx1CurrentTableEntry 18 }

     -- teradsx1IntervalTable

teradsx1IntervalTable OBJECT-TYPE
     SYNTAX SEQUENCE OF Teradsx1IntervalTableEntryType
     ACCESS not-accessible
     STATUS mandatory
     DESCRIPTION
          " table teradsx1IntervalTable"
     ::= { teraDs1Group 2 }

teradsx1IntervalTableEntry OBJECT-TYPE
          SYNTAX Teradsx1IntervalTableEntryType
          ACCESS not-accessible
          STATUS mandatory
          DESCRIPTION
               " table entry teradsx1IntervalTableEntry "
          INDEX {                   teradsx1IntervalIndex,                  teradsx1IntervalNumber }
     ::= { teradsx1IntervalTable 1 }

Teradsx1IntervalTableEntryType ::= SEQUENCE {
          teradsx1IntervalIndex   
             INTEGER,
          teradsx1IntervalNumber   
             INTEGER,
          teradsx1IntervalESs   
             Gauge32,
          teradsx1IntervalSESs   
             Gauge32,
          teradsx1IntervalSEFSs   
             Gauge32,
          teradsx1IntervalUASs   
             Gauge32,
          teradsx1IntervalCSSs   
             Gauge32,
          teradsx1IntervalPCVs   
             Gauge32,
          teradsx1IntervalLESs   
             Gauge32,
          teradsx1IntervalBESs   
             Gauge32,
          teradsx1IntervalDMs   
             Gauge32,
          teradsx1IntervalLCVs   
             Gauge32,
          teradsx1IntervalLOF   
             Gauge32,
          teradsx1IntervalYELLOW   
             Gauge32,
          teradsx1IntervalAIS   
             Gauge32,
          teraStandarddsx1IntervalLOF   
             Gauge32,
          teraStandarddsx1IntervalYELLOW   
             Gauge32,
          teraStandarddsx1IntervalAIS   
             Gauge32,
          teraStandarddsx1IntervalLOSs   
             Gauge32
}

teradsx1IntervalIndex OBJECT-TYPE
          SYNTAX INTEGER
          ACCESS read-only
          STATUS mandatory
          DESCRIPTION
               ""
          ::= { teradsx1IntervalTableEntry 1 }

teradsx1IntervalNumber OBJECT-TYPE
          SYNTAX INTEGER
          ACCESS read-only
          STATUS mandatory
          DESCRIPTION
               ""
          ::= { teradsx1IntervalTableEntry 2 }

teradsx1IntervalESs OBJECT-TYPE
          SYNTAX Gauge32
          ACCESS read-only
          STATUS mandatory
          DESCRIPTION
               ""
          ::= { teradsx1IntervalTableEntry 3 }

teradsx1IntervalSESs OBJECT-TYPE
          SYNTAX Gauge32
          ACCESS read-only
          STATUS mandatory
          DESCRIPTION
               ""
          ::= { teradsx1IntervalTableEntry 4 }

teradsx1IntervalSEFSs OBJECT-TYPE
          SYNTAX Gauge32
          ACCESS read-only
          STATUS mandatory
          DESCRIPTION
               ""
          ::= { teradsx1IntervalTableEntry 5 }

teradsx1IntervalUASs OBJECT-TYPE
          SYNTAX Gauge32
          ACCESS read-only
          STATUS mandatory
          DESCRIPTION
               ""
          ::= { teradsx1IntervalTableEntry 6 }

teradsx1IntervalCSSs OBJECT-TYPE
          SYNTAX Gauge32
          ACCESS read-only
          STATUS mandatory
          DESCRIPTION
               ""
          ::= { teradsx1IntervalTableEntry 7 }

teradsx1IntervalPCVs OBJECT-TYPE
          SYNTAX Gauge32
          ACCESS read-only
          STATUS mandatory
          DESCRIPTION
               ""
          ::= { teradsx1IntervalTableEntry 8 }

teradsx1IntervalLESs OBJECT-TYPE
          SYNTAX Gauge32
          ACCESS read-only
          STATUS mandatory
          DESCRIPTION
               ""
          ::= { teradsx1IntervalTableEntry 9 }

teradsx1IntervalBESs OBJECT-TYPE
          SYNTAX Gauge32
          ACCESS read-only
          STATUS mandatory
          DESCRIPTION
               ""
          ::= { teradsx1IntervalTableEntry 10 }

teradsx1IntervalDMs OBJECT-TYPE
          SYNTAX Gauge32
          ACCESS read-only
          STATUS mandatory
          DESCRIPTION
               ""
          ::= { teradsx1IntervalTableEntry 11 }

teradsx1IntervalLCVs OBJECT-TYPE
          SYNTAX Gauge32
          ACCESS read-only
          STATUS mandatory
          DESCRIPTION
               ""
          ::= { teradsx1IntervalTableEntry 12 }

teradsx1IntervalLOF OBJECT-TYPE
          SYNTAX Gauge32
          ACCESS read-only
          STATUS mandatory
          DESCRIPTION
               ""
          ::= { teradsx1IntervalTableEntry 13 }

teradsx1IntervalYELLOW OBJECT-TYPE
          SYNTAX Gauge32
          ACCESS read-only
          STATUS mandatory
          DESCRIPTION
               ""
          ::= { teradsx1IntervalTableEntry 14 }

teradsx1IntervalAIS OBJECT-TYPE
          SYNTAX Gauge32
          ACCESS read-only
          STATUS mandatory
          DESCRIPTION
               ""
          ::= { teradsx1IntervalTableEntry 15 }

teraStandarddsx1IntervalLOF OBJECT-TYPE
          SYNTAX Gauge32
          ACCESS read-only
          STATUS mandatory
          DESCRIPTION
               ""
          ::= { teradsx1IntervalTableEntry 16 }

teraStandarddsx1IntervalYELLOW OBJECT-TYPE
          SYNTAX Gauge32
          ACCESS read-only
          STATUS mandatory
          DESCRIPTION
               ""
          ::= { teradsx1IntervalTableEntry 17 }

teraStandarddsx1IntervalAIS OBJECT-TYPE
          SYNTAX Gauge32
          ACCESS read-only
          STATUS mandatory
          DESCRIPTION
               ""
          ::= { teradsx1IntervalTableEntry 18 }

teraStandarddsx1IntervalLOSs OBJECT-TYPE
          SYNTAX Gauge32
          ACCESS read-only
          STATUS mandatory
          DESCRIPTION
               ""
          ::= { teradsx1IntervalTableEntry 19 }

     -- teradsx1TotalTable

teradsx1TotalTable OBJECT-TYPE
     SYNTAX SEQUENCE OF Teradsx1TotalTableEntryType
     ACCESS not-accessible
     STATUS mandatory
     DESCRIPTION
          " table teradsx1TotalTable"
     ::= { teraDs1Group 3 }

teradsx1TotalTableEntry OBJECT-TYPE
          SYNTAX Teradsx1TotalTableEntryType
          ACCESS not-accessible
          STATUS mandatory
          DESCRIPTION
               " table entry teradsx1TotalTableEntry "
          INDEX {                   teradsx1TotalIndex }
     ::= { teradsx1TotalTable 1 }

Teradsx1TotalTableEntryType ::= SEQUENCE {
          teradsx1TotalIndex   
             INTEGER,
          teradsx1TotalESs   
             Gauge32,
          teradsx1TotalSESs   
             Gauge32,
          teradsx1TotalSEFSs   
             Gauge32,
          teradsx1TotalUAS   
             Gauge32,
          teradsx1TotalCSSs   
             Gauge32,
          teradsx1TotalPCVs   
             Gauge32,
          teradsx1TotalLESs   
             Gauge32,
          teradsx1TotalBESs   
             Gauge32,
          teradsx1TotalDMs   
             Gauge32,
          teradsx1TotalLCVs   
             Gauge32,
          teradsx1TotalLOF   
             Gauge32,
          teradsx1TotalYELLOW   
             Gauge32,
          teradsx1TotalAIS   
             Gauge32,
          teradsx1TotalPerfStat   
             INTEGER,
          teraStandarddsx1TotalLOF   
             Gauge32,
          teraStandarddsx1TotalYELLOW   
             Gauge32,
          teraStandarddsx1TotalAIS   
             Gauge32,
          teraStandarddsx1TotalLOSs   
             Gauge32
}

teradsx1TotalIndex OBJECT-TYPE
          SYNTAX INTEGER
          ACCESS read-only
          STATUS mandatory
          DESCRIPTION
               ""
          ::= { teradsx1TotalTableEntry 1 }

teradsx1TotalESs OBJECT-TYPE
          SYNTAX Gauge32
          ACCESS read-only
          STATUS mandatory
          DESCRIPTION
               ""
          ::= { teradsx1TotalTableEntry 2 }

teradsx1TotalSESs OBJECT-TYPE
          SYNTAX Gauge32
          ACCESS read-only
          STATUS mandatory
          DESCRIPTION
               ""
          ::= { teradsx1TotalTableEntry 3 }

teradsx1TotalSEFSs OBJECT-TYPE
          SYNTAX Gauge32
          ACCESS read-only
          STATUS mandatory
          DESCRIPTION
               ""
          ::= { teradsx1TotalTableEntry 4 }

teradsx1TotalUAS OBJECT-TYPE
          SYNTAX Gauge32
          ACCESS read-only
          STATUS mandatory
          DESCRIPTION
               ""
          ::= { teradsx1TotalTableEntry 5 }

teradsx1TotalCSSs OBJECT-TYPE
          SYNTAX Gauge32
          ACCESS read-only
          STATUS mandatory
          DESCRIPTION
               ""
          ::= { teradsx1TotalTableEntry 6 }

teradsx1TotalPCVs OBJECT-TYPE
          SYNTAX Gauge32
          ACCESS read-only
          STATUS mandatory
          DESCRIPTION
               ""
          ::= { teradsx1TotalTableEntry 7 }

teradsx1TotalLESs OBJECT-TYPE
          SYNTAX Gauge32
          ACCESS read-only
          STATUS mandatory
          DESCRIPTION
               ""
          ::= { teradsx1TotalTableEntry 8 }

teradsx1TotalBESs OBJECT-TYPE
          SYNTAX Gauge32
          ACCESS read-only
          STATUS mandatory
          DESCRIPTION
               ""
          ::= { teradsx1TotalTableEntry 9 }

teradsx1TotalDMs OBJECT-TYPE
          SYNTAX Gauge32
          ACCESS read-only
          STATUS mandatory
          DESCRIPTION
               ""
          ::= { teradsx1TotalTableEntry 10 }

teradsx1TotalLCVs OBJECT-TYPE
          SYNTAX Gauge32
          ACCESS read-only
          STATUS mandatory
          DESCRIPTION
               ""
          ::= { teradsx1TotalTableEntry 11 }

teradsx1TotalLOF OBJECT-TYPE
          SYNTAX Gauge32
          ACCESS read-only
          STATUS mandatory
          DESCRIPTION
               ""
          ::= { teradsx1TotalTableEntry 12 }

teradsx1TotalYELLOW OBJECT-TYPE
          SYNTAX Gauge32
          ACCESS read-only
          STATUS mandatory
          DESCRIPTION
               ""
          ::= { teradsx1TotalTableEntry 13 }

teradsx1TotalAIS OBJECT-TYPE
          SYNTAX Gauge32
          ACCESS read-only
          STATUS mandatory
          DESCRIPTION
               ""
          ::= { teradsx1TotalTableEntry 14 }

teradsx1TotalPerfStat OBJECT-TYPE
          SYNTAX INTEGER
                  {
                  ok(1),
                  clear(2)
                  }
          ACCESS read-write
          STATUS mandatory
          DESCRIPTION
               ""
          ::= { teradsx1TotalTableEntry 15 }

teraStandarddsx1TotalLOF OBJECT-TYPE
          SYNTAX Gauge32
          ACCESS read-only
          STATUS mandatory
          DESCRIPTION
               ""
          ::= { teradsx1TotalTableEntry 16 }

teraStandarddsx1TotalYELLOW OBJECT-TYPE
          SYNTAX Gauge32
          ACCESS read-only
          STATUS mandatory
          DESCRIPTION
               ""
          ::= { teradsx1TotalTableEntry 17 }

teraStandarddsx1TotalAIS OBJECT-TYPE
          SYNTAX Gauge32
          ACCESS read-only
          STATUS mandatory
          DESCRIPTION
               ""
          ::= { teradsx1TotalTableEntry 18 }

teraStandarddsx1TotalLOSs OBJECT-TYPE
          SYNTAX Gauge32
          ACCESS read-only
          STATUS mandatory
          DESCRIPTION
               ""
          ::= { teradsx1TotalTableEntry 19 }

     -- teradsx1Standard7DayTotalTable

teradsx1Standard7DayTotalTable OBJECT-TYPE
     SYNTAX SEQUENCE OF Teradsx1Standard7DayTotalTableEntryType
     ACCESS not-accessible
     STATUS mandatory
     DESCRIPTION
          " table teradsx1Standard7DayTotalTable"
     ::= { teraDs1Group 4 }

teradsx1Standard7DayTotalTableEntry OBJECT-TYPE
          SYNTAX Teradsx1Standard7DayTotalTableEntryType
          ACCESS not-accessible
          STATUS mandatory
          DESCRIPTION
               " table entry teradsx1Standard7DayTotalTableEntry "
          INDEX {                   teradsx1Standard7DayTotalIndex,                  teradsx1Standard7DayTotalNumber }
     ::= { teradsx1Standard7DayTotalTable 1 }

Teradsx1Standard7DayTotalTableEntryType ::= SEQUENCE {
          teradsx1Standard7DayTotalIndex   
             INTEGER,
          teradsx1Standard7DayTotalNumber   
             INTEGER (1..7),
          teradsx1Standard7DayTotalESs   
             Gauge32,
          teradsx1Standard7DayTotalSESs   
             Gauge32,
          teradsx1Standard7DayTotalSEFSs   
             Gauge32,
          teradsx1Standard7DayTotalUAS   
             Gauge32,
          teradsx1Standard7DayTotalCSSs   
             Gauge32,
          teradsx1Standard7DayTotalPCVs   
             Gauge32,
          teradsx1Standard7DayTotalLESs   
             Gauge32,
          teradsx1Standard7DayTotalBESs   
             Gauge32,
          teradsx1Standard7DayTotalDMs   
             Gauge32,
          teradsx1Standard7DayTotalLCVs   
             Gauge32,
          teradsx1Standard7DayTotalValidData   
             INTEGER
}

teradsx1Standard7DayTotalIndex OBJECT-TYPE
          SYNTAX INTEGER
          ACCESS read-only
          STATUS mandatory
          DESCRIPTION
               ""
          ::= { teradsx1Standard7DayTotalTableEntry 1 }

teradsx1Standard7DayTotalNumber OBJECT-TYPE
          SYNTAX INTEGER (1..7)
          ACCESS read-only
          STATUS mandatory
          DESCRIPTION
               ""
          ::= { teradsx1Standard7DayTotalTableEntry 2 }

teradsx1Standard7DayTotalESs OBJECT-TYPE
          SYNTAX Gauge32
          ACCESS read-only
          STATUS mandatory
          DESCRIPTION
               ""
          ::= { teradsx1Standard7DayTotalTableEntry 3 }

teradsx1Standard7DayTotalSESs OBJECT-TYPE
          SYNTAX Gauge32
          ACCESS read-only
          STATUS mandatory
          DESCRIPTION
               ""
          ::= { teradsx1Standard7DayTotalTableEntry 4 }

teradsx1Standard7DayTotalSEFSs OBJECT-TYPE
          SYNTAX Gauge32
          ACCESS read-only
          STATUS mandatory
          DESCRIPTION
               ""
          ::= { teradsx1Standard7DayTotalTableEntry 5 }

teradsx1Standard7DayTotalUAS OBJECT-TYPE
          SYNTAX Gauge32
          ACCESS read-only
          STATUS mandatory
          DESCRIPTION
               ""
          ::= { teradsx1Standard7DayTotalTableEntry 6 }

teradsx1Standard7DayTotalCSSs OBJECT-TYPE
          SYNTAX Gauge32
          ACCESS read-only
          STATUS mandatory
          DESCRIPTION
               ""
          ::= { teradsx1Standard7DayTotalTableEntry 7 }

teradsx1Standard7DayTotalPCVs OBJECT-TYPE
          SYNTAX Gauge32
          ACCESS read-only
          STATUS mandatory
          DESCRIPTION
               ""
          ::= { teradsx1Standard7DayTotalTableEntry 8 }

teradsx1Standard7DayTotalLESs OBJECT-TYPE
          SYNTAX Gauge32
          ACCESS read-only
          STATUS mandatory
          DESCRIPTION
               ""
          ::= { teradsx1Standard7DayTotalTableEntry 9 }

teradsx1Standard7DayTotalBESs OBJECT-TYPE
          SYNTAX Gauge32
          ACCESS read-only
          STATUS mandatory
          DESCRIPTION
               ""
          ::= { teradsx1Standard7DayTotalTableEntry 10 }

teradsx1Standard7DayTotalDMs OBJECT-TYPE
          SYNTAX Gauge32
          ACCESS read-only
          STATUS mandatory
          DESCRIPTION
               ""
          ::= { teradsx1Standard7DayTotalTableEntry 11 }

teradsx1Standard7DayTotalLCVs OBJECT-TYPE
          SYNTAX Gauge32
          ACCESS read-only
          STATUS mandatory
          DESCRIPTION
               ""
          ::= { teradsx1Standard7DayTotalTableEntry 12 }

teradsx1Standard7DayTotalValidData OBJECT-TYPE
          SYNTAX INTEGER
                  {
                  true(1),
                  false(2)
                  }
          ACCESS read-only
          STATUS mandatory
          DESCRIPTION
               ""
          ::= { teradsx1Standard7DayTotalTableEntry 13 }

     -- teradsx1Tera7DayTotalTable

teradsx1Tera7DayTotalTable OBJECT-TYPE
     SYNTAX SEQUENCE OF Teradsx1Tera7DayTotalTableEntryType
     ACCESS not-accessible
     STATUS mandatory
     DESCRIPTION
          " table teradsx1Tera7DayTotalTable"
     ::= { teraDs1Group 5 }

teradsx1Tera7DayTotalTableEntry OBJECT-TYPE
          SYNTAX Teradsx1Tera7DayTotalTableEntryType
          ACCESS not-accessible
          STATUS mandatory
          DESCRIPTION
               " table entry teradsx1Tera7DayTotalTableEntry "
          INDEX {                   teradsx1Tera7DayTotalIndex,                  teradsx1Tera7DayTotalNumber }
     ::= { teradsx1Tera7DayTotalTable 1 }

Teradsx1Tera7DayTotalTableEntryType ::= SEQUENCE {
          teradsx1Tera7DayTotalIndex   
             INTEGER,
          teradsx1Tera7DayTotalNumber   
             INTEGER (1..7),
          teradsx1Tera7DayTotalESs   
             Gauge32,
          teradsx1Tera7DayTotalSESs   
             Gauge32,
          teradsx1Tera7DayTotalSEFSs   
             Gauge32,
          teradsx1Tera7DayTotalUAS   
             Gauge32,
          teradsx1Tera7DayTotalCSSs   
             Gauge32,
          teradsx1Tera7DayTotalPCVs   
             Gauge32,
          teradsx1Tera7DayTotalLESs   
             Gauge32,
          teradsx1Tera7DayTotalBESs   
             Gauge32,
          teradsx1Tera7DayTotalDMs   
             Gauge32,
          teradsx1Tera7DayTotalLCVs   
             Gauge32,
          teradsx1Tera7DayTotalLOF   
             Gauge32,
          teradsx1Tera7DayTotalYELLOW   
             Gauge32,
          teradsx1Tera7DayTotalAIS   
             Gauge32,
          teradsx1TeraStandard7DayTotalLOF   
             Gauge32,
          teradsx1TeraStandard7DayTotalYELLOW   
             Gauge32,
          teradsx1TeraStandard7DayTotalAIS   
             Gauge32,
          teradsx1Tera7DayTotalValidData   
             INTEGER,
          teraStandarddsx1Tera7DayTotalLOSs   
             Gauge32
}

teradsx1Tera7DayTotalIndex OBJECT-TYPE
          SYNTAX INTEGER
          ACCESS read-only
          STATUS mandatory
          DESCRIPTION
               ""
          ::= { teradsx1Tera7DayTotalTableEntry 1 }

teradsx1Tera7DayTotalNumber OBJECT-TYPE
          SYNTAX INTEGER (1..7)
          ACCESS read-only
          STATUS mandatory
          DESCRIPTION
               ""
          ::= { teradsx1Tera7DayTotalTableEntry 2 }

teradsx1Tera7DayTotalESs OBJECT-TYPE
          SYNTAX Gauge32
          ACCESS read-only
          STATUS mandatory
          DESCRIPTION
               ""
          ::= { teradsx1Tera7DayTotalTableEntry 3 }

teradsx1Tera7DayTotalSESs OBJECT-TYPE
          SYNTAX Gauge32
          ACCESS read-only
          STATUS mandatory
          DESCRIPTION
               ""
          ::= { teradsx1Tera7DayTotalTableEntry 4 }

teradsx1Tera7DayTotalSEFSs OBJECT-TYPE
          SYNTAX Gauge32
          ACCESS read-only
          STATUS mandatory
          DESCRIPTION
               ""
          ::= { teradsx1Tera7DayTotalTableEntry 5 }

teradsx1Tera7DayTotalUAS OBJECT-TYPE
          SYNTAX Gauge32
          ACCESS read-only
          STATUS mandatory
          DESCRIPTION
               ""
          ::= { teradsx1Tera7DayTotalTableEntry 6 }

teradsx1Tera7DayTotalCSSs OBJECT-TYPE
          SYNTAX Gauge32
          ACCESS read-only
          STATUS mandatory
          DESCRIPTION
               ""
          ::= { teradsx1Tera7DayTotalTableEntry 7 }

teradsx1Tera7DayTotalPCVs OBJECT-TYPE
          SYNTAX Gauge32
          ACCESS read-only
          STATUS mandatory
          DESCRIPTION
               ""
          ::= { teradsx1Tera7DayTotalTableEntry 8 }

teradsx1Tera7DayTotalLESs OBJECT-TYPE
          SYNTAX Gauge32
          ACCESS read-only
          STATUS mandatory
          DESCRIPTION
               ""
          ::= { teradsx1Tera7DayTotalTableEntry 9 }

teradsx1Tera7DayTotalBESs OBJECT-TYPE
          SYNTAX Gauge32
          ACCESS read-only
          STATUS mandatory
          DESCRIPTION
               ""
          ::= { teradsx1Tera7DayTotalTableEntry 10 }

teradsx1Tera7DayTotalDMs OBJECT-TYPE
          SYNTAX Gauge32
          ACCESS read-only
          STATUS mandatory
          DESCRIPTION
               ""
          ::= { teradsx1Tera7DayTotalTableEntry 11 }

teradsx1Tera7DayTotalLCVs OBJECT-TYPE
          SYNTAX Gauge32
          ACCESS read-only
          STATUS mandatory
          DESCRIPTION
               ""
          ::= { teradsx1Tera7DayTotalTableEntry 12 }

teradsx1Tera7DayTotalLOF OBJECT-TYPE
          SYNTAX Gauge32
          ACCESS read-only
          STATUS mandatory
          DESCRIPTION
               ""
          ::= { teradsx1Tera7DayTotalTableEntry 13 }

teradsx1Tera7DayTotalYELLOW OBJECT-TYPE
          SYNTAX Gauge32
          ACCESS read-only
          STATUS mandatory
          DESCRIPTION
               ""
          ::= { teradsx1Tera7DayTotalTableEntry 14 }

teradsx1Tera7DayTotalAIS OBJECT-TYPE
          SYNTAX Gauge32
          ACCESS read-only
          STATUS mandatory
          DESCRIPTION
               ""
          ::= { teradsx1Tera7DayTotalTableEntry 15 }

teradsx1TeraStandard7DayTotalLOF OBJECT-TYPE
          SYNTAX Gauge32
          ACCESS read-only
          STATUS mandatory
          DESCRIPTION
               ""
          ::= { teradsx1Tera7DayTotalTableEntry 16 }

teradsx1TeraStandard7DayTotalYELLOW OBJECT-TYPE
          SYNTAX Gauge32
          ACCESS read-only
          STATUS mandatory
          DESCRIPTION
               ""
          ::= { teradsx1Tera7DayTotalTableEntry 17 }

teradsx1TeraStandard7DayTotalAIS OBJECT-TYPE
          SYNTAX Gauge32
          ACCESS read-only
          STATUS mandatory
          DESCRIPTION
               ""
          ::= { teradsx1Tera7DayTotalTableEntry 18 }

teradsx1Tera7DayTotalValidData OBJECT-TYPE
          SYNTAX INTEGER
                  {
                  true(1),
                  false(2)
                  }
          ACCESS read-only
          STATUS mandatory
          DESCRIPTION
               ""
          ::= { teradsx1Tera7DayTotalTableEntry 19 }

teraStandarddsx1Tera7DayTotalLOSs OBJECT-TYPE
          SYNTAX Gauge32
          ACCESS read-only
          STATUS mandatory
          DESCRIPTION
               ""
          ::= { teradsx1Tera7DayTotalTableEntry 20 }

END
