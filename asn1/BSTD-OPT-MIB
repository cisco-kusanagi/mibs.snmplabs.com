-- Version 2.15.1.1, modified 2001-05-31 17:27:31-04
        BSTD-OPT-MIB DEFINITIONS ::= BEGIN

        IMPORTS
            Counter, enterprises
                FROM RFC1155-SMI
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }
  cdx6500PCTBSTDDeviceGroup OBJECT IDENTIFIER ::= { cdx6500CfgProtocolGroup 8 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

        -- Textual conventions

        DisplayString ::= OCTET STRING

        -- The BSTD group contains the configuration parameters,
        -- statistics, and control objects used by the BSTD
        -- ports and devices.

        -- BSTD Port Configuration Table

        cdx6500PPCTBSTDPortTable OBJECT-TYPE
            SYNTAX SEQUENCE OF Cdx6500PPCTBSTDPortEntry
            ACCESS not-accessible
            STATUS mandatory
            DESCRIPTION
                "A table of BSTD Port configuration parameters."
        ::= { cdx6500PCTPortProtocolGroup 14 }

        cdx6500PPCTBSTDPortEntry OBJECT-TYPE
            SYNTAX Cdx6500PPCTBSTDPortEntry
            ACCESS not-accessible
            STATUS mandatory
            DESCRIPTION
                "A BSTD Configuration Table entry. Each entry
                 contains the configuration parameters for a single
                 BSTD port. "
            INDEX { cdx6500BSTDCfgPortNumber }
        ::= { cdx6500PPCTBSTDPortTable 1 }

        Cdx6500PPCTBSTDPortEntry ::=
            SEQUENCE {
                cdx6500BSTDCfgPortNumber 
                    INTEGER,    
                cdx6500BSTDCfgPADType 
                    INTEGER,    
                cdx6500BSTDCfgLineInterface
                    INTEGER,    
                cdx6500BSTDCfgClockSource 
                    INTEGER,    
                cdx6500BSTDCfgClockSpeed 
                    INTEGER,    
                cdx6500BSTDCfgSyncContention 
                    INTEGER,    
                cdx6500BSTDCfgAsyncConnType 
                    INTEGER,    
                cdx6500BSTDCfgNumDevices 
                    INTEGER,    
                cdx6500BSTDCfgServTimer 
                    INTEGER,    
                cdx6500BSTDCfgErrThreshCount 
                    INTEGER,    
                cdx6500BSTDCfgResponseTimeout 
                    INTEGER,    
                cdx6500BSTDCfgPadProtTimeout 
                    INTEGER,    
                cdx6500BSTDCfgTranNumbers 
                    INTEGER,    
                cdx6500BSTDCfgContentionMode 
                    INTEGER,    
                cdx6500BSTDCfgPortSubAddr 
                    DisplayString,
                cdx6500BSTDCfgPortOptions 
                    INTEGER,
                cdx6500BSTDCfgRestrictConnDest
                    DisplayString,
                cdx6500BSTDCfgBillRec 
                    INTEGER,    
                cdx6500BSTDPortOptString 
                    DisplayString,
                cdx6500BSTDCfgElectricalInterfaceType 
                    INTEGER,
                cdx6500BSTDCfgV24ElectricalInterfaceOption 
                    INTEGER,
                cdx6500BSTDCfgHighSpeedElectricalInterfaceOption 
                    INTEGER
                }

        cdx6500BSTDCfgPortNumber OBJECT-TYPE
            SYNTAX INTEGER (1..54)
            ACCESS read-only
            STATUS mandatory
            DESCRIPTION
                "The BSTD port number described by this entry."
        ::= { cdx6500PPCTBSTDPortEntry 1 }

        cdx6500BSTDCfgPADType OBJECT-TYPE
            SYNTAX INTEGER {
                    tpad       (0),
                    hpad       (1),
                    newvalTpad (50)
                    }
            ACCESS read-only
            STATUS mandatory
            DESCRIPTION
                "Indicates whether the port is functioning as a
                 Terminal PAD (tpad) or a Host PAD (hpad).
                 newvalTpad - same functionality as 'tpad', new enumeration
                 introduced for RFC1155 compatibility."
        ::= { cdx6500PPCTBSTDPortEntry 2 }

        cdx6500BSTDCfgLineInterface OBJECT-TYPE
            SYNTAX INTEGER {
                    sync       (0),
                    async      (1),
                    newvalSync (50)
                    }
            ACCESS read-only
            STATUS mandatory
            DESCRIPTION
                "Selects the line interface to use.
                 sync  - synchronous operation.
                 async - asynchronous operation.
                 newvalSync - same functionality as 'sync', new enumeration
                 introduced for RFC1155 compatibility."
        ::= { cdx6500PPCTBSTDPortEntry 3 }

        cdx6500BSTDCfgClockSource OBJECT-TYPE
            SYNTAX INTEGER {
                    int       (0),
                    ext       (1),
                    newvalInt (50)
                    }
            ACCESS read-only
            STATUS mandatory
            DESCRIPTION
                "int - internal clock source
                 ext - external clock source.
                 newvalInt - same functionality as 'int', new enumeration
                 introduced for RFC1155 compatibility." 
        ::= { cdx6500PPCTBSTDPortEntry 4 }


        cdx6500BSTDCfgClockSpeed OBJECT-TYPE
            SYNTAX INTEGER (1200..192000)
            ACCESS read-only
            STATUS mandatory
            DESCRIPTION
                "This is the speed of the port in bits per second,
                 when using internal clocking." 
        ::= { cdx6500PPCTBSTDPortEntry 5 }

        cdx6500BSTDCfgSyncContention OBJECT-TYPE
            SYNTAX INTEGER {
                    hdx       (0),
                    fdx       (1),
                    newvalHdx (50)
                    }
            ACCESS read-only
            STATUS mandatory
            DESCRIPTION
                "Indicates whether Half Duplex (hdx) or
                 Full Duplex (fdx) modem signals are being generated. 
                 Full Duplex indicates communication is occuring
                 in both directions simultaneously between devices.
                 Half Duplex indicates transmission is occuring
                 in both directions, but only in one direction
                 at a time.
                 newvalHdx - same functionality as 'hdx', new enumeration
                 introduced for RFC1155 compatibility." 
        ::= { cdx6500PPCTBSTDPortEntry 6 }

        cdx6500BSTDCfgAsyncConnType OBJECT-TYPE
            SYNTAX INTEGER {
                    simp       (0),
                    simpa      (15),
                    newvalSimp (50)
                    }
            ACCESS read-only
            STATUS mandatory
            DESCRIPTION
                "Specify the control signal handshake required for a
                 connection to be made to this port:
                 simp  - simple, no control signals required
                 simpa - CTS follows RTS, but no control signals required
                 Note: applicable for asynchronous operation only.
                 newvalSimp - same functionality as 'simp', new enumeration
                 introduced for RFC1155 compatibility."
        ::= { cdx6500PPCTBSTDPortEntry 7 }

        cdx6500BSTDCfgNumDevices OBJECT-TYPE
            SYNTAX INTEGER (1..32)
            ACCESS read-only
            STATUS mandatory
            DESCRIPTION
                "Specifies the number of physical devices on this line." 
        ::= { cdx6500PPCTBSTDPortEntry 8 }

        cdx6500BSTDCfgServTimer OBJECT-TYPE
            SYNTAX INTEGER (10..60)
            ACCESS read-only
            STATUS mandatory
            DESCRIPTION
                "The Service Timer specifies the interval of time in
                 seconds between periodic servicing. Such servicing
                 includes intervals between the time the PAD will
                 attempt to poll devices that previously failed to
                 respond and intervals between failures in attempts
                 to establish a connection from a device configured
                 for Autocall." 
        ::= { cdx6500PPCTBSTDPortEntry 9 }

        cdx6500BSTDCfgErrThreshCount OBJECT-TYPE
            SYNTAX INTEGER (1..255)
            ACCESS read-only
            STATUS mandatory
            DESCRIPTION
                "Indicates number of consecutive errors that can occur
                 before a device is considered down."
        ::= { cdx6500PPCTBSTDPortEntry 10 }

        cdx6500BSTDCfgResponseTimeout OBJECT-TYPE
            SYNTAX INTEGER (400..5000)
            ACCESS read-only
            STATUS mandatory
            DESCRIPTION
                "Specifies the amount of time in msec the PAD allows
                 a terminal, printer or host to respond. As a result,
                 the TPAD may re-transmit the previous message or abort
                 the current procedure.
                 The HPAD aborts the current procedure as though EOT
                 was received, allowing this HPAD station to disconnect
                 it's X.25 circuit if the host malfunctions. An HPAD with
                 a response timeout shorter than the hosts ability to respond
                 may result in  Inbound Errors."
        ::= { cdx6500PPCTBSTDPortEntry 11 }

        cdx6500BSTDCfgPadProtTimeout OBJECT-TYPE
            SYNTAX INTEGER (1..60)
            ACCESS read-only
            STATUS mandatory
            DESCRIPTION
                "Specifies the maximum amount of time in seconds the PAD 
                 will wait for the end of a multi-packet message from the 
                 network. If this time limit
                 is exceeded, the PAD will initiate the clearing of the 
                 circuit."
        ::= { cdx6500PPCTBSTDPortEntry 12 }

        cdx6500BSTDCfgTranNumbers OBJECT-TYPE
            SYNTAX INTEGER {
                    disable       (0),
                    modulo2       (1),
                    newvalDisable (50)
                    }
            ACCESS read-only
            STATUS mandatory
            DESCRIPTION
                "This parameter is used to select the BSTD Transmission 
                 Numbering's mode of operation.
                 disable  - Disable Transmission Numbering
                 modulo2  - Alternating '0' and '1' scheme.
                 newvalDisable - same functionality as 'disable', new 
                 enumeration introduced for RFC1155 compatibility."
        ::= { cdx6500PPCTBSTDPortEntry 13 }

        cdx6500BSTDCfgContentionMode OBJECT-TYPE
            SYNTAX INTEGER {
                    disable       (0),
                    enable        (1),
                    newvalDisable (50)
                    }  
            ACCESS read-only
            STATUS mandatory
            DESCRIPTION
                "For a TPAD port only : This parameter enables or
                 disables a TPAD port to use BSTD Contention Mode.
                 Note that an HPAD must have this option set to Enable.
                 disable - Disable Contention Mode
                 enable  - Enable Contention Mode.
                 newvalDisable - same functionality as 'disable', new
                 enumeration introduced for RFC1155 compatibility."
        ::= { cdx6500PPCTBSTDPortEntry 14 }

        cdx6500BSTDCfgPortSubAddr OBJECT-TYPE
            SYNTAX DisplayString (SIZE(0..3))
            ACCESS read-only
            STATUS mandatory
            DESCRIPTION  
                "0 - 3 Decimal digits
                 Calls addressed to this node and with this subaddress
                 will be routed to this port."
        ::= { cdx6500PPCTBSTDPortEntry 15 }

        cdx6500BSTDCfgPortOptions OBJECT-TYPE
            SYNTAX INTEGER {
                    deprecatedObj (1)
                    } 
            ACCESS read-only
            STATUS deprecated
            DESCRIPTION
                "This object has been deprecated,
                 It is replaced by cdx6500BSTDPortOptString."
        ::= { cdx6500PPCTBSTDPortEntry 16 }

        cdx6500BSTDCfgRestrictConnDest OBJECT-TYPE
            SYNTAX DisplayString (SIZE(0..3))
            ACCESS read-only
            STATUS mandatory
            DESCRIPTION
                "0 - 3 Decimal digits or a single blank
                 All calls originating from this port will be routed to
                 the destination specified in this parameter, irrespective
                 of route selection table entries.  For example, to route
                 calls to port 1, use P1. To route calls to port 2,
                 station 4, use P2S4." 
        ::= { cdx6500PPCTBSTDPortEntry 17 }

        cdx6500BSTDCfgBillRec OBJECT-TYPE
            SYNTAX INTEGER {
                    off       (0),
                    on        (1),
                    newvalOff (50)
                    }
            ACCESS read-only
            STATUS mandatory
            DESCRIPTION
                "This controls whether billing (accounting) records will
                 be created for calls on this Device.
                 newvalOff - same functionality as 'off', new
                 enumeration introduced for RFC1155 compatibility."
        ::= { cdx6500PPCTBSTDPortEntry 18 }

            cdx6500BSTDPortOptString OBJECT-TYPE
            SYNTAX DisplayString (SIZE(3..16))
            ACCESS read-only
            STATUS mandatory
            DESCRIPTION
                "This is the new object for cdx6500BSTDPortOption.
                 Select options on this BSTD port as follows:
                 NONE - no option specified
                 ORG  - Controllers on this port will originate the calls
                 ACK  - DSP End-to-End Acknowledgements are to be used
                 Any combination of above specified by summing (e.g. ORG+ACK)."
        ::= { cdx6500PPCTBSTDPortEntry 19 }

            cdx6500BSTDCfgElectricalInterfaceType OBJECT-TYPE
            SYNTAX INTEGER {
                    v24       (1),
                    v35       (2),
                    v36       (3),
                    x21       (4),
                    none      (5)
                    }
            ACCESS read-only
            STATUS mandatory
            DESCRIPTION
                 "Specify the Electrical Interface Type:
                   V.24  - V.24 Electrical Interface Type
                   V.35  - V.35 Electrical Interface Type
                   V.36  - V.36 Electrical Interface Type
                   X.21  - X.21 Electrical Interface Type
                   NONE  - Electrically disabled"
        ::= { cdx6500PPCTBSTDPortEntry 20 }

            cdx6500BSTDCfgV24ElectricalInterfaceOption OBJECT-TYPE
            SYNTAX INTEGER {
                    ri        (1),
                    tm        (2)
                    }
            ACCESS read-only
            STATUS mandatory
            DESCRIPTION
                 "Specify the Pin 22 option:
                  RI    - V.24 uses Pin 22 for Ring Indicator output signal
                  TM    - V.24 uses Pin 22 for Test Mode input signal"
        ::= { cdx6500PPCTBSTDPortEntry 21 }

            cdx6500BSTDCfgHighSpeedElectricalInterfaceOption OBJECT-TYPE
            SYNTAX INTEGER {
                    none      (1),
                    xover     (2)
                    }
            ACCESS read-only
            STATUS mandatory
            DESCRIPTION
                 "Specify the cable type:
                  NONE  - V.35/V.36/X.21 DCE with straight through cable
                  XOVER - V.35/V.36/X.21 DCE with crossover adapter cable"
        ::= { cdx6500PPCTBSTDPortEntry 22 }


        -- BSTD Device Configuration Table

        cdx6500PBCTBSTDDeviceTable OBJECT-TYPE
            SYNTAX SEQUENCE OF Cdx6500PBCTBSTDDeviceEntry
            ACCESS not-accessible
            STATUS mandatory
            DESCRIPTION
                "A table of BSTD device configuration parameters."
        ::= { cdx6500PCTBSTDDeviceGroup 1 }

        cdx6500PBCTBSTDDeviceEntry OBJECT-TYPE
            SYNTAX Cdx6500PBCTBSTDDeviceEntry
            ACCESS not-accessible
            STATUS mandatory
            DESCRIPTION
                "A BSTD Configuration Table entry. Each entry
                 contains the configuration parameters for a single
                 BSTD device."
            INDEX { cdx6500BSTDDevPortNumber, cdx6500BSTDDevEntry }
        ::= { cdx6500PBCTBSTDDeviceTable 1 }

        Cdx6500PBCTBSTDDeviceEntry ::=
            SEQUENCE {
                cdx6500BSTDDevPortNumber
                    INTEGER,    
                cdx6500BSTDDevEntry
                    INTEGER,
                cdx6500BSTDStationAddr1 
                    DisplayString, 
                cdx6500BSTDStationAddr2 
                    DisplayString,
                cdx6500BSTDDestStationAddr1 
                    DisplayString, 
                cdx6500BSTDDesstStationAddr2 
                    DisplayString, 
                cdx6500BSTDGroupAddr1 
                    DisplayString, 
                cdx6500BSTDGroupAddr2 
                    DisplayString, 
                cdx6500BSTDCallMnemonic 
                    DisplayString, 
                cdx6500BSTDStationEnabled 
                    INTEGER
                }

        cdx6500BSTDDevPortNumber OBJECT-TYPE
            SYNTAX INTEGER (1..54)
            ACCESS read-only
            STATUS mandatory
            DESCRIPTION
                "The BSTD port accessing this device"
        ::= { cdx6500PBCTBSTDDeviceEntry 1 }


        cdx6500BSTDDevEntry OBJECT-TYPE
            SYNTAX INTEGER (1..32)
            ACCESS read-only
            STATUS mandatory
            DESCRIPTION
                "The unique number for this specific port." 
        ::= { cdx6500PBCTBSTDDeviceEntry 2 }

        cdx6500BSTDStationAddr1 OBJECT-TYPE
            SYNTAX DisplayString (SIZE(2))
            ACCESS read-only
            STATUS mandatory
            DESCRIPTION
                 "This is the first byte of this Station's address.
                  The Station address consists of two hexadecimal digits.
                  The valid range for a digit is 20-7F."
        ::= { cdx6500PBCTBSTDDeviceEntry 3 }

        cdx6500BSTDStationAddr2 OBJECT-TYPE
            SYNTAX DisplayString (SIZE(2))
            ACCESS read-only
            STATUS mandatory
            DESCRIPTION
                 "This is the second byte of this Station's address.
                  The Station address consists of two hexadecimal digits.
                  The valid range for a digit is 20-7F."
        ::= { cdx6500PBCTBSTDDeviceEntry 4 }

        cdx6500BSTDDestStationAddr1 OBJECT-TYPE
            SYNTAX DisplayString (SIZE(2))
            ACCESS read-only
            STATUS mandatory
            DESCRIPTION
                "This is the first byte for the Station on the remote PAD.
                 The Destination Station address consists of two hexadecimal
                 digits. The valid range for a digit is 20-7F."
        ::= { cdx6500PBCTBSTDDeviceEntry 5 }

        cdx6500BSTDDesstStationAddr2 OBJECT-TYPE
            SYNTAX DisplayString (SIZE(2))
            ACCESS read-only
            STATUS mandatory
            DESCRIPTION
                "This is the first byte for the Station on the remote PAD.
                 The Destination Station address consists of two hexadecimal 
                 digits. The valid range for a digit is 20-7F."
        ::= { cdx6500PBCTBSTDDeviceEntry 6 }

        cdx6500BSTDGroupAddr1 OBJECT-TYPE
            SYNTAX DisplayString (SIZE(2))
            ACCESS read-only
            STATUS mandatory
            DESCRIPTION
                "This is the first byte of this Station's Group address.
                 The Group address consists of two hexadecimal digits.
                 The valid range for a digit is 20-7F."
        ::= { cdx6500PBCTBSTDDeviceEntry 7 }

        cdx6500BSTDGroupAddr2 OBJECT-TYPE
            SYNTAX DisplayString (SIZE(2))
            ACCESS read-only
            STATUS mandatory
            DESCRIPTION
                "This is the second byte of this Station's Group address.
                 The Group address consists of two hexadecimal digits.
                 The valid range for a digit is 20-7F."
        ::= { cdx6500PBCTBSTDDeviceEntry 8 }

        cdx6500BSTDCallMnemonic OBJECT-TYPE
            SYNTAX DisplayString (SIZE(0..8))
            ACCESS read-only
            STATUS mandatory
            DESCRIPTION
                "This mnemonic name is used for originating calls from this
                 Station."
        ::= { cdx6500PBCTBSTDDeviceEntry 9 }

        cdx6500BSTDStationEnabled OBJECT-TYPE
            SYNTAX INTEGER {
                    no       (0),
                    yes      (1),
                    newvalNo (50)
                    }
            ACCESS read-only
            STATUS mandatory
            DESCRIPTION
                "This parameter is used to enable or disable the operation 
                 of this Station.
                 no  - Disable Station. 
                 yes - Enable Station.
                 newvalNo - same functionality as 'no', new
                 enumeration introduced for RFC1155 compatibility."
        ::= { cdx6500PBCTBSTDDeviceEntry 10 }

        -- BSTD Port Statistics

        cdx6500PPSTBSTDPortStatTable  OBJECT-TYPE
            SYNTAX SEQUENCE OF Cdx6500BSTDPortStatEntry
            ACCESS not-accessible
            STATUS mandatory
            DESCRIPTION
                "A table of BSTD port statistics."
        ::= { cdx6500PSTPortProtocolGroup 14 }

        cdx6500BSTDPortStatEntry OBJECT-TYPE
            SYNTAX Cdx6500BSTDPortStatEntry
            ACCESS not-accessible
            STATUS mandatory
            DESCRIPTION
                "A BSTD Port Statistic Table entry. Each entry
                 contains the statistics for a single BSTD port."
            INDEX { cdx6500BSTDStatPortNumber }
        ::= { cdx6500PPSTBSTDPortStatTable 1 }

        Cdx6500BSTDPortStatEntry ::=
            SEQUENCE {
                cdx6500BSTDStatPortNumber
                    INTEGER,
                cdx6500BSTDPortStatus
                    INTEGER,
                cdx6500BSTDPortState
                    DisplayString,
                cdx6500BSTDPortSpeed
                    INTEGER,
                cdx6500BSTDPortUtilIn
                    INTEGER,
                cdx6500BSTDPortUtilOut
                    INTEGER,
                cdx6500BSTDInMsgs
                    Counter,
                cdx6500BSTDOutMsgs
                    Counter,
                cdx6500BSTDInChars
                    Counter,
                cdx6500BSTDOutChars
                    Counter,
                cdx6500BSTDCharRateIn
                    INTEGER,
                cdx6500BSTDCharRateOut
                    INTEGER,
                cdx6500BSTDCrcBccErrs
                    Counter
                }

        cdx6500BSTDStatPortNumber OBJECT-TYPE
            SYNTAX INTEGER (1..54)
            ACCESS read-only
            STATUS mandatory
            DESCRIPTION
                "The BSTD port number described by this entry." 
        ::= { cdx6500BSTDPortStatEntry 1 }

        cdx6500BSTDPortStatus OBJECT-TYPE
            SYNTAX INTEGER {
                    disabled       (0),
                    enabled        (1),
                    busyOut        (2),
                    up             (3),
                    down           (4),
                    newvalDisabled (50)
                    }
            ACCESS read-only
            STATUS mandatory
            DESCRIPTION
                "Port Status indicates whether or not the port
                 is switched on and is ready for operation. This value
                 may be one of :
                 up       - Port is up and running.
                 down     - port is down.
                 disabled - port has been disabled.
                 enabled  - port has been enabled, but is not yet Up
                 busyOut  - port has been set to be disabled as soon as
                            last active session is disestablished. No
                            new sessions will be established.
                 newvalDisabled - same functionality as 'disabled', new
                 enumeration introduced for RFC1155 compatibility."
        ::= { cdx6500BSTDPortStatEntry 2 }

        cdx6500BSTDPortState OBJECT-TYPE
            SYNTAX DisplayString (SIZE(4..10))
            ACCESS read-only
            STATUS mandatory
            DESCRIPTION
                "Port State indicates what the port is actually in the
                 process of doing. This value may be one of :
                 INACTIVE      - H/TPAD port inactive entered during boot
                 WTPOLSERVE    - TPAD is waiting for response to a poll
                 WTSELRESP     - TPAD is waiting for the response to a
                                 select
                 WTDATARESP    - H/TPAD is waiting for data to be
                                 acknowledged
                 DATA          - H/TPAD is in the process of sending/receiving
                                 data
                 SEL/POL       - TPAD is about to select or poll a
                                 controller. This is the most common state
                                 for a TPAD
                 SELECT        - TPAD is about to select a device
                 POLL          - TPAD is about to poll a device
                 WTENQRESP     - H/TPAD is waiting for a NAK response to
                                 an ENQ sent
                 IDLE          - HPAD is waiting for the host to send commands.
                                 This is the most common state of the HPAD
                 WTEOT         - HPAD is waiting for an expected EOT from the
                                 host
                 FLUSHINGDATA  - HPAD encountered an error in the message
                                 received from the host. As a result, 
                                 the data is being flushed
                 WTLCM         - HPAD received a read/modify and is waiting for
                                 the response from the TPAD."
        ::= { cdx6500BSTDPortStatEntry 3 }

        cdx6500BSTDPortSpeed OBJECT-TYPE
            SYNTAX INTEGER
            ACCESS read-only
            STATUS mandatory
            DESCRIPTION
                "This is the speed of the port if clock is internal. If
                 clock is external, this is the detected clock speed. If
                 Port Speed is 0, clock is external, but clocking is not
                 being received from attatched device."
        ::= { cdx6500BSTDPortStatEntry 4 }

        cdx6500BSTDPortUtilIn OBJECT-TYPE
            SYNTAX INTEGER (0..100)
            ACCESS read-only
            STATUS mandatory
            DESCRIPTION
                "Percentage of Port input bandwidth in use."
        ::= { cdx6500BSTDPortStatEntry 5 }

        cdx6500BSTDPortUtilOut OBJECT-TYPE
            SYNTAX INTEGER (0..100)
            ACCESS read-only
            STATUS mandatory
            DESCRIPTION
                "Percentage of Port output bandwidth in use."
        ::= { cdx6500BSTDPortStatEntry 6 }

        cdx6500BSTDInMsgs OBJECT-TYPE
            SYNTAX Counter
            ACCESS read-only
            STATUS mandatory
            DESCRIPTION
                "Number of message received since last node, port, or
                 statistics reset."
        ::= { cdx6500BSTDPortStatEntry 7 }

        cdx6500BSTDOutMsgs OBJECT-TYPE
            SYNTAX Counter
            ACCESS read-only
            STATUS mandatory
            DESCRIPTION
                "Number of message sent since last node, port, or
                 statistics reset."
        ::= { cdx6500BSTDPortStatEntry 8 }

        cdx6500BSTDInChars OBJECT-TYPE
            SYNTAX Counter
            ACCESS read-only
            STATUS mandatory
            DESCRIPTION
                "Number of characters received since last node, port, or
                 statistics reset."
        ::= { cdx6500BSTDPortStatEntry 9 }

        cdx6500BSTDOutChars OBJECT-TYPE
            SYNTAX Counter
            ACCESS read-only
            STATUS mandatory
            DESCRIPTION
                "Number of characters sent since last node, port, or
                 statistics reset."
        ::= { cdx6500BSTDPortStatEntry 10 }

        cdx6500BSTDCharRateIn OBJECT-TYPE
            SYNTAX INTEGER (0..65535)
            ACCESS read-only
            STATUS mandatory
            DESCRIPTION
                "Number of characters received per second."
        ::= { cdx6500BSTDPortStatEntry 11 }

        cdx6500BSTDCharRateOut OBJECT-TYPE
            SYNTAX INTEGER (0..65535)
            ACCESS read-only
            STATUS mandatory
            DESCRIPTION
                "Number of characters sent per second."
        ::= { cdx6500BSTDPortStatEntry 12 }

        cdx6500BSTDCrcBccErrs OBJECT-TYPE
            SYNTAX Counter
            ACCESS read-only
            STATUS mandatory
            DESCRIPTION
                "Number of CRC errors since last node, port, or
                 statistics reset."
        ::= { cdx6500BSTDPortStatEntry 13 }

        END
