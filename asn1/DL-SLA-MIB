DL-SLA-MIB

DEFINITIONS ::= BEGIN
-- V1.3 01/05/2000 Jerry Sugiarto
 -- Added 6 objects to deliveryRatioPerDLCITable for Discard Eligible,
 --   FECN and BECN counters
-- V1.2 11/10/99  Jerry Sugiarto
 -- Added 12 objects to deliveryRatioPerDLCITable to separate statistics
 --   based on Transmits and Receives data
 -- Obsoleted objects 'deliveryTableTimestamp', 'fdrNumberOfSamplesTaken',
 --   'fDRNumberOfThresholdViolations', 'dDRNumberOfSamplesTaken',
 --   and 'dDRNumberOfThresholdViolations' in deliveryRatioPerDLCITable
-- V1.1 06/23/99  Jerry Sugiarto
 -- Changed the range in thresholdForDelayMeasurementPerDLCI
-- V1.0 04/21/99  Jerry Sugiarto
 -- First version.

IMPORTS
 enterprises, IpAddress, Counter FROM RFC1155-SMI
 OBJECT-TYPE FROM RFC-1212
 TRAP-TYPE FROM RFC-1215;

digital-link OBJECT IDENTIFIER ::= { enterprises 300 }
dl-ServiceLevelAgreement OBJECT IDENTIFIER ::= { digital-link 260 }

dlcSLAConfigurationGroup OBJECT IDENTIFIER
  ::= { dl-ServiceLevelAgreement 1 }


--
-- Service Level Agreement Configuration Group
--
--

unitSLAConfiguration OBJECT IDENTIFIER
  ::= { dlcSLAConfigurationGroup 1 }

configSLA OBJECT-TYPE
  SYNTAX  INTEGER {
	enabled	(1),
	disabled (2)
  }
  ACCESS read-write
  STATUS mandatory
  DESCRIPTION
   "This object represents whether SLA is enabled or disabled on this unit."
  ::= { unitSLAConfiguration 1 }

unitSamplingPeriodForFDR-DDR OBJECT-TYPE
  SYNTAX  INTEGER (1..255)
  ACCESS  read-write
  STATUS  mandatory
  DESCRIPTION
   "This object is to configure the sampling period in minutes for Frame
    Delivery Ratio and Data Delivery Ratio. The default is 1 minute."
  ::= { unitSLAConfiguration 2 }

unitSamplingPeriodForDelayMeasurement OBJECT-TYPE
  SYNTAX  INTEGER (1..255)
  ACCESS  read-write
  STATUS  mandatory
  DESCRIPTION
   "This object is to configure the sampling period in minutes for Delay
    Measurements. The default is 1 minute."
  ::= { unitSLAConfiguration 3 }

unitThresholdForFDR OBJECT-TYPE
  SYNTAX  INTEGER (0..99999)
  ACCESS  read-write
  STATUS  mandatory
  DESCRIPTION
   "This object is to configure the threshold in one thousandth of a
    percentage for Frame Delivery Ratio. A value of 0 disables the trap
    altogether."
  ::= { unitSLAConfiguration 4 }

unitThresholdForDDR OBJECT-TYPE
  SYNTAX  INTEGER (0..99999)
  ACCESS  read-write
  STATUS  mandatory
  DESCRIPTION
   "This object is to configure the threshold in one thousandth of a
    percentage for Data Delivery Ratio. A value of 0 disables the trap
    altogether."
  ::= { unitSLAConfiguration 5 }

unitDelayMeasurementPacketSize OBJECT-TYPE
  SYNTAX  INTEGER (50..1500)
  ACCESS  read-write
  STATUS  mandatory
  DESCRIPTION
   "This object is to configure the size in bytes of Delay Measurement
    Packets, one size of all DLCIs."
  ::= { unitSLAConfiguration 6 }

unitOamDomainIdentifier OBJECT-TYPE
  SYNTAX  Counter 
  ACCESS  read-write
  STATUS  mandatory
  DESCRIPTION
   "This object is the Domain Identifier for OA&M protocol.
    All end points participating in this SLA measurement must have the SAME
    OA&M Domain Identifier. The default is 0."
  ::= { unitSLAConfiguration 7 }

unitOamLocationIdentifier OBJECT-TYPE
  SYNTAX  Counter 
  ACCESS  read-write
  STATUS  mandatory
  DESCRIPTION
   "This object is the Location Identifier for OA&M protocol.
    All end points participating in this SLA measurement must have a unique
    OA&M Location Identifier."
  ::= { unitSLAConfiguration 8 }

--
-- Per DLCI Configuration
--

perDLCIConfiguration OBJECT IDENTIFIER
  ::= { dlcSLAConfigurationGroup 2 }

configurationPerDLCITable OBJECT-TYPE
  SYNTAX SEQUENCE OF ConfigurationPerDLCIEntry
  ACCESS not-accessible
  STATUS mandatory
  DESCRIPTION
   "Configuration Table Per DLCI"
  --DEFAULT get-function-async get_async_configurationPerDLCI
  --DEFAULT set-function-async AsyncSetProc
  --DEFAULT test-function-async test_async_configurationPerDLCI
  --DEFAULT next-function-async next_async_configurationPerDLCI
  ::= { perDLCIConfiguration 1 }

configurationPerDLCIEntry OBJECT-TYPE
  SYNTAX ConfigurationPerDLCIEntry
  ACCESS not-accessible
  STATUS mandatory
  DESCRIPTION
   "An entry in the Configuration per DLCI table."
  INDEX { configurationPerDLCITableIndex}
  ::= { configurationPerDLCITable 1 }

ConfigurationPerDLCIEntry ::=
SEQUENCE  {
	configurationPerDLCITableIndex  INTEGER,
	commitedInformationRatePerDLCI  INTEGER,
	remoteDLCIPerDLCI		INTEGER,
	remoteIpAddressPerDLCI		IpAddress,
	thresholdForDelayMeasurementsPerDLCI   INTEGER
}

configurationPerDLCITableIndex OBJECT-TYPE
   SYNTAX INTEGER
   ACCESS read-only
   STATUS mandatory
   DESCRIPTION
    "The index of Configuration Per DLCI table, which is DLCI number."
   ::= { configurationPerDLCIEntry 1 }

commitedInformationRatePerDLCI OBJECT-TYPE
   SYNTAX INTEGER (0..1536000)
   ACCESS read-only
   STATUS mandatory
   DESCRIPTION
    "This is the DLCI's Committed Information Rate (CIR).
     The CIR can be discovered automatically if LMI Rev 1.0 is used.
     If Annex A or Annex D is used, then the CIR must be entered manually
     in the DLCI table. The DLCI table is in the enterprise MIB."
   ::= { configurationPerDLCIEntry 2 }

remoteDLCIPerDLCI OBJECT-TYPE
  SYNTAX INTEGER
  ACCESS read-only
  STATUS mandatory
  DESCRIPTION
   "DLCI of the far end unit on each DLCI, which is discovered using
    Frame Relay OA&M Protocol. It will be stored in volatile memory."
  ::= { configurationPerDLCIEntry 3 }

remoteIpAddressPerDLCI OBJECT-TYPE
  SYNTAX IpAddress
  ACCESS read-only
  STATUS mandatory
  DESCRIPTION
   "IP Address of the NET port of the far end unit on each DLCI, which
    is discovered using Frame Relay OA&M Protocol. It will be stored in
    volatile memory."
  ::= { configurationPerDLCIEntry 4 }

thresholdForDelayMeasurementsPerDLCI OBJECT-TYPE
   SYNTAX INTEGER (0..64000)
   ACCESS read-write
   STATUS mandatory
   DESCRIPTION
    "This object represents this DLCI's delay threshold in milliseconds.
     The default is 64000. A value of 0 disables the trap altogether."
   ::= { configurationPerDLCIEntry 5 }


--
-- Service Level Agreement Statistics Group
--
--

dlcSLAStatisticsGroup OBJECT IDENTIFIER
  ::= { dl-ServiceLevelAgreement 2 }

--
-- Frame Delivery Ratio Statistics Group
--

dlcDeliveryRatioStatistics OBJECT IDENTIFIER
  ::= { dlcSLAStatisticsGroup 1 }

deliveryRatioPerDLCITable OBJECT-TYPE
  SYNTAX SEQUENCE OF DeliveryRatioPerDLCIEntry
  ACCESS not-accessible
  STATUS mandatory
  DESCRIPTION
   "Lifetime Delivery counter Table Per DLCI, contains both Frame Delivery
    Ratio and Data Delivery Ratio."
  ::= { dlcDeliveryRatioStatistics 1 }

deliveryRatioPerDLCIEntry OBJECT-TYPE
  SYNTAX DeliveryRatioPerDLCIEntry
  ACCESS not-accessible
  STATUS mandatory
  DESCRIPTION
   "An entry in the Delivery Ratio table."
  INDEX { deliveryRatioPerDLCITableIndex}
  ::= { deliveryRatioPerDLCITable 1 }

DeliveryRatioPerDLCIEntry ::=
SEQUENCE  {
	deliveryRatioPerDLCITableIndex   INTEGER,
	deliveryTableEncodedValue        OCTET STRING,
	deliveryTableTimestamp           Counter,
	fTCLperDLCI                      Counter,
	fTELperDLCI                      Counter,
	fRCLperDLCI                      Counter,
	fRELperDLCI                      Counter,
	fTCRperDLCI                      Counter,
	fTERperDLCI                      Counter,
	fRCRperDLCI                      Counter,
	fRERperDLCI                      Counter,
	fDRNumberOfSamplesTaken          Counter,
	fDRNumberOfThresholdViolations   Counter,
	dTCLperDLCI                      Counter,
	dTELperDLCI                      Counter,
	dRCLperDLCI                      Counter,
	dRELperDLCI                      Counter,
	dTCRperDLCI                      Counter,
	dTERperDLCI                      Counter,
	dRCRperDLCI                      Counter,
	dRERperDLCI                      Counter,
	dDRNumberOfSamplesTaken          Counter,
	dDRNumberOfThresholdViolations   Counter,
        txFDRTimestamp                   Counter,
        txFDRNumberOfSamplesTaken        Counter,
        txFDRNumberOfThresholdViolations Counter,
        rxFDRTimestamp                   Counter,
        rxFDRNumberOfSamplesTaken        Counter,
        rxFDRNumberOfThresholdViolations Counter,
        txDDRTimestamp                   Counter,
        txDDRNumberOfSamplesTaken        Counter,
        txDDRNumberOfThresholdViolations Counter,
        rxDDRTimestamp                   Counter,
        rxDDRNumberOfSamplesTaken        Counter,
        rxDDRNumberOfThresholdViolations Counter,
        txDiscardEligible                Counter,
        rxDiscardEligible                Counter,
        txFECN                           Counter,
        rxFECN                           Counter,
        txBECN                           Counter,
        rxBECN                           Counter
}

deliveryRatioPerDLCITableIndex OBJECT-TYPE
   SYNTAX INTEGER
   ACCESS read-only
   STATUS mandatory
   DESCRIPTION
    "The index of Delivery Ratio Table, which is the same value as
     configurationPerDLCITableIndex."
::= { deliveryRatioPerDLCIEntry 1}

deliveryTableEncodedValue OBJECT-TYPE
   SYNTAX OCTET STRING
   ACCESS read-only
   STATUS mandatory
   DESCRIPTION
    "This object represents the value of the whole row of the table.
     If the table. The intent of object is to increase the efficiency
     of retrieving the table. For each object value in this table,
     which are all of Counter type, it will be represented with 4 bytes
     of data. The byte order of the Counter value will be MSB ... LSB.
     This object will contain the value of all objects on the table,
     except 'deliveryRatioPerDLCITableIndex'."
   ::= { deliveryRatioPerDLCIEntry 2 }

deliveryTableTimestamp OBJECT-TYPE
   SYNTAX Counter
   ACCESS read-only
   STATUS obsolete
   DESCRIPTION
    "Timestamp of the last sample for delivery Entry statistics.
     Each time the near end of the DLCI receives Delivery Ratio Results
     Information Field, this number will contain the unit's current
     timestamp. A timestamp is a 32-bit number representing the number
     of seconds that have elapsed since 12:00AM, January 1, 1970."
   ::= { deliveryRatioPerDLCIEntry 3 }

fTCLperDLCI  OBJECT-TYPE
   SYNTAX Counter
   ACCESS read-only
   STATUS mandatory
   DESCRIPTION
    "Number of frames transmitted at the near end within CIR on this DLCI."
   ::= { deliveryRatioPerDLCIEntry 4 }

fTELperDLCI  OBJECT-TYPE
   SYNTAX Counter
   ACCESS read-only
   STATUS mandatory
   DESCRIPTION
    "Number of frames transmitted at the near end above CIR on this DLCI"
   ::= { deliveryRatioPerDLCIEntry 5 }

fRCLperDLCI  OBJECT-TYPE
   SYNTAX Counter
   ACCESS read-only
   STATUS mandatory
   DESCRIPTION
    "Number of frames received at the near end on this DLCI within CIR.
     These frames will have the Discard Eligible (DE) bit reset."
   ::= { deliveryRatioPerDLCIEntry 6 }

fRELperDLCI  OBJECT-TYPE
   SYNTAX Counter
   ACCESS read-only
   STATUS mandatory
   DESCRIPTION
    "Number of frames received at the near end on this DLCI above CIR.
     These frames will have the Discard Eligible (DE) bit set."
   ::= { deliveryRatioPerDLCIEntry 7 }

fTCRperDLCI  OBJECT-TYPE
   SYNTAX Counter
   ACCESS read-only
   STATUS mandatory
   DESCRIPTION
    "Number of frames transmitted at the far end within CIR on this DLCI."
   ::= { deliveryRatioPerDLCIEntry 8 }

fTERperDLCI  OBJECT-TYPE
   SYNTAX Counter
   ACCESS read-only
   STATUS mandatory
   DESCRIPTION
    "Number of frames transmitted at the far end above CIR on this DLCI."
   ::= { deliveryRatioPerDLCIEntry 9 }

fRCRperDLCI  OBJECT-TYPE
   SYNTAX Counter
   ACCESS read-only
   STATUS mandatory
   DESCRIPTION
    "Number of frames received at the far end on this DLCI within CIR.
     These frames will have the Discard Eligible (DE) bit reset."
   ::= { deliveryRatioPerDLCIEntry 10 }

fRERperDLCI  OBJECT-TYPE
   SYNTAX Counter
   ACCESS read-only
   STATUS mandatory
   DESCRIPTION
    "Number of frames received at the far end on this DLCI above CIR.
     These frames will have the Discard Eligible (DE) bit set."
   ::= { deliveryRatioPerDLCIEntry 11 }

fDRNumberOfSamplesTaken OBJECT-TYPE
   SYNTAX Counter
   ACCESS read-only
   STATUS obsolete
   DESCRIPTION
    "Number of samples taken for Frame Delivery Statistics.
     Each time the near end receives the Frame Delivery Ratio Results
     Information Field, this counter will be incremented."
   ::= { deliveryRatioPerDLCIEntry 12 }

fDRNumberOfThresholdViolations OBJECT-TYPE
   SYNTAX Counter
   ACCESS read-only
   STATUS obsolete
   DESCRIPTION
    "Number of threshold violations for Frame Delivery.
     FDRCL = fRCRPerDLCI / fTCLPerDLCI
     FDRCR = fRCLPerDLCI / fTCRPerDLCI
     For each sample, FDRCL and FDRCR are compared to the threshold
     configured on object 'unitThresholdForFDR'. When either FDRCL
     or FDRCR is less than the threshold, this counter is incremented."
   ::= { deliveryRatioPerDLCIEntry 13 }

dTCLperDLCI  OBJECT-TYPE
   SYNTAX Counter
   ACCESS read-only
   STATUS mandatory
   DESCRIPTION
    "Number of bytes transmitted to the network within CIR on this DLCI."
   ::= { deliveryRatioPerDLCIEntry 14 }

dTELperDLCI  OBJECT-TYPE
   SYNTAX Counter
   ACCESS read-only
   STATUS mandatory
   DESCRIPTION
    "Number of bytes transmitted to the network above CIR on this DLCI"
   ::= { deliveryRatioPerDLCIEntry 15 }

dRCLperDLCI  OBJECT-TYPE
   SYNTAX Counter
   ACCESS read-only
   STATUS mandatory
   DESCRIPTION
    "Number of bytes received at the near end on this DLCI within CIR.
     These frames will have the Discard Eligible (DE) bit reset."
   ::= { deliveryRatioPerDLCIEntry 16 }

dRELperDLCI  OBJECT-TYPE
   SYNTAX Counter
   ACCESS read-only
   STATUS mandatory
   DESCRIPTION
    "Number of bytes received at the near end of this DLCI above CIR.
     These frames will have the Discard Eligible (DE) bit set."
   ::= { deliveryRatioPerDLCIEntry 17 }

dTCRperDLCI  OBJECT-TYPE
   SYNTAX Counter
   ACCESS read-only
   STATUS mandatory
   DESCRIPTION
    "Number of bytes transmitted at the far end within CIR on this DLCI."
   ::= { deliveryRatioPerDLCIEntry 18 }

dTERperDLCI  OBJECT-TYPE
   SYNTAX Counter
   ACCESS read-only
   STATUS mandatory
   DESCRIPTION
    "Number of bytes transmitted at the far end above CIR on this DLCI."
   ::= { deliveryRatioPerDLCIEntry 19 }

dRCRperDLCI  OBJECT-TYPE
   SYNTAX Counter
   ACCESS read-only
   STATUS mandatory
   DESCRIPTION
    "Number of bytes received at the far end on this DLCI above CIR.
     These frames will have the Discard Eligible (DE) bit reset."
   ::= { deliveryRatioPerDLCIEntry 20 }

dRERperDLCI  OBJECT-TYPE
   SYNTAX Counter
   ACCESS read-only
   STATUS mandatory
   DESCRIPTION
    "Number of bytes received at the far end on his DLCI above CIR.
     These frames will have the Discard Eligible (DE) bit set."
   ::= { deliveryRatioPerDLCIEntry 21 }

dDRNumberOfSamplesTaken OBJECT-TYPE
   SYNTAX Counter
   ACCESS read-only
   STATUS obsolete
   DESCRIPTION
    "Number of samples taken for Data Delivery statistics.
     Each time the near end receives the Data Delivery Ratio Results
     Information Field, this counter will be incremented."
   ::= { deliveryRatioPerDLCIEntry 22 }

dDRNumberOfThresholdViolations OBJECT-TYPE
   SYNTAX Counter
   ACCESS read-only
   STATUS obsolete
   DESCRIPTION
    "Number of threshold violations for Data Delivery statistics.
     DDRCL = dRCRPerDLCI / dTCLPerDLCI
     DDRCR = dRCLPerDLCI / dTCRPerDLCI
     For each sample, DDRCL and DDRCR are compared to the threshold
     configured on object 'unitThresholdForDDR'. When either DDRCL
     or DDRCR is less than the threshold, this counter is incremented."
   ::= { deliveryRatioPerDLCIEntry 23 }

txFDRTimestamp OBJECT-TYPE
   SYNTAX Counter
   ACCESS read-only
   STATUS mandatory
   DESCRIPTION
    "Timestamp of the last sample for delivery Entry statistics.
     Each time the near end of the DLCI receives Delivery Ratio Results
     Information Field, this number will contain the unit's current
     timestamp. A timestamp is a 32-bit number representing the number
     of seconds that have elapsed since 12:00AM, January 1, 1970."
   ::= { deliveryRatioPerDLCIEntry 24 }

txFDRNumberOfSamplesTaken OBJECT-TYPE
   SYNTAX Counter
   ACCESS read-only
   STATUS mandatory
   DESCRIPTION
    "Number of samples taken for Frame Delivery Statistics.
     Each time the near end receives the Frame Delivery Ratio Results
     Information Field, this counter will be incremented."
   ::= { deliveryRatioPerDLCIEntry 25 }

txFDRNumberOfThresholdViolations OBJECT-TYPE
   SYNTAX Counter
   ACCESS read-only
   STATUS mandatory
   DESCRIPTION
    "Number of threshold violations for Frame Delivery.
     FDRCL = fRCRPerDLCI / fTCLPerDLCI
     For each sample, FDRCL is compared to the threshold configured on
     object 'unitThresholdForFDR'. When FDRCL is less than the threshold,
     this counter is incremented."
   ::= { deliveryRatioPerDLCIEntry 26 }

rxFDRTimestamp OBJECT-TYPE
   SYNTAX Counter
   ACCESS read-only
   STATUS mandatory
   DESCRIPTION
    "Timestamp of the last sample for delivery Entry statistics.
     Each time the near end of the DLCI receives Delivery Ratio poll,
     this number will contain the unit's current timestamp.
     A timestamp is a 32-bit number representing the number of seconds
     that have elapsed since 12:00AM, January 1, 1970."
   ::= { deliveryRatioPerDLCIEntry 27 }

rxFDRNumberOfSamplesTaken OBJECT-TYPE
   SYNTAX Counter
   ACCESS read-only
   STATUS mandatory
   DESCRIPTION
    "Number of samples taken for Frame Delivery Statistics.
     Each time the near end receives the Frame Delivery Ratio poll,
     this counter will be incremented."
   ::= { deliveryRatioPerDLCIEntry 28 }

rxFDRNumberOfThresholdViolations OBJECT-TYPE
   SYNTAX Counter
   ACCESS read-only
   STATUS mandatory
   DESCRIPTION
    "Number of threshold violations for Frame Delivery.
     FDRCR = fRCLPerDLCI / fTCRPerDLCI
     For each sample, FDRCR is compared to the threshold configured
     on object 'unitThresholdForFDR'. When FDRCR is less than the
     threshold, this counter is incremented."
   ::= { deliveryRatioPerDLCIEntry 29 }

txDDRTimestamp OBJECT-TYPE
   SYNTAX Counter
   ACCESS read-only
   STATUS mandatory
   DESCRIPTION
    "Timestamp of the last sample for delivery Entry statistics.
     Each time the near end of the DLCI receives Delivery Ratio Results
     Information Field, this number will contain the unit's current
     timestamp. A timestamp is a 32-bit number representing the number
     of seconds that have elapsed since 12:00AM, January 1, 1970."
   ::= { deliveryRatioPerDLCIEntry 30 }

txDDRNumberOfSamplesTaken OBJECT-TYPE
   SYNTAX Counter
   ACCESS read-only
   STATUS mandatory
   DESCRIPTION
    "Number of samples taken for DataDelivery Statistics.
     Each time the near end receives the Data Delivery Ratio Results
     Information Field, this counter will be incremented."
   ::= { deliveryRatioPerDLCIEntry 31 }

txDDRNumberOfThresholdViolations OBJECT-TYPE
   SYNTAX Counter
   ACCESS read-only
   STATUS mandatory
   DESCRIPTION
    "Number of threshold violations for Data Delivery.
     DDRCL = dRCRPerDLCI / dTCLPerDLCI
     For each sample, DDRCL is compared to the threshold configured
     on object 'unitThresholdForDDR'. When DDRCL is less than the
     threshold, this counter is incremented."
   ::= { deliveryRatioPerDLCIEntry 32 }

rxDDRTimestamp OBJECT-TYPE
   SYNTAX Counter
   ACCESS read-only
   STATUS mandatory
   DESCRIPTION
    "Timestamp of the last sample for delivery Entry statistics.
     Each time the near end of the DLCI receives Delivery Ratio poll,
     this number will contain the unit's current timestamp.
     A timestamp is a 32-bit number representing the number of seconds
     that have elapsed since 12:00AM, January 1, 1970."
   ::= { deliveryRatioPerDLCIEntry 33 }

rxDDRNumberOfSamplesTaken OBJECT-TYPE
   SYNTAX Counter
   ACCESS read-only
   STATUS mandatory
   DESCRIPTION
    "Number of samples taken for Data Delivery Statistics.
     Each time the near end receives the Data Delivery Ratio poll,
     this counter will be incremented."
   ::= { deliveryRatioPerDLCIEntry 34 }

rxDDRNumberOfThresholdViolations OBJECT-TYPE
   SYNTAX Counter
   ACCESS read-only
   STATUS mandatory
   DESCRIPTION
    "Number of threshold violations for Data Delivery.
     DDRCR = dRCLPerDLCI / dTCRPerDLCI
     For each sample, DDRCR is compared to the threshold configured
     on object 'unitThresholdForDDR'. When DDRCR is less than the
     threshold, this counter is incremented."
   ::= { deliveryRatioPerDLCIEntry 35 }

txDiscardEligible OBJECT-TYPE
   SYNTAX Counter
   ACCESS read-only
   STATUS mandatory
   DESCRIPTION
    "Number of Discard Eligible counters transmitted at the near end.
     This counter has the same value as object 'etherStatsFragments'
     in RMON MIB (RFC 1757) for DTE port."
   ::= { deliveryRatioPerDLCIEntry 36 }

rxDiscardEligible OBJECT-TYPE
   SYNTAX Counter
   ACCESS read-only
   STATUS mandatory
   DESCRIPTION
    "Number of Discard Eligible counters received by the near end.
     This counter has the same value as object 'etherStatsFragments'
     in RMON MIB (RFC 1757) for DCE port"
   ::= { deliveryRatioPerDLCIEntry 37 }

txFECN OBJECT-TYPE
   SYNTAX Counter
   ACCESS read-only
   STATUS mandatory
   DESCRIPTION
    "Number of FECN counters transmitted at the near end.
     This counter has the same value as object 'etherStatsCollisions'
     in RMON MIB (RFC 1757) for DTE port."
   ::= { deliveryRatioPerDLCIEntry 38 }

rxFECN OBJECT-TYPE
   SYNTAX Counter
   ACCESS read-only
   STATUS mandatory
   DESCRIPTION
    "Number of FECN counters received by the near end.
     This counter has the same value as object 'etherStatsCollisions'
     in RMON MIB (RFC 1757) for DCE port."
   ::= { deliveryRatioPerDLCIEntry 39 }

txBECN OBJECT-TYPE
   SYNTAX Counter
   ACCESS read-only
   STATUS mandatory
   DESCRIPTION
    "Number of BECN counters transmitted at the near end.
     This counter has the same value as object 'etherStatsJabbers'
     in RMON MIB (RFC 1757) for DTE port."
   ::= { deliveryRatioPerDLCIEntry 40 }

rxBECN OBJECT-TYPE
   SYNTAX Counter
   ACCESS read-only
   STATUS mandatory
   DESCRIPTION
    "Number of BECN counters received by the near end.
     This counter has the same value as object 'etherStatsJabbers'
     in RMON MIB (RFC 1757) for DCE port."
   ::= { deliveryRatioPerDLCIEntry 41 }

--
--  Delay Statistics Group
--

dlcDelayStatistics OBJECT IDENTIFIER
  ::= { dlcSLAStatisticsGroup 2 }

delayPerDLCITable OBJECT-TYPE
  SYNTAX SEQUENCE OF DelayPerDLCIEntry
  ACCESS not-accessible
  STATUS mandatory
  DESCRIPTION
   "Delay Table Per DLCI"
  ::= { dlcDelayStatistics 1 }

delayPerDLCIEntry OBJECT-TYPE
  SYNTAX DelayPerDLCIEntry
  ACCESS not-accessible
  STATUS mandatory
  DESCRIPTION
   "An entry in the Delay per DLCI table."
  INDEX { delayPerDLCITableIndex}
  ::= { delayPerDLCITable 1 }

DelayPerDLCIEntry ::=
SEQUENCE  {
	delayPerDLCITableIndex                  INTEGER,
	delayTableEncodedValue			OCTET STRING,
	delayTableTimestamp			Counter,
	totalRoundTripDelayPerDLCI              Counter,
	maximumRoundTripDelayNSamplesPerDLCI    Counter,
 	maximumRoundTripDelay2NSamplesPerDLCI   Counter,
	maximumRoundTripDelay4NSamplesPerDLCI   Counter,
	numberOfDelayMeasurementsPerDLCI        Counter,
	delayNumberOfThresholdViolations	Counter
	}

delayPerDLCITableIndex OBJECT-TYPE
   SYNTAX INTEGER
   ACCESS read-only
   STATUS mandatory
   DESCRIPTION
    "The index of Delay Table, which is DLCI number."
   ::= { delayPerDLCIEntry 1 }

delayTableEncodedValue OBJECT-TYPE
   SYNTAX OCTET STRING
   ACCESS read-only
   STATUS mandatory
   DESCRIPTION
    "This object represents the value of the whole row of the table.
     If the table. The intent of object is to increase the efficiency
     of retrieving the table. For each object value in this table,
     which are all of Counter type, it will be represented with 4 bytes
     of data. The byte order of the Counter value will be MSB ... LSB.
     This object will contain the value of all objects on the table,
     except 'delayPerDLCITableIndex'."
   ::= { delayPerDLCIEntry 2 }

delayTableTimestamp OBJECT-TYPE
   SYNTAX Counter
   ACCESS read-only
   STATUS mandatory
   DESCRIPTION
    "Timestamp for Delay Table entry.
     Each time the near end of the DLCI receives an OA&M message
     containing a Frame Transfer Delay Information Field,
     this number will contain the unit's current timestamp.
     A timestamp is a 32-bit number representing the number
     of seconds that have elapsed since 12:00AM, January 1, 1970."
   ::= { delayPerDLCIEntry 3 }

totalRoundTripDelayPerDLCI  OBJECT-TYPE
   SYNTAX Counter
   ACCESS read-only
   STATUS mandatory
   DESCRIPTION 
   "Sum of all the round trip delay measurements taken so far."
   ::= { delayPerDLCIEntry 4 }

maximumRoundTripDelayNSamplesPerDLCI  OBJECT-TYPE
   SYNTAX Counter
   ACCESS read-only
   STATUS mandatory
   DESCRIPTION
    "Maximum Round Trip Delay in last n samples. N is 15."
   ::= { delayPerDLCIEntry 5 }

maximumRoundTripDelay2NSamplesPerDLCI  OBJECT-TYPE
   SYNTAX Counter
   ACCESS read-only
   STATUS mandatory
   DESCRIPTION
     "Maximum Round Trip Delay in last 2N samples. N is 15."
   ::= { delayPerDLCIEntry 6 }

maximumRoundTripDelay4NSamplesPerDLCI  OBJECT-TYPE
   SYNTAX Counter
   ACCESS read-only
   STATUS mandatory
   DESCRIPTION
     "Maximum Round Trip Delay in last 4n samples. N is 15."
   ::= { delayPerDLCIEntry 7 }

numberOfDelayMeasurementsPerDLCI  OBJECT-TYPE
   SYNTAX Counter
   ACCESS read-only
   STATUS mandatory
   DESCRIPTION
    "Number of delay measurements per DLCI.
     Each time the near end receives an OA&M message containing
     a Frame Transfer Delay Information Field, this counter
     will be incremented."
   ::= { delayPerDLCIEntry 8 }

delayNumberOfThresholdViolations  OBJECT-TYPE
   SYNTAX Counter
   ACCESS read-only
   STATUS mandatory
   DESCRIPTION
    "Number of threshold violations on Delay measurement.
     If an individual delay measurement on this DLCI is greater
     than the threshold value configured in object 
     'thresholdForDelayMeasurementPerDLCI', this counter will be
     incremented."
   ::= { delayPerDLCIEntry 9 }

--
--  Outage Statistics Group
--

dlcOutageStatistics OBJECT IDENTIFIER
  ::= { dlcSLAStatisticsGroup 3 }

outagePerDLCITable OBJECT-TYPE
  SYNTAX SEQUENCE OF OutagePerDLCIEntry
  ACCESS not-accessible
  STATUS mandatory
  DESCRIPTION
   "Outage Table Per DLCI"
  ::= { dlcOutageStatistics 1 }

outagePerDLCIEntry OBJECT-TYPE
  SYNTAX OutagePerDLCIEntry
  ACCESS not-accessible
  STATUS mandatory
  DESCRIPTION
   "An entry in the Outage per DLCI table."
  INDEX { outageTableIndex }
  ::= { outagePerDLCITable 1 }

OutagePerDLCIEntry ::=
SEQUENCE  {
	outageTableIndex		INTEGER,
	outageTableEncodedValue         OCTET STRING,
	outageTableTimestamp		Counter,
	outageStatus                    INTEGER,
        numberOfOutageCounter		Counter,
	periodOfOutages			Counter,
	numberOfExcludedOutageCounter	Counter,
	periodOfExcludedOutages		Counter
}

outageTableIndex OBJECT-TYPE
   SYNTAX INTEGER
   ACCESS read-only
   STATUS mandatory
   DESCRIPTION
    "Index of Outage Table, which is the DLCI number."
   ::= { outagePerDLCIEntry 1 }

outageTableEncodedValue OBJECT-TYPE
   SYNTAX OCTET STRING
   ACCESS read-only
   STATUS mandatory
   DESCRIPTION
    "This object represents the value of the whole row of the table.
     If the table. The intent of object is to increase the efficiency
     of retrieving the table. For each object value in this table,
     which are all of Counter type, it will be represented with 4 bytes
     of data. The byte order of the Counter value will be MSB ... LSB.
     This object will contain the value of all objects on the table,
     except 'outageTableIndex'."
   ::= { outagePerDLCIEntry 2 }

outageTableTimestamp OBJECT-TYPE
   SYNTAX Counter
   ACCESS read-only
   STATUS mandatory
   DESCRIPTION
    "Timestamp of when this Outage Table entry last updated.
     A timestamp is a 32-bit number representing the number
     of seconds that have elapsed since 12:00AM, January 1, 1970."
   ::= { outagePerDLCIEntry 3 }

outageStatus OBJECT-TYPE
  SYNTAX  INTEGER {
	unknown	(1),
	no-outage (2),
        excluded-outage (3),
        included-outage (4)
  }
  ACCESS read-only
  STATUS mandatory
  DESCRIPTION
   ""
  ::= { outagePerDLCIEntry 4 }

numberOfOutageCounter OBJECT-TYPE
   SYNTAX Counter
   ACCESS read-only
   STATUS mandatory
   DESCRIPTION
    "Number of outages."
   ::= { outagePerDLCIEntry 5 }

periodOfOutages OBJECT-TYPE
   SYNTAX Counter
   ACCESS read-only
   STATUS mandatory
   DESCRIPTION
    "The sum total of how long the outages are."
   ::= { outagePerDLCIEntry 6 }

numberOfExcludedOutageCounter OBJECT-TYPE
   SYNTAX Counter
   ACCESS read-only
   STATUS mandatory
   DESCRIPTION
    "Number of excluded outages."
   ::= { outagePerDLCIEntry 7 }

periodOfExcludedOutages OBJECT-TYPE
   SYNTAX Counter
   ACCESS read-only
   STATUS mandatory
   DESCRIPTION
    "The sum total of how long excluded outages are."
   ::= { outagePerDLCIEntry 8 }

outageTableLastTimestamp OBJECT-TYPE
  SYNTAX Counter
  ACCESS read-only
  STATUS mandatory
  DESCRIPTION
   "This object contains timestamp (in seconds) of the last
    time 'outagePerDLCITable' is updated (changed)."
  ::= { dlcOutageStatistics 2 }


--
-- SLA Traps
--

fDRThresholdTrap TRAP-TYPE
  ENTERPRISE dl-ServiceLevelAgreement
  VARIABLES { deliveryRatioPerDLCITableIndex }
  DESCRIPTION
   "This trap will be sent if 'fDRNumberOfThresholdViolations'
    is incremented. The VARIABLES contain the DLCI number whose
    Frame Delivery Ratio threshold violation is updated."
  ::= 1

dDRThresholdTrap TRAP-TYPE
  ENTERPRISE dl-ServiceLevelAgreement
  VARIABLES { deliveryRatioPerDLCITableIndex }
  DESCRIPTION
   "This trap will be sent if 'dDRNumberOfThresholdViolations'
    is incremented. The VARIABLES contain the DLCI number whose
    Data Delivery Ratio threshold violation is updated."
  ::= 2

delayThresholdTrap TRAP-TYPE
  ENTERPRISE dl-ServiceLevelAgreement
  VARIABLES { delayPerDLCITableIndex }
  DESCRIPTION
   "This trap will be sent if 'delayNumberOfThresholdViolations'
    is incremented. The VARIABLES contain the DLCI number whose
    Delay threshold violation is updated."
  ::= 3

END
