-- **********************************************************
-- Copyright 2007 VMware, Inc.  All rights reserved. 
-- 
--  This MIB Module provides resource monitoring of ESX.
--  See SMIv2 format version of this MIB module to access
--  64 bit wide counters.
--
-- **********************************************************
-- Version 2.0

VMWARE-RESOURCES-MIB DEFINITIONS ::= BEGIN

IMPORTS
   Counter, Gauge
      FROM RFC1155-SMI
   OBJECT-TYPE
      FROM RFC-1212
   DisplayString 
      FROM RFC1213-MIB 
   vmwResources 
      FROM VMWARE-ROOT-MIB;

--      "This file contains the VMware MIB's subtree for resource variables.
--       Note: Throughout this file, the term 'machine' is used to refer to the
--       physical machine (on which the ESX Server is running). "

-- CPU subtree

vmwCPU OBJECT IDENTIFIER ::= { vmwResources 1 }

numCPUs OBJECT-TYPE
   SYNTAX	Gauge
   ACCESS      	read-only
   STATUS      	mandatory
   DESCRIPTION
      "Number of physical CPUs on the system."
   ::= { vmwCPU 1 }

cpuTable OBJECT-TYPE
   SYNTAX	SEQUENCE OF CpuEntry
   ACCESS    	not-accessible	
   STATUS    	mandatory
   DESCRIPTION
      "CPU Usage table by virtual machine."
   ::= { vmwCPU 2 }

cpuEntry OBJECT-TYPE
   SYNTAX	CpuEntry
   ACCESS    	not-accessible	
   STATUS    	mandatory
   DESCRIPTION
      "A record for CPU usage by a single virtual machine."
   INDEX	{ cpuVMID }
   ::= { cpuTable 1 }

CpuEntry    ::= SEQUENCE
{
   cpuVMID 	INTEGER,
   cpuShares	Gauge,
   cpuUtil	Gauge
}

cpuVMID OBJECT-TYPE
   SYNTAX	INTEGER (0..1023)
   ACCESS    	read-only
   STATUS    	mandatory
   DESCRIPTION
      "ID allocated to running vm by the vmkernel."
   ::= { cpuEntry 1 }

cpuShares OBJECT-TYPE
   SYNTAX	Gauge
   ACCESS    	read-only
   STATUS    	mandatory
   DESCRIPTION
      "Share of CPU allocated to vm by vmkernel."
   ::= { cpuEntry 2 }

cpuUtil OBJECT-TYPE
   SYNTAX       Gauge
   ACCESS    	read-only
   STATUS    	mandatory
   DESCRIPTION
      "Time the virtual machine has been running on the CPU (seconds)."
   ::= { cpuEntry 3 }

-- Memory subtree 

vmwMemory OBJECT IDENTIFIER ::= { vmwResources 2 }

memSize OBJECT-TYPE
   SYNTAX	Gauge
   ACCESS    	read-only
   STATUS    	mandatory
   DESCRIPTION
      "Amount of physical memory present on machine (KB)."
   ::= { vmwMemory 1 }

memCOS OBJECT-TYPE
   SYNTAX	Gauge
   ACCESS    	read-only
   STATUS    	mandatory
   DESCRIPTION
      "Amount of physical memory used by the console OS (KB)."
   ::= { vmwMemory 2 }

memAvail OBJECT-TYPE
   SYNTAX	Gauge
   ACCESS    	read-only
   STATUS    	mandatory
   DESCRIPTION
      "Amount of physical memory available/free (KB)."
   ::= { vmwMemory 3 }

memTable OBJECT-TYPE
   SYNTAX	SEQUENCE OF MemEntry
   ACCESS    	not-accessible	
   STATUS    	mandatory
   DESCRIPTION
      "Table of memory usage by virtual machine."
   ::= { vmwMemory 4 }

memEntry OBJECT-TYPE
   SYNTAX	MemEntry
   ACCESS    	not-accessible	
   STATUS    	mandatory
   DESCRIPTION
      "A record for memory usage by a single virtual machine."
   INDEX	{ memVMID }
   ::= { memTable 1 }

MemEntry    ::= SEQUENCE
{
   memVMID	 INTEGER,
   memShares	 Gauge,
   memConfigured Gauge,
   memUtil       Gauge
}

memVMID OBJECT-TYPE
   SYNTAX	INTEGER (0..1023)
   ACCESS    	read-only
   STATUS    	mandatory
   DESCRIPTION
      "ID allocated to running vm by the vmkernel."
   ::= { memEntry 1 }

memShares OBJECT-TYPE
   SYNTAX	Gauge
   ACCESS    	read-only
   STATUS    	mandatory
   DESCRIPTION
      "Shares of memory allocated to vm by vmkernel."
   ::= { memEntry 2 }

memConfigured OBJECT-TYPE
   SYNTAX	Gauge
   ACCESS    	read-only
   STATUS    	mandatory
   DESCRIPTION
      "Amount of memory the vm was configured with. (KB)"
   ::= { memEntry 3 }

memUtil OBJECT-TYPE
   SYNTAX	Gauge
   ACCESS    	read-only
   STATUS    	mandatory
   DESCRIPTION
      "Amount of memory utilized by the vm. (KB; instantaneous)"
   ::= { memEntry 4 }

-- Disk subtree --

vmwHBATable OBJECT-TYPE
   SYNTAX	SEQUENCE OF HbaEntry
   ACCESS    	not-accessible	
   STATUS    	mandatory
   DESCRIPTION
      "Disk adapter and target information table."
   ::= { vmwResources 3 }

hbaEntry OBJECT-TYPE
   SYNTAX	HbaEntry
   ACCESS     	not-accessible	
   STATUS    	mandatory
   DESCRIPTION
      "A record for a single hba on the machine."
   INDEX	{ hbaIdx }
   ::= { vmwHBATable 1 }

HbaEntry     ::= SEQUENCE
{
   hbaIdx  	INTEGER,
   hbaName	DisplayString,
   hbaVMID	INTEGER,
   diskShares	Gauge,
   numReads	Counter,
   kbRead	Counter,
   numWrites	Counter,
   kbWritten	Counter
}


hbaIdx OBJECT-TYPE
   SYNTAX	INTEGER (0..255)
   ACCESS    	read-only
   STATUS    	mandatory
   DESCRIPTION
      "Index for HBA table."
   ::= { hbaEntry 1 }

hbaName OBJECT-TYPE
   SYNTAX	DisplayString	
   ACCESS    	read-only
   STATUS    	mandatory
   DESCRIPTION
      "String describing the disk. Format: <devname#>:<tgt>:<lun> "
   ::= { hbaEntry 2 }

hbaVMID OBJECT-TYPE
   SYNTAX	INTEGER
   ACCESS    	read-only
   STATUS    	mandatory
   DESCRIPTION
      "ID assigned to running vm by the vmkernel."
   ::= { hbaEntry 3 }

diskShares OBJECT-TYPE
   SYNTAX	Gauge
   ACCESS    	read-only
   STATUS    	mandatory
   DESCRIPTION
      "Share of disk bandwidth allocated to this vm."
   ::= { hbaEntry 4 }

numReads OBJECT-TYPE
   SYNTAX	Counter
   ACCESS    	read-only
   STATUS    	mandatory
   DESCRIPTION
      "Number of reads to this disk since disk module was loaded."
   ::= { hbaEntry 5 }

kbRead OBJECT-TYPE
   SYNTAX	Counter
   ACCESS    	read-only
   STATUS    	mandatory
   DESCRIPTION
      "Kilobytes read from this disk since disk module was loaded."
   ::= { hbaEntry 6 }

numWrites OBJECT-TYPE
   SYNTAX	Counter
   ACCESS    	read-only
   STATUS    	mandatory
   DESCRIPTION
      "Number of writes to this disk since disk module was loaded." 
   ::= { hbaEntry 7 }

kbWritten OBJECT-TYPE
   SYNTAX	Counter
   ACCESS    	read-only
   STATUS    	mandatory
   DESCRIPTION
      "Kilobytes written to this disk since disk module was loaded."
   ::= { hbaEntry 8 }

-- Net subtree

vmwNetTable OBJECT-TYPE
   SYNTAX	SEQUENCE OF NetEntry
   ACCESS    	not-accessible	
   STATUS    	mandatory
   DESCRIPTION
      "Network adapter statistics."
   ::= { vmwResources 4 }

netEntry OBJECT-TYPE
   SYNTAX	NetEntry
   ACCESS     	not-accessible	
   STATUS    	mandatory
   DESCRIPTION
      "A record for a single nic on the machine."
   INDEX	{ netIdx }
   ::= { vmwNetTable 1 }

NetEntry     ::= SEQUENCE
{
   netIdx  	INTEGER,
   netName	DisplayString,
   netVMID	INTEGER,
   ifAddr       DisplayString,
   netShares	Gauge,
   pktsTx       Counter,
   kbTx         Counter,
   pktsRx       Counter,
   kbRx         Counter
}


netIdx OBJECT-TYPE
   SYNTAX	INTEGER (0..255)
   ACCESS    	read-only
   STATUS    	mandatory
   DESCRIPTION
      "Index for net table."
   ::= { netEntry 1 }

netName OBJECT-TYPE
   SYNTAX	DisplayString	
   ACCESS    	read-only
   STATUS    	mandatory
   DESCRIPTION
      "String describing the network adapter. Format: vmnic*" 
   ::= { netEntry 2 }

netVMID OBJECT-TYPE
   SYNTAX	INTEGER
   ACCESS    	read-only
   STATUS    	mandatory
   DESCRIPTION
      "ID assigned to running vm by the vmkernel."
   ::= { netEntry 3 }

ifAddr OBJECT-TYPE
   SYNTAX	DisplayString	
   ACCESS    	read-only
   STATUS    	mandatory
   DESCRIPTION
      "MAC address of vm's virtual NIC." 
   ::= { netEntry 4 }

netShares OBJECT-TYPE
   SYNTAX       Gauge
   ACCESS       not-accessible	
   STATUS    	mandatory
   DESCRIPTION
      "Share of net bandwidth allocated to this vm. (NOT IMPLEMENTED)"
   ::= { netEntry 5 }

pktsTx OBJECT-TYPE
   SYNTAX	Counter
   ACCESS    	read-only
   STATUS    	mandatory
   DESCRIPTION
      "Number of pkts transmitted on this NIC since network module was
       loaded. See SMIv2 version for 64 bit packets"
   ::= { netEntry 6 }

kbTx OBJECT-TYPE
   SYNTAX	Counter
   ACCESS    	read-only
   STATUS    	mandatory
   DESCRIPTION
      "Kilobytes sent from this NIC since network module was loaded.
       See SMIv2 version for 64 bit packets."      
   ::= { netEntry 7 }

pktsRx OBJECT-TYPE
   SYNTAX	Counter
   ACCESS    	read-only
   STATUS    	mandatory
   DESCRIPTION
      "Number of pkts received on this NIC since network module was loaded.
       See SMIv2 version for 64 bit packets."            
   ::= { netEntry 8 }

kbRx OBJECT-TYPE
   SYNTAX	Counter
   ACCESS    	read-only
   STATUS    	mandatory
   DESCRIPTION
      "Kilobytes received on this NIC since network module was loaded.
       See SMIv2 version for 64 bit packets."                  
   ::= { netEntry 9 }

END
