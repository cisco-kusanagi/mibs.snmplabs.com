DL5400-MIB  DEFINITIONS ::= BEGIN

-- Digital-Link Corporation  definitions for DL5400 product agents
-- Version  : V1.0 08/28/1998
-- Comments : This MIB has not been officially released to the N.I.C.

IMPORTS
	OBJECT-TYPE
		FROM RFC-1212
	TRAP-TYPE
		FROM RFC-1215
	enterprises,  IpAddress, TimeTicks, Counter
		FROM RFC1155-SMI;

--	The following information has been included from RFC1213.
--	textual conventions
	
	DisplayString ::=
		OCTET STRING

--	This data type is used to model textual information taken from 
--	NVT ASCII character set. By convention, objects with this syntax
--	are declared as having SIZE (0..255)



digital-link	OBJECT IDENTIFIER ::= { enterprises 300 }
dl5400          OBJECT IDENTIFIER ::= { digital-link 110 }

configuration   OBJECT IDENTIFIER ::= { dl5400 1 }
alarms       	OBJECT IDENTIFIER ::= { dl5400 2 }
events       	OBJECT IDENTIFIER ::= { dl5400 3 }
statistics      OBJECT IDENTIFIER ::= { dl5400 4 }
maintenance     OBJECT IDENTIFIER ::= { dl5400 5 }

   -- the Validation type is used for the variable that deletes
   -- an entry from a table, and ALWAYS takes at least these values:

DL5400Validation ::= INTEGER { valid (1), invalid (2) }


DL5400commBaudRate ::= 
	INTEGER {
            bps1200        (1),
            bps2400        (2),
            bps4800        (3),
            bps9600        (4),
            bps19200       (5),
            bps38400       (6),
            bps57600       (7),
	    bps115200      (8)
	}

DL5400commParity ::= 
        INTEGER {
	    even    (1),
	    odd     (2),
	    none    (3)
	}


DL5400commStopBits ::= 
        INTEGER {
            one        (1),
	    oneAndHalf  (2),
	    two         (3)
	}

DL5400commNumDataBits ::=
	INTEGER {
	    seven	(7),
	    eight	(8)
	}
DL5400commFlowControl ::=
	INTEGER {
	    xoffUntilXon	(1),
	    xoffUntilAny	(2),
	    hwFlowControl	(3),
	    none		(4)
	}

TODYear		::= INTEGER (0..9999)
TODMonth	::= INTEGER (1..12)
TODDay		::= INTEGER (1..31) 
TODHour		::= INTEGER (0..23)
TODMinute	::= INTEGER (0..59)
TODSecond       ::= INTEGER (0..59)


DL5400CardId ::= 
	INTEGER {
            mpm    (1),
            pp     (2),
            enet   (3),
            ds1    (4)
        }

DL5400PortId ::= 
	INTEGER {
            dte             (1),
            nmsEthernet     (2),
            comm1           (3),
            comm2           (4),
            net1            (5),
            net2            (6),
            net3            (7),
            net4            (8),
            net5            (9),
            net6            (10),
            net7            (11),
            net8            (12)
        }


DL5400TxClkSrc ::=
	INTEGER {
	    internalClock (1),
	    externalClock (2),
            rcvrdTiming   (3),
            autoTiming    (4)
        }


DL5400Event ::=
	INTEGER {
	    ev-mod-appear (1)
	  , ev-mod-disappear (2)
	  , ev-system-reset (3)
	  , ev-system-initialized (4)
	  , ev-timeofday-changed (5)
	  , ev-admin-isnr (6)
	  , ev-admin-oos (7)
	  , ev-admin-oosmt (8)
	  , ev-cuisession-inactivitytimeout (9)
	  , ev-clkref-configchanged (10)
	  , ev-selftest-fail(11)
	  , ev-ram-test-fail(12)
	  , ev-rom-checksum-fail(13)
	  , ev-flash-checksum-fail(14)
	  , ev-time-not-set(15)
	  , ev-unit-restart(16)
	  , ev-lamptest-start(17)
	  , ev-lamptest-end(18)
	  , ev-mgmt-post-fail(19)
	  , ev-mgmt-post-fail-remit(20)
	  , ev-front-high-temperature(21)
	  , ev-front-high-temperature-remit(22)
	  , ev-back-high-temperature(23)
	  , ev-back-high-temperature-remit(24)
	  , ev-external-major-alarm-input(25)
	  , ev-external-major-alarm-input-end(26)
	  , ev-external-minor-alarm-input(27)
	  , ev-external-minor-alarm-input-end(28)
	  , ev-external-status-alarm-input(29)
	  , ev-external-status-alarm-input-end(30)
	  , ev-primary-clk-fail(31)
	  , ev-primary-clk-ok(32)
	  , ev-secondary-clk-fail(33)
	  , ev-secondary-clk-ok(34)
	  , ev-ext-clk-fail(35)
	  , ev-ext-clk-ok(36)
	  , ev-fan1-fail(37)
	  , ev-fan1-ok(38)
	  , ev-fan2-fail(39)
	  , ev-fan2-ok(40)
	  , ev-ps-fan-fail(41)
	  , ev-ps-fan-ok(42)
	  , ev-packet-processor-post-fail(43)
	  , ev-packet-processor-post-ok(44)
	  , ev-packet-processor-missing(45)
	  , ev-packet-processor-ok(46)
	  , ev-voltage-exceeds(47)
	  , ev-voltage-ok(48)
	  , ev-module-processor-fail(49)
	  , ev-module-processor-ok(50)
	  , ev-mod-cfg-mismatch (51)
	  , ev-mod-cfg-match (52)
	  , ev-use-primary-clk(53)
	  , ev-use-secondary-clk(54)
	  , ev-use-internal-clk(55)
	  , ev-use-rx-clk1(56)
	  , ev-use-rx-clk2(57)
	  , ev-use-rx-clk3(58)
	  , ev-use-rx-clk4(59)
	  , ev-use-rx-clk5(60)
	  , ev-use-rx-clk6(61)
	  , ev-use-rx-clk7(62)
	  , ev-use-rx-clk8(63)
	  , ev-mlppp-post-fail(64)
	  , ev-mlppp-post-fail-remit(65)
	  , ev-mlppp-module-missing(66)
	  , ev-mlppp-module-ok(67)
          , ev-mlppp-insufficient-links(68)
          , ev-mlppp-insufficient-links-remit(69)
	  , ev-mod-fail (70)
	  , ev-mod-up (71)
	  , ev-mod-no-resp (72)
	  , ev-mod-hello (73)
	  , ev-mod-init-fail (74)
	  , ev-mod-init-ok (75)
	  , ev-mod-some-ports-failed (76)
	  , ev-mod-some-ports-ok (77)
	  , ev-mod-all-ports-failed (78)
	  , ev-mod-all-ports-ok (79)
          , ev-lost-signal(100)
          , ev-lost-signal-remit(101)
          , ev-lof(102)
          , ev-lof-remit(103)
          , ev-ais(104)
          , ev-ais-remit(105)
          , ev-rai(106)
          , ev-rai-remit(107)
	  , ev-red-alarm(108)
	  , ev-red-alarm-remit(109)
	  , ev-exceeded-cv-consec-sec(110)
	  , ev-exceeded-cv-consec-sec-remit(111)
	  , ev-exceeded-ses-consec-sec(112)
	  , ev-exceeded-ses-consec-sec-remit(113)
	  , ev-exceeded-uas-consec-sec(114)
	  , ev-exceeded-uas-consec-sec-remit(115)
	  , ev-exceeded-pcv-15min-minor-threshold(116)
	  , ev-exceeded-pcv-15min-minor-threshold-remit(117)
	  , ev-exceeded-pcv-15min-major-threshold(118)
	  , ev-exceeded-pcv-15min-major-threshold-remit(119)
	  , ev-exceeded-es-15min-minor-threshold(120)
	  , ev-exceeded-es-15min-minor-threshold-remit(121)
	  , ev-exceeded-es-15min-major-threshold(122)
	  , ev-exceeded-es-15min-major-threshold-remit(123)
	  , ev-exceeded-ses-15min-minor-threshold(124)
	  , ev-exceeded-ses-15min-minor-threshold-remit(125)
	  , ev-exceeded-ses-15min-major-threshold(126)
	  , ev-exceeded-ses-15min-major-threshold-remit(127)
	  , ev-exceeded-sas-15min-minor-threshold(128)
	  , ev-exceeded-sas-15min-minor-threshold-remit(129)
	  , ev-exceeded-sas-15min-major-threshold(130)
	  , ev-exceeded-sas-15min-major-threshold-remit(131)
	  , ev-exceeded-uas-15min-minor-threshold(132)
	  , ev-exceeded-uas-15min-minor-threshold-remit(133)
	  , ev-exceeded-uas-15min-major-threshold(134)
	  , ev-exceeded-uas-15min-major-threshold-remit(135)
	  , ev-exceeded-pcv-24hr-minor-threshold(136)
	  , ev-exceeded-pcv-24hr-minor-threshold-remit(137)
	  , ev-exceeded-pcv-24hr-major-threshold(138)
	  , ev-exceeded-pcv-24hr-major-threshold-remit(139)
	  , ev-exceeded-es-24hr-minor-threshold(140)
	  , ev-exceeded-es-24hr-minor-threshold-remit(141)
	  , ev-exceeded-es-24hr-major-threshold(142)
	  , ev-exceeded-es-24hr-major-threshold-remit(143)
	  , ev-exceeded-ses-24hr-minor-threshold(144)
	  , ev-exceeded-ses-24hr-minor-threshold-remit(145)
	  , ev-exceeded-ses-24hr-major-threshold(146)
	  , ev-exceeded-ses-24hr-major-threshold-remit(147)
	  , ev-exceeded-sas-24hr-minor-threshold(148)
	  , ev-exceeded-sas-24hr-minor-threshold-remit(149)
	  , ev-exceeded-sas-24hr-major-threshold(150)
	  , ev-exceeded-sas-24hr-major-threshold-remit(151)
	  , ev-exceeded-uas-24hr-minor-threshold(152)
	  , ev-exceeded-uas-24hr-minor-threshold-remit(153)
	  , ev-exceeded-uas-24hr-major-threshold(154)
	  , ev-exceeded-uas-24hr-major-threshold-remit(155)
	  , ev-net-local-loopback-start(156)
	  , ev-net-local-loopback-end(157)
	  , ev-net-remote-loopback-start(158)
	  , ev-net-remote-loopback-end(159)
	  , ev-net-payload-loopback-start(160)
	  , ev-net-payload-loopback-end(161)
	  , ev-net-BERT-start(162)
	  , ev-net-BERT-end(163)
          , ev-ppp-echo-timeout(164)
          , ev-ppp-echo-timeout-remit(165)
          , ev-ppp-loopback-line(166)
          , ev-ppp-loopback-line-remit(167)
          , ev-ppp-link-fallback(168)
          , ev-ppp-link-fallback-remit(169)
	  , ev-dte-local-loopback-start(170)
	  , ev-dte-local-loopback-end(171)
	  , ev-dte-remote-loopback-start(172)
	  , ev-dte-remote-loopback-end(173)
          , ev-mlppp-link-down(174)
          , ev-mlppp-link-up(175)
	}


-- =============================================================================
-- Unit Level Configuration
-- =============================================================================

unitLevelConfig  OBJECT IDENTIFIER ::= { configuration 1 }

    unitSerialNum OBJECT-TYPE
        SYNTAX  DisplayString (SIZE(0..20))
        ACCESS  read-only
	STATUS	mandatory
	DESCRIPTION
                   "An ID that uniquely and globally identifies the unit.
                   A Serial Number must consist of printable ASCII
                   characters 0x20..0x7E."
	::= { unitLevelConfig 1 }

    unitName  OBJECT-TYPE
	SYNTAX	DisplayString (SIZE (0..20))
	ACCESS	read-write
	STATUS	mandatory
	DESCRIPTION
                "A descriptive name that identifies the DL5400 unit.
		 Use of this parameter is optional, but recommended
		 to aid management."
	::= { unitLevelConfig 2 }

    unitHwRev  OBJECT-TYPE
	SYNTAX	DisplayString (SIZE (1..4))
	ACCESS	read-only
	STATUS	mandatory
	DESCRIPTION
                "The DL5400 hardware revision."
	::= { unitLevelConfig 3 }

    unitSwRev  OBJECT-TYPE
	SYNTAX	DisplayString (SIZE (1..7))
	ACCESS	read-only
	STATUS	mandatory
	DESCRIPTION
                "The DL5400 software revision."
	::= { unitLevelConfig 4 }

    unitMibRev  OBJECT-TYPE
	SYNTAX	DisplayString (SIZE (0..20))
	ACCESS	read-only
	STATUS	mandatory
	DESCRIPTION
                "The DL5400 MIB revision."
	::= { unitLevelConfig 5 }

    unitFrontPnl  OBJECT-TYPE
	SYNTAX	INTEGER {
		    disabled(1),
                    enabled(2)
		}
	ACCESS	read-write
	STATUS	mandatory
	DESCRIPTION
		"This feature enables (ON) or disables (OFF) the users
		 ability to make changes in the configuration or run 
  		 tests from the front panel display and buttons."
        ::= { unitLevelConfig 6 }

    unitDateYear  OBJECT-TYPE
        SYNTAX  TODYear
	ACCESS	read-write
	STATUS	mandatory
	DESCRIPTION
                "The DL5400's date: Year."
        ::= { unitLevelConfig 7 }

    unitDateMonth  OBJECT-TYPE
	SYNTAX	TODMonth
	ACCESS	read-write
	STATUS	mandatory
	DESCRIPTION
                "The DL5400's date: Month."
        ::= { unitLevelConfig 8 }

    unitDateDay  OBJECT-TYPE
	SYNTAX	TODDay
	ACCESS	read-write
	STATUS	mandatory
	DESCRIPTION
                "The DL5400's date: Day."
        ::= { unitLevelConfig 9 }

    unitTimeHour  OBJECT-TYPE
	SYNTAX	TODHour
	ACCESS	read-write
	STATUS	mandatory
	DESCRIPTION
                "The DL5400's time: Hour."
        ::= { unitLevelConfig 10 }

    unitTimeMinute  OBJECT-TYPE
	SYNTAX	TODMinute
	ACCESS	read-write
	STATUS	mandatory
	DESCRIPTION
                "The DL5400's time: Minute."
        ::= { unitLevelConfig 11 }

    unitTimeSecond  OBJECT-TYPE
	SYNTAX	TODSecond
	ACCESS	read-write
	STATUS	mandatory
	DESCRIPTION
                "The DL5400's time: Second."
        ::= { unitLevelConfig 12 }

     unitTimezone OBJECT-TYPE 
        SYNTAX  INTEGER{
				gmtTimezone ( 1),
				g01Timezone ( 2),
				g02Timezone ( 3),
				g03Timezone ( 4),
				g04Timezone ( 5),
				estTimezone ( 6),
				cstTimezone ( 7),
				mstTimezone ( 8),
				pstTimezone ( 9),
				astTimezone (10),
				hstTimezone (11),
				g11Timezone (12),
				g12Timezone (13),
				g13Timezone (14),
				g14Timezone (15),
				g15Timezone (16),
				g16Timezone (17),
				g17Timezone (18),
				g18Timezone (19),
				g19Timezone (20),
				g20Timezone (21),
				g21Timezone (22),
				g22Timezone (23),
				g23Timezone (24)
				}
        ACCESS  read-write
        STATUS  mandatory
        DESCRIPTION 
                " This object is used to indicate the timezone
                associated with the time of day that exists on 
				DL5400 System.
				
				The enumerated values are defined as hours west
				of Greenwhich, for example, g01Timezone represents
				the time zone which is 1 hour west of Greenwhich. " 
 		DEFVAL { gmtTimezone }
        ::= { unitLevelConfig 13 } 

    unitLedStatus  OBJECT-TYPE
	SYNTAX	INTEGER {
                off          (1),
                green        (2),
		blink-Green  (3),
                blink-Amber  (4),
                solid-Amber  (5),
                red          (6),
		blink-Red    (7)
        }
	ACCESS	read-only
	STATUS	mandatory
	DESCRIPTION 
		" The defined values have the following description
		  Off   - The unit is not equipped or is provision in an out of Service state
		  Green - No alarms, status or test conditions exists for the unit
		  Blink Amber  
			- Test conditions are present in the unit
		  Solid Amber  
			- A minor alarm condition persists in the unit or on some 
			  interface of the unit, or the unit is powering up.
		  Red   - An Alarm condition persists in the unit or on some interface of the unit
		  Blink-Green - reserved
		  Blink-Red - reserved
		"
	::= { unitLevelConfig 14 }

    unitTimeStamp OBJECT-TYPE
        SYNTAX  DisplayString (SIZE(1..20))
        ACCESS  read-only
	STATUS	mandatory
	DESCRIPTION
                   "Time Stamp on the unit of format
			MM/DD/YYYY HH:MM:SS
		    This will be sent as a varbind along with all the traps
			to NMS manager"
	::= { unitLevelConfig 15 }

    unitModelType OBJECT-TYPE
    	SYNTAX	INTEGER {
	  ml-pppNxDs1Enet	(1)
	}
	ACCESS	read-only
	STATUS	mandatory
	DESCRIPTION
	  	"The unit model type "
        ::= { unitLevelConfig 16 }

    unitRouteMode OBJECT-TYPE
    	SYNTAX	INTEGER {
		staticIp		(1),
		fastForward		(2)
	}
	ACCESS	read-write
	STATUS	mandatory
	DESCRIPTION
		"Unit Route Mode"
	::= { unitLevelConfig 17 }

--  =========================================================================
--  Telnet Configuration Parameters
--  =========================================================================

unitTelnetConfig  OBJECT IDENTIFIER ::= { configuration 2 }
 
        unitTelnetIdleTimeout OBJECT-TYPE
        SYNTAX  INTEGER
        ACCESS  read-write
        STATUS  mandatory
        DESCRIPTION
                " This object is used to indicate
                number of minutes of inactivity
                required before setting the
                telnet access point to auto-logoff. "
        DEFVAL { 0 }
        ::= {   unitTelnetConfig 1 }

-- =============================================================================
-- DTE Interface Configuration
-- =============================================================================

unitDteEnetCfg  OBJECT IDENTIFIER ::= { configuration 3 }

    dteEnetTable OBJECT-TYPE
    	SYNTAX	SEQUENCE OF DteEnetEntry
	ACCESS	not-accessible
	STATUS	mandatory
	DESCRIPTION
	        "Table of all Dte Ethernet ports in the system "
	::= {unitDteEnetCfg 1}

    dteEnetEntry OBJECT-TYPE
    	SYNTAX	DteEnetEntry
	ACCESS	not-accessible
	STATUS	mandatory
	DESCRIPTION
		"An entry in the dteEnetTable "
	INDEX  { dteEnetIndex }
	::= {dteEnetTable 1}

    DteEnetEntry ::=
        SEQUENCE {
	    dteEnetIndex	INTEGER,
	    dteEnetIpAddress	IpAddress,
	    dteEnetSubnetMask	IpAddress,
	    dteEnetMacAddress	OCTET STRING,
	    dteEnetProtocol	INTEGER,
	    dteEnetOper		INTEGER,
	    dteEnetMode		INTEGER,
	    dteEnetOperStatus	DisplayString,
	    dteEnetModeStatus	DisplayString
	}

	dteEnetIndex OBJECT-TYPE
	SYNTAX	INTEGER {
		dte1	(1)
	}
	ACCESS	read-only
	STATUS	mandatory
	DESCRIPTION
		" The dteEnet port index "
	::= {dteEnetEntry 1}

        dteEnetIpAddress OBJECT-TYPE
	SYNTAX IpAddress
	ACCESS read-write
	STATUS mandatory
	DESCRIPTION
        "IP address assigned to the DTE port of the DL5400."
        ::= {dteEnetEntry 2}

        dteEnetSubnetMask OBJECT-TYPE
	SYNTAX IpAddress
	ACCESS read-write
	STATUS mandatory
	DESCRIPTION
        "IP Subnet mask assigned to the DTE port of the DL5400."
        ::= {dteEnetEntry 3}

        dteEnetMacAddress OBJECT-TYPE
	SYNTAX OCTET STRING (SIZE(6))
	ACCESS read-only
	STATUS mandatory
	DESCRIPTION
		"Ethernet MAC address of this dte port"
        ::= {dteEnetEntry 4}

        dteEnetProtocol OBJECT-TYPE
	SYNTAX INTEGER {
		ethernet	(1),
		ieee8023	(2)
	}
	ACCESS read-write
	STATUS mandatory
	DESCRIPTION
        "Ethernet protocol used by the DL5400. dix is also called Ethernet-II."
        ::= {dteEnetEntry 5}

        dteEnetOper OBJECT-TYPE
	SYNTAX INTEGER {
		autodetect	(1),
		tenMb		(2),
		hundredMb	(3)
	}
	ACCESS read-write
	STATUS mandatory
	DESCRIPTION
        "Ethernet operation used by the DL5400."
        ::= {dteEnetEntry 6}


        dteEnetMode OBJECT-TYPE
	SYNTAX INTEGER {
		autodetect	(1),
		halfduplex	(2),
		fullduplex	(3)
	}
	ACCESS read-write
	STATUS mandatory
	DESCRIPTION
        "Ethernet mode used by the DL5400."
        ::= {dteEnetEntry 7}

        dteEnetOperStatus OBJECT-TYPE
        SYNTAX  DisplayString
	ACCESS read-only
	STATUS mandatory
	DESCRIPTION
		"Ethernet operation status"
        ::= {dteEnetEntry 8}

        dteEnetModeStatus OBJECT-TYPE
        SYNTAX  DisplayString
	ACCESS read-only
	STATUS mandatory
	DESCRIPTION
		"Ethernet Mode status"
        ::= {dteEnetEntry 9}

 
-- =============================================================================
-- Management Port Ethernet Common Configuration. Currently not supported 5-10-00
-- =============================================================================

-- mgmtEnetConfig OBJECT IDENTIFIER ::= { configuration 4 }

--	mgmtEnetIpAddress OBJECT-TYPE
--	SYNTAX IpAddress
--	ACCESS read-write
--	STATUS mandatory
--	DESCRIPTION
--      "IP address assigned to the Management Ethernet port of the DL5400."
--      ::= { mgmtEnetConfig 1 }

--	mgmtEnetSubnetMask OBJECT-TYPE
--	SYNTAX IpAddress
--	ACCESS read-write
--	STATUS mandatory
--	DESCRIPTION
--        "IP Subnet mask assigned to the Management Ethernet port of the DL5400."
--        ::= { mgmtEnetConfig 2 }

--	mgmtEnetDefaultGateway OBJECT-TYPE
--	SYNTAX IpAddress
--	ACCESS read-write
--	STATUS mandatory
--	DESCRIPTION
--        "IP address of the default gateway attached to the DL5400.
--	The default gateway must be on the same Ethernet segment
--        as the Dl5400."
--        ::= { mgmtEnetConfig 3 }

--  mgmtEnetMacAddress OBJECT-TYPE
--	SYNTAX OCTET STRING (SIZE(6))
--	ACCESS read-only
--	STATUS mandatory
--	DESCRIPTION
--        "Ethernet MAC address of the DL5400."
--        ::= { mgmtEnetConfig 4 }

-- =============================================================================
-- Comm1 Configuration
-- =============================================================================

comm1SerialConfig OBJECT IDENTIFIER ::= { configuration 5 }

	comm1SerialPortState OBJECT-TYPE
        SYNTAX  INTEGER{
                disabled     (1),
                enabled      (2)
                }
        ACCESS  read-write
        STATUS  mandatory
        DESCRIPTION
                " This object is used to enable or 
				disable port."
        DEFVAL { enabled }
        ::= {  comm1SerialConfig 1 }

        comm1SerialBaudRate OBJECT-TYPE
	SYNTAX DL5400commBaudRate
	ACCESS read-write
	STATUS mandatory
	DESCRIPTION
        "COMM 1 Baud Rate."
        ::= { comm1SerialConfig 2 }

        comm1SerialBitsPerWord OBJECT-TYPE
	SYNTAX DL5400commNumDataBits 
	ACCESS read-write
	STATUS mandatory
	DESCRIPTION
        "COMM 1 Bits Per Word."
        ::= { comm1SerialConfig 3 }

        comm1SerialStopBits OBJECT-TYPE
	SYNTAX DL5400commStopBits
	ACCESS read-write
	STATUS mandatory
	DESCRIPTION
        "COMM 1 Stop Bits."
        ::= { comm1SerialConfig 4 }

        comm1SerialParity OBJECT-TYPE
	SYNTAX DL5400commParity
	ACCESS read-write
	STATUS mandatory
	DESCRIPTION
        "COMM 1 Parity."
        ::= { comm1SerialConfig 5 }

        comm1SerialFlowControl OBJECT-TYPE
	SYNTAX DL5400commFlowControl
	ACCESS read-write
	STATUS mandatory
	DESCRIPTION
        "COMM 1 Flow Control."
        ::= { comm1SerialConfig 6 }

	comm1SerialLogoutOnLos OBJECT-TYPE
        SYNTAX  INTEGER{
                disabled     (1),
                enabled      (2)
                }
        ACCESS  read-write
        STATUS  mandatory
        DESCRIPTION
                " This object is used to enable or 
				disable auto-logoff on loss of DSR."
        DEFVAL { enabled }
        ::= {  comm1SerialConfig 7 }
 
 	comm1SerialIdleTimeout OBJECT-TYPE
        SYNTAX  INTEGER
        ACCESS  read-write
        STATUS  mandatory 
        DESCRIPTION 
                " This object is used to indicate 
                number of minutes of inactivity 
                required before setting this 
				serial access point to 
				auto-logoff. "
        DEFVAL { 0 }
        ::= {  comm1SerialConfig 8 } 
  

-- =============================================================================
-- Comm2 Configuration
-- =============================================================================

comm2SerialConfig OBJECT IDENTIFIER ::= { configuration 6 }

	comm2SerialPortState OBJECT-TYPE
        SYNTAX  INTEGER{
                disabled     (1),
                enabled      (2)
                }
        ACCESS  read-write
        STATUS  mandatory
        DESCRIPTION
                " This object is used to enable or 
				disable port."
        DEFVAL { enabled }
        ::= {  comm2SerialConfig 1 }

        comm2SerialBaudRate OBJECT-TYPE
	SYNTAX DL5400commBaudRate
	ACCESS read-write
	STATUS mandatory
	DESCRIPTION
        "COMM 2 Baud Rate."
        ::= { comm2SerialConfig 2 }

        comm2SerialBitsPerWord OBJECT-TYPE
	SYNTAX DL5400commNumDataBits
	ACCESS read-write
	STATUS mandatory
	DESCRIPTION
        "COMM 2 Bits Per Word."
        ::= { comm2SerialConfig 3 }

        comm2SerialStopBits OBJECT-TYPE
	SYNTAX DL5400commStopBits
	ACCESS read-write
	STATUS mandatory
	DESCRIPTION
        "COMM 2 Stop Bits."
        ::= { comm2SerialConfig 4 }

        comm2SerialParity OBJECT-TYPE
	SYNTAX DL5400commParity
	ACCESS read-write
	STATUS mandatory
	DESCRIPTION
        "COMM 2 Parity."
        ::= { comm2SerialConfig 5 }

        comm2SerialFlowControl OBJECT-TYPE
	SYNTAX DL5400commFlowControl
	ACCESS read-write
	STATUS mandatory
	DESCRIPTION
        "COMM 2 Flow Control. HwFlowControl option is not applicable
	 for multidrop serial port when in MultiDrop mode"
        ::= { comm2SerialConfig 6 }

	comm2SerialLogoutOnLos OBJECT-TYPE
        SYNTAX  INTEGER{
                disabled     (1),
                enabled      (2)
                }
        ACCESS  read-write
        STATUS  mandatory
        DESCRIPTION
                " This object is used to enable or 
		  disable auto-logoff on loss of DSR."
        DEFVAL { enabled }
        ::= {  comm2SerialConfig 7 }
 
 	comm2SerialIdleTimeout OBJECT-TYPE
        SYNTAX  INTEGER
        ACCESS  read-write
        STATUS  mandatory 
        DESCRIPTION 
                " This object is used to indicate 
                number of minutes of inactivity 
                required before setting this 
			serial access point to 
			auto-logoff. "
        DEFVAL { 0 }
        ::= {  comm2SerialConfig 8 } 
  
	comm2InMDmode	OBJECT-TYPE
	SYNTAX	INTEGER{
		disabled	(1),
		enabled 	(2)
		}
	ACCESS  read-write
	STATUS	mandatory
	DESCRIPTION
		" This object indicates if this serial
		port is in multidrop mode or not. "
	::= { comm2SerialConfig 9 }
  

	comm2InMDId OBJECT-TYPE
        SYNTAX  DisplayString
        ACCESS  read-write
        STATUS  mandatory
        DESCRIPTION
                "Identifies the multidrop session "
        DEFVAL { "0" }
        ::= {  comm2SerialConfig 10 }  

-- =============================================================================
-- NET Configuration
-- =============================================================================

netConfig  OBJECT IDENTIFIER ::= { configuration 7 }

    netPriTxClk OBJECT-TYPE
	SYNTAX	DL5400TxClkSrc	
	ACCESS	read-write
	STATUS	mandatory
	DESCRIPTION
                "The primary transmit clock source for DL5400."
        ::= { netConfig 1 }

    netPriLoopPort OBJECT-TYPE
	SYNTAX	INTEGER	
	ACCESS	read-write
	STATUS	mandatory
	DESCRIPTION
                "The primary loop port clock source for DL5400."
        ::= { netConfig 2 }

    netSecTxClk OBJECT-TYPE
	SYNTAX	DL5400TxClkSrc	
	ACCESS	read-write
	STATUS	mandatory
	DESCRIPTION
                "The secondary transmit clock source for DL5400."
        ::= { netConfig 3 }

    netSecLoopPort OBJECT-TYPE
	SYNTAX	INTEGER	
	ACCESS	read-write
	STATUS	mandatory
	DESCRIPTION
                "The secondary loop port clock source for DL5400."
        ::= { netConfig 4 }
  
     netExtClkFrequency OBJECT-TYPE
	SYNTAX  INTEGER {
		freq8kHZ     (1),
		freq1544kHZ  (2)
	}
	ACCESS  read-write
	STATUS  mandatory
	DESCRIPTION
		"The defined parameters are the external clock frequencies.
		 The user must provision what frequency is to be used"
	::= { netConfig 5 }

     netPriStatus OBJECT-TYPE
        SYNTAX DisplayString
	ACCESS read-only
	STATUS mandatory
	DESCRIPTION
		"Primary clock operation status"
        ::= { netConfig 6 }

     netSecStatus OBJECT-TYPE
        SYNTAX  DisplayString
	ACCESS read-only
	STATUS mandatory
	DESCRIPTION
		"Secondary clock operation status"
        ::= { netConfig 7 }

     netActiveStatus OBJECT-TYPE
        SYNTAX  DisplayString
	ACCESS read-only
	STATUS mandatory
	DESCRIPTION
		"Active clock operation status"
        ::= { netConfig 8 }

     netSuppressYeldet  OBJECT-TYPE
        SYNTAX  INTEGER {
                    suppressYelDet(1),
                    allowYelDet(2)
                }
        ACCESS  read-write
        STATUS  mandatory
        DESCRIPTION
                "This enables or disables the suppression of
                 Yellow Alarm (RAI) detection. Applicable in
		 SF Framing"
        ::= { netConfig 9 }

	netLineType	OBJECT-TYPE
	SYNTAX	INTEGER{
		 t1	(1),
		 e1	(2)
		}
	ACCESS	read-only
	STATUS	mandatory
	DESCRIPTION
		"Tells if this is a T1 or E1 device"
	::= {netConfig 10 }

-- ===========================================================================
-- Network Port Configuration
-- ===========================================================================

netPortTable  OBJECT-TYPE
    SYNTAX      SEQUENCE OF NetPortEntry
    ACCESS      not-accessible
    STATUS      mandatory
    DESCRIPTION
        " Table of all network port in the system. "
    ::= { netConfig 11 }

netPortEntry  OBJECT-TYPE
	SYNTAX NetPortEntry
	ACCESS not-accessible
	STATUS mandatory
	DESCRIPTION
	"An entry in the Net Port Table"
	INDEX { netPortIndex }
	::= { netPortTable 1 }

NetPortEntry ::= 
	SEQUENCE {
            netPortIndex 
                INTEGER,
            netAdmin
                INTEGER,
	    netFramingFormat
	    	INTEGER,
	    netLineCode
	    	INTEGER,
            netLBO
                INTEGER,
            netEGL
                INTEGER,
            netFDL
                INTEGER,
            netSetCode
                INTEGER,
            netClock
                INTEGER,
	    netFrameStatus
		DisplayString,
	    netFrameUpTime
		TimeTicks
       }


     netPortIndex  OBJECT-TYPE
        SYNTAX  INTEGER (1..8)
        ACCESS  read-only
        STATUS  mandatory
        DESCRIPTION
                "The network port index."
        ::= { netPortEntry 1 }

    netAdmin OBJECT-TYPE
        SYNTAX     INTEGER {
                 is(1),
                 oos(2),
                 oos-mt(3)
               }
        ACCESS     read-write
        STATUS     mandatory
	DESCRIPTION
		"Tells the Net DS1 Admin state"
        ::= { netPortEntry  2 }

     netFramingFormat  OBJECT-TYPE
    	SYNTAX  INTEGER {
		 esf    (2),
		 d4	(3)
		}
	ACCESS  read-write
	STATUS  mandatory
	DESCRIPTION
	"This variable describes the Framing Format
	option for the network port."
	::= { netPortEntry 3 }

     netLineCode  OBJECT-TYPE
	SYNTAX  INTEGER {
		 b8zs	(2),
		 ami	(5)
		}
	ACCESS  read-write
	STATUS  mandatory
	DESCRIPTION
	"This variable describes the Line Code
	option for the network port."
	::= { netPortEntry 4 }

     netLBO  OBJECT-TYPE
        SYNTAX  INTEGER {
		    ft0To133   (3),
		    ft133To266 (4),
		    ft266To399 (5),
		    ft399To533 (6),
		    ft533To655 (7),
                    lbo-0dB    (8),
                    lbo-7p5dB  (9),
                    lbo-15dB   (10),
		    lbo-22p5dB (11)
                }
        ACCESS  read-write
        STATUS  mandatory
        DESCRIPTION
                "This selects the line build out value in dBs and
                 applies to CSU/DSU mode only."
        ::= { netPortEntry 5 }

     netEGL  OBJECT-TYPE
        SYNTAX  INTEGER {
                    egl-36dB(1),
                    egl-30dB(2)
                }
        ACCESS  read-write
        STATUS  mandatory
        DESCRIPTION
                "This selects the equalizer gain limit in dBs and
                 applies to CSU mode only."
        ::= { netPortEntry 6 }

     netFDL  OBJECT-TYPE
        SYNTAX  INTEGER {
                    none	(1),
                    ansi	(2),
                    att		(3),
                    both	(4)
                }
        ACCESS  read-write
        STATUS  mandatory
        DESCRIPTION
                "'other' indicates that a protocol  other  than
         	one following is used.
          	'dsx1Ansi-T1-403' refers to the  FDL  exchange
         	recommended by ANSI.
          	'dsx1Att-54016' refers to ESF FDL exchanges.
          	'dsx1Fdl-none' indicates that the device  does
         	not use the FDL."
        ::= { netPortEntry 7 }

     netSetCode  OBJECT-TYPE
        SYNTAX  INTEGER {
                    no (1),
                    yes(2)
                }
        ACCESS  read-write
        STATUS  mandatory
        DESCRIPTION
                "enabled or disabled setCode feature."
        ::= { netPortEntry 8 }

     netClock  OBJECT-TYPE
        SYNTAX  INTEGER {
                    loopTiming(1),
                    sysTiming(3)
                }
        ACCESS  read-write
        STATUS  mandatory
        DESCRIPTION
                "This selects the source of Transmit clock."
        ::= { netPortEntry 9 }

    netFrameStatus OBJECT-TYPE
        SYNTAX  DisplayString
        ACCESS  read-only
        STATUS  mandatory
        DESCRIPTION
		"Framing Operational State."
        ::= { netPortEntry 10 }

    netFrameUpTime	OBJECT-TYPE
	SYNTAX	TimeTicks
	ACCESS	read-only
	STATUS	mandatory
	DESCRIPTION
		"Tells the Framing UpTime."
	::= { netPortEntry 11 }

-- ============================================================================
-- SNMP Configuration items
-- ============================================================================

 unitSnmpConfig OBJECT IDENTIFIER ::= { configuration 8 }

 unitSnmpTrapAddrTable OBJECT-TYPE
 	SYNTAX	SEQUENCE OF UnitSnmpTrapAddrEntry
	ACCESS  not-accessible
	STATUS  mandatory
	DESCRIPTION 
		" A list of IP addresses of the management stations
		  along with information on how to direct a trap to
		  that addresss"
  ::= { unitSnmpConfig 1}

 unitSnmpTrapAddrEntry  OBJECT-TYPE
 	SYNTAX	UnitSnmpTrapAddrEntry
	ACCESS	not-accessible
	STATUS	mandatory
	DESCRIPTION
		"An entry in the Snmp trap address table"
	INDEX	{ unitSnmpTrapHostAddr }
  ::= {unitSnmpTrapAddrTable 1}

  UnitSnmpTrapAddrEntry ::=
  	SEQUENCE {
	  unitSnmpTrapHostAddr 		IpAddress,
	  unitSnmpTrapDirection		INTEGER
	}

  unitSnmpTrapHostAddr OBJECT-TYPE
   SYNTAX IpAddress
   ACCESS read-only
   STATUS mandatory
   DESCRIPTION
    "Specifies the IP address
    of the management station
    to which this unit sends traps."
   ::= { unitSnmpTrapAddrEntry 1 }

  unitSnmpTrapDirection OBJECT-TYPE
   SYNTAX INTEGER {
   	disabled	(1),
   	inBand		(2),
	outBand		(3)
   }
   ACCESS read-only
   STATUS mandatory
   DESCRIPTION
   	"Specifies the way the trap is to be sent to the host"
   ::= { unitSnmpTrapAddrEntry 2 }

  unitSnmpTrapDevState OBJECT-TYPE
   SYNTAX INTEGER {
	forward  (1),
	block    (2)
   }
   ACCESS read-write
   STATUS mandatory
   DESCRIPTION
    "Specifies whether to forward or block SNMP traps on device."
   ::= { unitSnmpConfig 2 }

  unitSnmpTrapCommunity OBJECT-TYPE
   SYNTAX DisplayString
   ACCESS read-write
   STATUS mandatory
   DESCRIPTION
    "Specifies the Community Name
    of the management station
    to which this unit sends traps."
   ::= { unitSnmpConfig 3 }

-- =============================================================================
-- PPP Configuration
-- =============================================================================

unitPPPConfig  OBJECT IDENTIFIER ::= { configuration 9 }

--- PPP Port table, defines objects for PPP port initialization and status information

pppPortTable  OBJECT-TYPE
    SYNTAX      SEQUENCE OF PPPPortEntry
    ACCESS      not-accessible
    STATUS      mandatory
    DESCRIPTION
        " Table of all network ports in the system. "
    ::= { unitPPPConfig 1 }

pppPortEntry  OBJECT-TYPE
	SYNTAX	PPPPortEntry
	ACCESS	not-accessible
	STATUS	mandatory
	DESCRIPTION
		"An entry in the PPP Port table"
	INDEX	{ pppPortIndex }
  ::= {pppPortTable 1}

PPPPortEntry  ::=
	SEQUENCE {
            pppPortIndex 
                INTEGER,
            pppPortInitialMRU
            	INTEGER,
            pppPortMagicNumber
            	INTEGER,
            pppPortFcsSize
            	INTEGER,
	    pppPortRestore
		INTEGER
	}

    pppPortIndex OBJECT-TYPE
    SYNTAX INTEGER{
    	net1	(1),
	net2	(2),
	net3	(3),
	net4	(4),
	net5	(5),
	net6	(6),
	net7	(7),
	net8	(8)
    }
    ACCESS read-only
    STATUS mandatory
    DESCRIPTION
    "Port number of the Net port."
    ::= { pppPortEntry 1 }

    pppPortInitialMRU OBJECT-TYPE
    SYNTAX     INTEGER
    ACCESS     read-write
    STATUS     mandatory
    DESCRIPTION
        "The initial Maximum Receive Unit (MRU) that
         the local PPP entity will advertise to the
         remote entity. If the value of this variable is
         0 then the local PPP entity will not advertise
         any MRU to the remote entity and the default
         MRU will be assumed. Changing this object will
         have effect when the link is next restarted."
    ::= { pppPortEntry  2 }

    pppPortMagicNumber OBJECT-TYPE
    SYNTAX     INTEGER {
                 false(1),
                 true(2)
               }
    ACCESS     read-write
    STATUS     mandatory
    DESCRIPTION
        "If true(2) then the local node will attempt to
         perform Magic Number negotiation with the
         remote node. If false(1) then this negotiation
         is not performed. In any event, the local node
         will comply with any magic number negotiations
         attempted by the remote node, per the PPP
         specification. Changing this object will have
         effect when the link is next restarted."
    ::= { pppPortEntry  3 }

    pppPortFcsSize OBJECT-TYPE
    SYNTAX     INTEGER {
                 size16bits(1),
                 size32bits(2)
               }
    ACCESS     read-write
    STATUS     mandatory
    DESCRIPTION
        "The size of the FCS, in bits, the local node
         will attempt to negotiate for use with the
         remote node. Regardless of the value of this
         object, the local node will comply with any FCS
         size negotiations initiated by the remote node,
         per the PPP specification. Changing this object
         will have effect when the link is next
         restarted."
    ::= { pppPortEntry  4 }

    pppPortRestore  OBJECT-TYPE
    SYNTAX  INTEGER {
           auto 	(1),
           manual 	(2)
            }
    ACCESS  read-write
    STATUS  mandatory
    DESCRIPTION
            "PPP port restore mode, auto or manual."
    ::= { pppPortEntry 5 }

-- =============================================================================
-- ML-PPP Parameters
-- =============================================================================

unitMLPPPConfig  OBJECT IDENTIFIER ::= { unitPPPConfig 2 }

        mlPPPIpAddress OBJECT-TYPE
	SYNTAX IpAddress
	ACCESS read-write
	STATUS mandatory
	DESCRIPTION
        "IP Address assigned to the ML-PPP port of DL5400."
        ::= { unitMLPPPConfig 1 }

        mlPPPSubnetMask OBJECT-TYPE
	SYNTAX IpAddress
	ACCESS read-write
	STATUS mandatory
	DESCRIPTION
        "IP Subnet mask assigned to the ML-PPP link of DL5400."
        ::= { unitMLPPPConfig 2 }

        mlPPPNumberedInterface OBJECT-TYPE
	SYNTAX INTEGER {
     	    disabled	(1),
    	    enabled	(2)
	}
	ACCESS read-write
	STATUS mandatory
	DESCRIPTION
        "Numbered Interface enabled or disabled."
        ::= { unitMLPPPConfig 3 }

        mlPPPMRRU OBJECT-TYPE
	SYNTAX INTEGER
	ACCESS read-write
	STATUS mandatory
	DESCRIPTION
        "Maximum Received Reconstructed Unit of ML-PPP."
        ::= { unitMLPPPConfig 4 }

        mlPPPBundleStatus OBJECT-TYPE
        SYNTAX  DisplayString
        ACCESS  read-only
        STATUS  mandatory
        DESCRIPTION
                "Tells the current bundle status"
        ::= {unitMLPPPConfig 5 }

        mlPPPBundleUpTime OBJECT-TYPE
        SYNTAX  TimeTicks
        ACCESS  read-only
        STATUS  mandatory
        DESCRIPTION
                "The time (in hundredths of a second) since the
                bundle is up."
        ::= { unitMLPPPConfig 6 }

        mlPPPIPCPState OBJECT-TYPE
        SYNTAX  DisplayString
        ACCESS  read-only
        STATUS  mandatory
        DESCRIPTION
                "The current state of IPCP."
        ::= { unitMLPPPConfig 7 }


mlPPPPortTable  OBJECT-TYPE
    SYNTAX      SEQUENCE OF MLPPPPortEntry
    ACCESS      not-accessible
    STATUS      mandatory
    DESCRIPTION
        " Table of all mlppp port in the system. "
    ::= { unitPPPConfig 3 }

mlPPPPortEntry  OBJECT-TYPE
        SYNTAX MLPPPPortEntry
        ACCESS not-accessible
        STATUS mandatory
        DESCRIPTION
        "An entry in the mlppp Port Table"
        INDEX { mlPPPPortIndex }
        ::= { mlPPPPortTable 1 }

MLPPPPortEntry ::=
        SEQUENCE {
            mlPPPPortIndex
                INTEGER,
            mlPPPAdmin
                INTEGER,
            mlPPPStatus
                DisplayString,
            mlPPPUpTime
                TimeTicks,
            mlPPPLCPState
                DisplayString
       }


    mlPPPPortIndex  OBJECT-TYPE
        SYNTAX  INTEGER (1..8)
        ACCESS  read-only
        STATUS  mandatory
        DESCRIPTION
                "The network port index."
        ::= { mlPPPPortEntry 1 }

    mlPPPAdmin OBJECT-TYPE
        SYNTAX     INTEGER {
                 is(1),
                 oos(2),
                 oos-mt(3)
               }
        ACCESS     read-write
        STATUS     mandatory
        DESCRIPTION
                "Tells the MLPPP Admin State."
        ::= { mlPPPPortEntry 2 }

    mlPPPStatus      OBJECT-TYPE
        SYNTAX  DisplayString
        ACCESS  read-only
        STATUS  mandatory
        DESCRIPTION
                "Tells the MLPPP Operational State."
        ::= { mlPPPPortEntry 3 }

    mlPPPUpTime OBJECT-TYPE
        SYNTAX  TimeTicks
        ACCESS  read-only
        STATUS  mandatory
        DESCRIPTION
                "The time (in hundredths of a second) since the
                MLPPP is up."
        ::= { mlPPPPortEntry 4 }

    mlPPPLCPState OBJECT-TYPE
        SYNTAX  DisplayString
        ACCESS  read-only
        STATUS  mandatory
        DESCRIPTION
                "Tells the LCP Operational State."
        ::= { mlPPPPortEntry 5 }


-- =============================================================================
-- Router Configuration
-- =============================================================================

unitRouterConfig  OBJECT IDENTIFIER ::= { configuration 10 }

unitStaticRoutingTable OBJECT-TYPE
    SYNTAX      SEQUENCE OF StaticRoutingEntry
    ACCESS      not-accessible
    STATUS      mandatory
    DESCRIPTION
        " Table of all static routing entries in the system. "
    ::= { unitRouterConfig 1 }

staticRoutingEntry OBJECT-TYPE
    SYNTAX      StaticRoutingEntry
    ACCESS      not-accessible
    STATUS      mandatory
    DESCRIPTION
        " An entry in the static routing table. "
    INDEX { routeDestination }
    ::= { unitStaticRoutingTable 1 }

StaticRoutingEntry ::= 
	SEQUENCE {
            routeDestination 	IpAddress,
            routeNetworkMask 	IpAddress,
            routeNextHopAddress IpAddress,
            routeMetric 	INTEGER,
            routeDirection 	INTEGER,
            routeStatus 	DL5400Validation
         }

    routeDestination OBJECT-TYPE
    SYNTAX IpAddress
    ACCESS read-write
    STATUS mandatory
    DESCRIPTION
    "Destination of the static route."
    ::= { staticRoutingEntry 1 }

    routeNetworkMask OBJECT-TYPE
    SYNTAX IpAddress
    ACCESS read-write
    STATUS mandatory
    DESCRIPTION
    "Network Mask"
    ::= { staticRoutingEntry 2 }

    routeNextHopAddress OBJECT-TYPE
    SYNTAX IpAddress
    ACCESS read-write
    STATUS mandatory
    DESCRIPTION
    "Address of the next hop router. The next hop router 
     must be on the same local network as DL5400"
    ::= { staticRoutingEntry 3 }

    routeMetric OBJECT-TYPE
    SYNTAX INTEGER
    ACCESS read-write
    STATUS mandatory
    DESCRIPTION
    "Number of hops between DL5400 and the destination."
    ::= { staticRoutingEntry 4 }

    routeDirection OBJECT-TYPE
    SYNTAX INTEGER {
		wan(1),
		num(2)
	   }
    ACCESS read-write
    STATUS mandatory
    DESCRIPTION
    "Direction of the Route, Network(NUM) or WAN."
    ::= { staticRoutingEntry 5 }

    routeStatus OBJECT-TYPE
    SYNTAX DL5400Validation
    ACCESS read-write
    STATUS mandatory
    DESCRIPTION
              "Writing invalid has  the  effect  of  deleting
              this interface."
    ::= { staticRoutingEntry 6 }


unitArpConfig  OBJECT IDENTIFIER ::= { configuration 11 }

unitClearArpTable OBJECT-TYPE
    SYNTAX INTEGER {
             true(1)
           }
    ACCESS  read-write
    STATUS  mandatory
    DESCRIPTION
        " Clear all arp entries in the system. "
    ::= { unitArpConfig 1 }

unitArpTable OBJECT-TYPE
    SYNTAX      SEQUENCE OF UnitArpEntry
    ACCESS      not-accessible
    STATUS      mandatory
    DESCRIPTION
        " Table of all arp entries in the system. "
    ::= { unitArpConfig 2 }

unitArpEntry OBJECT-TYPE
    SYNTAX      UnitArpEntry
    ACCESS      not-accessible
    STATUS      mandatory
    DESCRIPTION
        " An entry in the arp table. "
    INDEX { arpEntryNum }
    ::= { unitArpTable 1 }

UnitArpEntry ::=
        SEQUENCE {
            arpEntryNum		INTEGER,
            arpIPAddress    	IpAddress,
            arpMACAddress 	OCTET STRING,
            arpPortNum         	INTEGER
         }

    arpEntryNum OBJECT-TYPE
    SYNTAX INTEGER
    ACCESS read-only
    STATUS mandatory
    DESCRIPTION
    "Entry Number in the arp table."
    ::= { unitArpEntry 1 }

    arpIPAddress OBJECT-TYPE
    SYNTAX IpAddress
    ACCESS read-only
    STATUS mandatory
    DESCRIPTION
    "Entry IpAddress in the arp table."
    ::= { unitArpEntry 2 }

    arpMACAddress OBJECT-TYPE
    SYNTAX OCTET STRING (SIZE(6))
    ACCESS read-only
    STATUS mandatory
    DESCRIPTION
    "Entry MAC address in the arp table."
    ::= { unitArpEntry 3 }

    arpPortNum OBJECT-TYPE
    SYNTAX INTEGER
    ACCESS read-only
    STATUS mandatory
    DESCRIPTION
    "Entry Port Number in the arp table."
    ::= { unitArpEntry 4 }


-- =============================================================================
-- Unit Alarm Status
-- =============================================================================

unitAlarmConfig  OBJECT IDENTIFIER ::= { alarms 1 }

unitAlarmStatusTable OBJECT-TYPE
    SYNTAX      SEQUENCE OF UnitAlarmStatusEntry
    ACCESS	not-accessible
    STATUS	mandatory
    DESCRIPTION
	"The Unit Level alarms and status table."
    ::= { unitAlarmConfig 1 }

unitAlarmStatusEntry OBJECT-TYPE
    SYNTAX      UnitAlarmStatusEntry
    ACCESS	not-accessible
    STATUS	mandatory
    DESCRIPTION
	"An Entry in the unit Alarms Table."
    INDEX	{ unitAlarmIndex }
    ::= { unitAlarmStatusTable 1 }

UnitAlarmStatusEntry ::=
         SEQUENCE {
            unitAlarmIndex 	    INTEGER,
	    unitAlarmSeverity 	    INTEGER,
	    unitAlarmType 	    DL5400Event,
            unitAlarmOriginCardNum  DL5400CardId,
            unitAlarmOriginPortNum  DL5400PortId
	}

    unitAlarmIndex  OBJECT-TYPE
	SYNTAX	INTEGER
	ACCESS	read-only
	STATUS	mandatory
	DESCRIPTION
		"An index value that uniquely identifies a
		 Unit Level alarm entry."
	::= { unitAlarmStatusEntry 1 }

    unitAlarmSeverity  OBJECT-TYPE
	SYNTAX	INTEGER {
 		    status(1),
		    minor(2),
		    major(3)
		}
	ACCESS	read-only
	STATUS	mandatory
	DESCRIPTION
		"This parameter indicates the severity of
		 the alarm, or may indicate that the data is
		 status only."
	::= { unitAlarmStatusEntry 2 }

    unitAlarmType  OBJECT-TYPE
        SYNTAX  DL5400Event
	ACCESS	read-only
	STATUS	mandatory
	DESCRIPTION
		"This parameter is the code for the alarm or
		 status  type.  This code is used to index 
		 into an array of text strings to present a
		 message to the human operator."
	::= { unitAlarmStatusEntry 3 }

    unitAlarmOriginCardNum OBJECT-TYPE
	SYNTAX	DL5400CardId
	ACCESS	read-only
	STATUS	mandatory
	DESCRIPTION
		"The card type of the device
		 originating the event."
        ::= { unitAlarmStatusEntry 4 }


    unitAlarmOriginPortNum OBJECT-TYPE
	SYNTAX	DL5400PortId
	ACCESS	read-only
	STATUS	mandatory
	DESCRIPTION
		"The port number of the device
		 originating the event."
        ::= { unitAlarmStatusEntry 5 }

-- ============================================================================
-- Unit Event History
-- ============================================================================

unitEventTable  OBJECT-TYPE
	SYNTAX	SEQUENCE OF UnitEventEntry
	ACCESS	not-accessible
	STATUS	mandatory
	DESCRIPTION
		"The Unit Level event history table."
	::= { events 1 }

unitEventEntry OBJECT-TYPE
	SYNTAX	UnitEventEntry
	ACCESS	not-accessible
	STATUS	mandatory
	DESCRIPTION
		"An entry in the Unit Level event history table."
	INDEX	{ unitEventIndex }
	::= { unitEventTable 1 }
	
UnitEventEntry ::=
	SEQUENCE {
	    unitEventIndex
		INTEGER,
	    unitEventSeverity
		INTEGER,
	    unitEventHour
		TODHour,
	    unitEventMinute
		TODMinute,
	    unitEventSecond
		TODSecond,
	    unitEventMonth
		TODMonth,
	    unitEventDay
		TODDay,
	    unitEventYear
		TODYear,
	    unitEventOriginCardNum
		DL5400CardId,
	    unitEventOriginPortNum
		DL5400PortId,
	    unitEventType
                DL5400Event
	}

    unitEventIndex OBJECT-TYPE
	SYNTAX	INTEGER
	ACCESS	read-only
	STATUS	mandatory
	DESCRIPTION
		"An index that uniquely identifies a
		 Unit Level event entry."
	::= { unitEventEntry 1 }

    unitEventSeverity OBJECT-TYPE
	SYNTAX	INTEGER {
		    status   (1),
		    minor    (2),
		    major    (3),
                    clear    (4),
                    information    (5)
		}
	ACCESS	read-only
	STATUS	mandatory
	DESCRIPTION
		"This parameter indicates whether an entry
		 is status-only or the severity of an alarm
		 entry."
	::= { unitEventEntry 2 }

    unitEventHour OBJECT-TYPE
	SYNTAX	TODHour
	ACCESS	read-only
	STATUS	mandatory
	DESCRIPTION
		"The hour that the event occurred."
	::= { unitEventEntry 3 }

    unitEventMinute OBJECT-TYPE
	SYNTAX	TODMinute
	ACCESS	read-only
	STATUS	mandatory
	DESCRIPTION
		"The minute that the event occurred."
	::= { unitEventEntry 4 }

    unitEventSecond OBJECT-TYPE
	SYNTAX	TODSecond
	ACCESS	read-only
	STATUS	mandatory
	DESCRIPTION
		"The second that the event occurred."
	::= { unitEventEntry 5 }

    unitEventMonth OBJECT-TYPE
	SYNTAX	TODMonth
	ACCESS	read-only
	STATUS	mandatory
	DESCRIPTION
		"The month that the event occurred."
	::= { unitEventEntry 6 }

    unitEventDay OBJECT-TYPE
	SYNTAX	TODDay
	ACCESS	read-only
	STATUS	mandatory
	DESCRIPTION
		"The day that the event occurred."
	::= { unitEventEntry 7 }

    unitEventYear OBJECT-TYPE
	SYNTAX	TODYear
	ACCESS	read-only
	STATUS	mandatory
	DESCRIPTION
		"The year that the event occurred."
	::= { unitEventEntry 8 }

    unitEventOriginCardNum OBJECT-TYPE
	SYNTAX	DL5400CardId
	ACCESS	read-only
	STATUS	mandatory
	DESCRIPTION
		"The card type of the device
		 originating the event."
        ::= { unitEventEntry 9 }

    unitEventOriginPortNum OBJECT-TYPE
	SYNTAX	DL5400PortId
	ACCESS	read-only
	STATUS	mandatory
	DESCRIPTION
		"The port number of the device
		 originating the event."
        ::= { unitEventEntry 10 }

    unitEventType OBJECT-TYPE
        SYNTAX  DL5400Event
	ACCESS	read-only
	STATUS	mandatory
	DESCRIPTION
		"This parameter is the code for the event
	 	 type.  This code is used to index into an
		 array of text strings to present a message
		 to the human operator."
        ::= { unitEventEntry 11 }

-- ============================================================================
-- STATISTICS
-- ============================================================================

arpStats	OBJECT IDENTIFIER ::= { statistics 1 }

    arpbadLengthField OBJECT-TYPE
	SYNTAX  Counter
	ACCESS  read-only
	STATUS  mandatory
        DESCRIPTION
                "Bad Length Field"
        ::= { arpStats 1 }

    arpunsupportedHardware OBJECT-TYPE
	SYNTAX  Counter
	ACCESS  read-only
	STATUS  mandatory
        DESCRIPTION
                "unsupported Hardware"
        ::= { arpStats 2 }

    arpunsupportedProtocol OBJECT-TYPE
	SYNTAX  Counter
	ACCESS  read-only
	STATUS  mandatory
        DESCRIPTION
                "unsupported Protocol"
        ::= { arpStats 3 }

    arpinvalidSenderAddr OBJECT-TYPE
	SYNTAX  Counter
	ACCESS  read-only
	STATUS  mandatory
        DESCRIPTION
                "total number of packets with invalid sender protocol address"
        ::= { arpStats 4 }

    arpinvalidTargetAddr OBJECT-TYPE
	SYNTAX  Counter
	ACCESS  read-only
	STATUS  mandatory
        DESCRIPTION
                "total number of packets with invalid target protocol address"
        ::= { arpStats 5 }

    arpbadAddress OBJECT-TYPE
	SYNTAX  Counter
	ACCESS  read-only
	STATUS  mandatory
        DESCRIPTION
                "bad address"
        ::= { arpStats 6 }

    arppktsReceived OBJECT-TYPE
	SYNTAX  Counter
	ACCESS  read-only
	STATUS  mandatory
        DESCRIPTION
                "total number of packets recieved"
        ::= { arpStats 7 }

    arpshortPktsReceived OBJECT-TYPE
	SYNTAX  Counter
	ACCESS  read-only
	STATUS  mandatory
        DESCRIPTION
                "total number of short packets recieved"
        ::= { arpStats 8 }

    arppktsFromMeReceived OBJECT-TYPE
	SYNTAX  Counter
	ACCESS  read-only
	STATUS  mandatory
        DESCRIPTION
                "total number of packets from me received"
        ::= { arpStats 9 }

    arpsrcBcstReceived OBJECT-TYPE
	SYNTAX  Counter
	ACCESS  read-only
	STATUS  mandatory
        DESCRIPTION
                "total number of source broadcasts received"
        ::= { arpStats 10 }

    arprepliedSent OBJECT-TYPE
	SYNTAX  Counter
	ACCESS  read-only
	STATUS  mandatory
        DESCRIPTION
                "total number of replies sent"
        ::= { arpStats 11 }

    arpincomingRequests OBJECT-TYPE
	SYNTAX  Counter
	ACCESS  read-only
	STATUS  mandatory
        DESCRIPTION
                "total number of incoming requests"
        ::= { arpStats 12 }

    arprequestSent OBJECT-TYPE
	SYNTAX  Counter
	ACCESS  read-only
	STATUS  mandatory
        DESCRIPTION
                "total number of requests sent"
        ::= { arpStats 13 }

    arpnoMACAddr OBJECT-TYPE
	SYNTAX  Counter
	ACCESS  read-only
	STATUS  mandatory
        DESCRIPTION
                "No MAC address"
        ::= { arpStats 14 }

hdlcStatsTable  OBJECT-TYPE
        SYNTAX  SEQUENCE OF HdlcStatsEntry
        ACCESS  not-accessible
        STATUS  mandatory
        DESCRIPTION
                "The hdlc statistics table."
        ::= { statistics 2 }

hdlcStatsEntry OBJECT-TYPE
        SYNTAX  HdlcStatsEntry
        ACCESS  not-accessible
        STATUS  mandatory
        DESCRIPTION
                "An entry in the Hdlc statistics table."
        INDEX      { hdlcPortIndex }
        ::= { hdlcStatsTable 1 }

HdlcStatsEntry ::=
        SEQUENCE {
            hdlcPortIndex
                INTEGER,
            hdlcLinkStatusBadFCSc
                Counter,
            hdlcFramesAborted
                Counter,
            hdlcFramesNotAligned
                Counter,
            hdlcOctetsRcv
                Counter,
            hdlcPctsRcv
                Counter,
            hdlcOctetsTrsmt
                Counter,
            hdlcPctsTrsmt
                Counter
        }

    hdlcPortIndex OBJECT-TYPE
        SYNTAX  INTEGER
        ACCESS  read-only
        STATUS  mandatory
        DESCRIPTION
                "Port Index"
        ::= { hdlcStatsEntry 1 }

    hdlcLinkStatusBadFCSc OBJECT-TYPE
        SYNTAX  Counter
        ACCESS  read-only
        STATUS  mandatory
        DESCRIPTION
                "Bad FCS"
        ::= { hdlcStatsEntry 2 }

    hdlcFramesAborted OBJECT-TYPE
        SYNTAX  Counter
        ACCESS  read-only
        STATUS  mandatory
        DESCRIPTION
                "Frame aborted"
        ::= { hdlcStatsEntry 3 }

    hdlcFramesNotAligned OBJECT-TYPE
        SYNTAX  Counter
        ACCESS  read-only
        STATUS  mandatory
        DESCRIPTION
                "Frame not aligned"
        ::= { hdlcStatsEntry 4 }

    hdlcOctetsRcv OBJECT-TYPE
        SYNTAX  Counter
        ACCESS  read-only
        STATUS  mandatory
        DESCRIPTION
                "Octets Received"
        ::= { hdlcStatsEntry 5 }

    hdlcPctsRcv OBJECT-TYPE
        SYNTAX  Counter
        ACCESS  read-only
        STATUS  mandatory
        DESCRIPTION
                "Packets Received"
        ::= { hdlcStatsEntry 6 }

    hdlcOctetsTrsmt OBJECT-TYPE
        SYNTAX  Counter
        ACCESS  read-only
        STATUS  mandatory
        DESCRIPTION
                "Octets Transmitted"
        ::= { hdlcStatsEntry 7 }

    hdlcPctsTrsmt OBJECT-TYPE
        SYNTAX  Counter
        ACCESS  read-only
        STATUS  mandatory
        DESCRIPTION
                "Packets Transmitted"
        ::= { hdlcStatsEntry 8 }

miscStats	OBJECT IDENTIFIER ::= { statistics 3 }

    miscprotocolPctsDumped OBJECT-TYPE
	SYNTAX  Counter
	ACCESS  read-only
	STATUS  mandatory
        DESCRIPTION
                "Rx packets with IF error on data Ethernet interface"
        ::= { miscStats 1 }

     miscnonroutablePcts OBJECT-TYPE
	SYNTAX  Counter
	ACCESS  read-only
	STATUS  mandatory
        DESCRIPTION
                "Rx packets non routable on data Ehternet interface"
        ::= { miscStats 2 }

clrStats	OBJECT IDENTIFIER ::= { statistics 4 }

    clearAllStats OBJECT-TYPE
        SYNTAX INTEGER {
                 true(1)
               }
	ACCESS  read-write
	STATUS  mandatory
        DESCRIPTION
                "clear all statistics"
        ::= { clrStats 1 }

    clearCur15Min OBJECT-TYPE
        SYNTAX INTEGER {
                 true(1)
               }
	ACCESS  read-write
	STATUS  mandatory
        DESCRIPTION
                "clear current 15 minutes statistics"
        ::= { clrStats 2 }

    clearCur24Hr OBJECT-TYPE
        SYNTAX INTEGER {
                 true(1)
               }
	ACCESS  read-write
	STATUS  mandatory
        DESCRIPTION
                "clear current 24 hours statistics"
        ::= { clrStats 3 }

    clearOld15Min OBJECT-TYPE
        SYNTAX INTEGER {
                 true(1)
               }
	ACCESS  read-write
	STATUS  mandatory
        DESCRIPTION
                "clear old 15 minutes statistics"
        ::= { clrStats 4 }

    clearOld24Hr OBJECT-TYPE
        SYNTAX INTEGER {
                 true(1)
               }
	ACCESS  read-write
	STATUS  mandatory
        DESCRIPTION
                "clear old 24 hours statistics"
        ::= { clrStats 5 }


-- ============================================================================
-- MAINTENANCE
-- ============================================================================

    maintModTable OBJECT-TYPE
    	SYNTAX	SEQUENCE OF MaintModEntry
	ACCESS	not-accessible
	STATUS	mandatory
	DESCRIPTION
	        "Table of all Module Status in the system "
	::= {maintenance 1}

    maintModEntry OBJECT-TYPE
    	SYNTAX	MaintModEntry
	ACCESS	not-accessible
	STATUS	mandatory
	DESCRIPTION
		"An entry in the maintModTable "
	INDEX  { maintModIndex }
	::= {maintModTable 1}

    MaintModEntry ::=
        SEQUENCE {
	    maintModIndex	INTEGER,
	    maintModStatus	DisplayString,
	    maintOperstatus	DisplayString
	}

	maintModIndex OBJECT-TYPE
	SYNTAX	INTEGER {
		pp	(1),
		ds1	(2),
		enet	(3),
		mpm	(4)
	}
	ACCESS	read-only
	STATUS	mandatory
	DESCRIPTION
		" The module index "
	::= {maintModEntry 1}

        maintModStatus OBJECT-TYPE
	SYNTAX DisplayString 
	ACCESS read-only
	STATUS mandatory
	DESCRIPTION
		"Module actual status"
        ::= {maintModEntry 2}

        maintOperstatus OBJECT-TYPE
	SYNTAX DisplayString 
	ACCESS read-only
	STATUS mandatory
	DESCRIPTION
		"Module Operational status"
        ::= {maintModEntry 3}


-- ===========================================================================
--                       TRAPS FOR DL5400                           
-- ===========================================================================

    dl5400ModulesAppear TRAP-TYPE
        ENTERPRISE dl5400
        VARIABLES { unitEventSeverity , unitTimeStamp }
        DESCRIPTION
                "There is a module appeared in the device."
        ::= 1

    dl5400ModulesDisappear      TRAP-TYPE
        ENTERPRISE dl5400
        VARIABLES { unitEventSeverity , unitTimeStamp }
        DESCRIPTION
                "There is a module disappeared in the device."
        ::= 2

    dl5400SelfTestFail TRAP-TYPE
	ENTERPRISE dl5400
	VARIABLES { unitEventSeverity , unitTimeStamp }
	DESCRIPTION
		"Self Test failed on the unit."
        ::= 11

    dl5400RamTestFail TRAP-TYPE
	ENTERPRISE dl5400
	VARIABLES { unitEventSeverity , unitTimeStamp }
	DESCRIPTION
		"RAM Test failed on the unit."
        ::= 12

    dl5400RomChecksumFail TRAP-TYPE
	ENTERPRISE dl5400
	VARIABLES { unitEventSeverity , unitTimeStamp }
	DESCRIPTION
		"ROM Checksum failed on the unit."
        ::= 13

    dl5400FlashChecksumFail TRAP-TYPE
	ENTERPRISE dl5400
	VARIABLES { unitEventSeverity , unitTimeStamp }
	DESCRIPTION
		"Flash Checksum failed on the unit."
        ::= 14

    dl5400TimeNotSet TRAP-TYPE
	ENTERPRISE dl5400
	VARIABLES { unitEventSeverity , unitTimeStamp }
	DESCRIPTION
		"The Unit's time is not set."
        ::= 15


    dl5400UnitRestart TRAP-TYPE
	ENTERPRISE dl5400
	VARIABLES { unitEventSeverity , unitTimeStamp }
	DESCRIPTION
		"The Unit is resetting."
        ::= 16


    dl5400LampTestStart TRAP-TYPE
	ENTERPRISE dl5400
	VARIABLES { unitEventSeverity , unitTimeStamp }
	DESCRIPTION
		"Lamp Test started."
        ::= 17

    dl5400LampTestEnd TRAP-TYPE
	ENTERPRISE dl5400
	VARIABLES { unitEventSeverity , unitTimeStamp }
	DESCRIPTION
		"Lamp Test terminated."
        ::= 18

    dl5400mgmtPOSTFail TRAP-TYPE
	ENTERPRISE dl5400
	VARIABLES { unitEventSeverity , unitTimeStamp }
	DESCRIPTION
		"Management POST failed."
        ::= 19

    dl5400mgmtPOSTok TRAP-TYPE
	ENTERPRISE dl5400
	VARIABLES { unitEventSeverity , unitTimeStamp }
	DESCRIPTION
		"Management Port OK."
        ::= 20

    dl5400FrontTemperatureHigh TRAP-TYPE
	ENTERPRISE dl5400
	VARIABLES { unitEventSeverity , unitTimeStamp }
	DESCRIPTION
		"The unit's front temperature is high."
        ::= 21

    dl5400FrontTemperatureOK TRAP-TYPE
	ENTERPRISE dl5400
	VARIABLES { unitEventSeverity , unitTimeStamp }
	DESCRIPTION
		"The unit's front temperature is OK."
        ::= 22

    dl5400BackTemperatureHigh TRAP-TYPE
	ENTERPRISE dl5400
	VARIABLES { unitEventSeverity , unitTimeStamp }
	DESCRIPTION
		"The unit's back temperature is high."
        ::= 23

    dl5400BackTemperatureOK TRAP-TYPE
	ENTERPRISE dl5400
	VARIABLES { unitEventSeverity , unitTimeStamp }
	DESCRIPTION
		"The unit's back temperature is OK."
        ::= 24

    dl5400ExternalMajorAlarmStart TRAP-TYPE
	ENTERPRISE dl5400
	VARIABLES { unitEventSeverity, unitTimeStamp }
	DESCRIPTION
		"The external major alarm input is active on the unit."
        ::= 25

    dl5400ExternalMajorAlarmEnd TRAP-TYPE
	ENTERPRISE dl5400
	VARIABLES { unitEventSeverity, unitTimeStamp }
	DESCRIPTION
		"The external major alarm input is de-activated on the unit."
        ::= 26

    dl5400ExternalMinorAlarmStart TRAP-TYPE
	ENTERPRISE dl5400
	VARIABLES { unitEventSeverity, unitTimeStamp }
	DESCRIPTION
		"The external minor alarm input is active on the unit."
        ::= 27

    dl5400ExternalMinorAlarmEnd TRAP-TYPE
	ENTERPRISE dl5400
	VARIABLES { unitEventSeverity, unitTimeStamp }
	DESCRIPTION
		"The external minor alarm input is de-activated on the unit."
        ::= 28

    dl5400ExternalStatusAlarmStart TRAP-TYPE
	ENTERPRISE dl5400
	VARIABLES { unitEventSeverity, unitTimeStamp }
	DESCRIPTION
		"The external status alarm input is active on the unit."
        ::= 29

    dl5400ExternalStatusAlarmEnd TRAP-TYPE
	ENTERPRISE dl5400
	VARIABLES { unitEventSeverity, unitTimeStamp }
	DESCRIPTION
		"The external status alarm input is de-activated on the unit."
        ::= 30

    dl5400PrimaryClockFail TRAP-TYPE
	ENTERPRISE dl5400
	VARIABLES { unitEventSeverity, unitTimeStamp }
	DESCRIPTION
		"Unit's primary clock has failed."
        ::= 31

    dl5400PrimaryClockOk TRAP-TYPE
	ENTERPRISE dl5400
	VARIABLES { unitEventSeverity, unitTimeStamp }
	DESCRIPTION
		"Unit's primary clock is OK."
        ::= 32

    dl5400SecondaryClockFail TRAP-TYPE
	ENTERPRISE dl5400
	VARIABLES { unitEventSeverity, unitTimeStamp }
	DESCRIPTION
		"Unit's Secondary clock has failed."
        ::= 33

    dl5400SecondaryClockOk TRAP-TYPE
	ENTERPRISE dl5400
	VARIABLES { unitEventSeverity, unitTimeStamp }
	DESCRIPTION
		"Unit's Secondary clock is OK."
        ::= 34

    dl5400ExternalClockFail TRAP-TYPE
	ENTERPRISE dl5400
	VARIABLES { unitEventSeverity, unitTimeStamp }
	DESCRIPTION
		"Unit's external clock has failed."
        ::= 35

    dl5400ExternalClockOk TRAP-TYPE
	ENTERPRISE dl5400
	VARIABLES { unitEventSeverity, unitTimeStamp }
	DESCRIPTION
		"Unit's external clock is OK."
        ::= 36

    dl5400Fan1FailAlarm TRAP-TYPE
	ENTERPRISE dl5400
	VARIABLES { unitEventSeverity, unitTimeStamp }
	DESCRIPTION
		"A fan 1 failed on the unit."
        ::= 37

    dl5400Fan1Ok TRAP-TYPE
	ENTERPRISE dl5400
	VARIABLES { unitEventSeverity, unitTimeStamp }
	DESCRIPTION
		"A fan is ok on the unit."
        ::= 38

    dl5400Fan2FailAlarm TRAP-TYPE
	ENTERPRISE dl5400
	VARIABLES { unitEventSeverity, unitTimeStamp }
	DESCRIPTION
		"A fan 2 failed on the unit."
        ::= 39

    dl5400Fan2Ok TRAP-TYPE
	ENTERPRISE dl5400
	VARIABLES { unitEventSeverity, unitTimeStamp }
	DESCRIPTION
		"A fan 2 is ok on the unit."
        ::= 40

    dl5400PSFanFailed TRAP-TYPE
	ENTERPRISE dl5400
	VARIABLES { unitEventSeverity , unitTimeStamp }
	DESCRIPTION
		"Power Supply Fan Failed on the unit."
        ::= 41

    dl5400PSFanOK	TRAP-TYPE
	ENTERPRISE dl5400
	VARIABLES { unitEventSeverity , unitTimeStamp }
	DESCRIPTION
		"Power Supply Fan OK on the unit."
        ::= 42

    dl5400PktProcessorPostFail TRAP-TYPE
	ENTERPRISE dl5400
	VARIABLES { unitEventSeverity , unitTimeStamp }
	DESCRIPTION
		"Packet Processor POST Failed."
        ::= 43

    dl5400PktProcessorPostOk TRAP-TYPE
	ENTERPRISE dl5400
	VARIABLES { unitEventSeverity , unitTimeStamp }
	DESCRIPTION
		"Packet Processor POST  OK."
        ::= 44

    dl5400PacketProcessorMissing TRAP-TYPE
	ENTERPRISE dl5400
	VARIABLES { unitEventSeverity , unitTimeStamp }
	DESCRIPTION
		"Packet Processor Missing."
        ::= 45

    dl5400PacketProcessorOk TRAP-TYPE
	ENTERPRISE dl5400
	VARIABLES { unitEventSeverity , unitTimeStamp }
	DESCRIPTION
		"Packet Processor OK."
        ::= 46

    dl5400VoltageExceeds	TRAP-TYPE
    	ENTERPRISE dl5400
	VARIABLES { unitEventSeverity , unitTimeStamp }
	DESCRIPTION
		"Voltage has exceeded allowed operating voltage range"
	::= 47

    dl5400VoltageOk		TRAP-TYPE
    	ENTERPRISE dl5400
	VARIABLES { unitEventSeverity , unitTimeStamp }
	DESCRIPTION
		"Voltage is within allowed limits"
	::= 48

    dl5400ModuleProcessorFail	 TRAP-TYPE
	ENTERPRISE dl5400
	VARIABLES { unitEventSeverity , unitTimeStamp }
	DESCRIPTION
		"Module Processor Failed"
        ::= 49

    dl5400ModuleProcessorOk TRAP-TYPE
	ENTERPRISE dl5400
	VARIABLES { unitEventSeverity , unitTimeStamp }
	DESCRIPTION
		"Module Processor OK."
        ::= 50

    dl5400ModulesCfgMismatch	TRAP-TYPE
	ENTERPRISE dl5400
	VARIABLES { unitEventSeverity , unitTimeStamp }
	DESCRIPTION
		"There is configuration mismatch between equipped modules."
        ::= 51
    
    dl5400ModulesCfgMatch	TRAP-TYPE
	ENTERPRISE dl5400
	VARIABLES { unitEventSeverity , unitTimeStamp }
	DESCRIPTION
		"There is no configuration mismatch between equipped modules."
        ::= 52
    
    dl5400UsePriClkAlarm TRAP-TYPE
	ENTERPRISE dl5400
	VARIABLES { unitEventSeverity, unitTimeStamp }
	DESCRIPTION
		"Using primary clock source on the unit."
        ::= 53

    dl5400UseSecClkAlarm TRAP-TYPE
	ENTERPRISE dl5400
	VARIABLES { unitEventSeverity, unitTimeStamp }
	DESCRIPTION
		"Using secondary clock source on the unit. Primary clock
 		 source failed on the unit."
        ::= 54

    dl5400UseIntClkAlarm TRAP-TYPE
	ENTERPRISE dl5400
	VARIABLES { unitEventSeverity, unitTimeStamp }
	DESCRIPTION
		"Using internal clock source on the unit. Primary and 
		 secondary clock sources failed on the unit."
        ::= 55

    dl5400UseRxClk1Alarm TRAP-TYPE
	ENTERPRISE dl5400
	VARIABLES { unitEventSeverity, unitTimeStamp }
	DESCRIPTION
		"Receive multiplexer synced to net 1."
        ::= 56

    dl5400UseRxClk2Alarm TRAP-TYPE
	ENTERPRISE dl5400
	VARIABLES { unitEventSeverity, unitTimeStamp }
	DESCRIPTION
		"Receive multiplexer synced to net 2."
        ::= 57

    dl5400UseRxClk3Alarm TRAP-TYPE
	ENTERPRISE dl5400
	VARIABLES { unitEventSeverity, unitTimeStamp }
	DESCRIPTION
		"Receive multiplexer synced to net 3."
        ::= 58

    dl5400UseRxClk4Alarm TRAP-TYPE
	ENTERPRISE dl5400
	VARIABLES { unitEventSeverity, unitTimeStamp }
	DESCRIPTION
		"Receive multiplexer synced to net 4."
        ::= 59

    dl5400UseRxClk5Alarm TRAP-TYPE
	ENTERPRISE dl5400
	VARIABLES { unitEventSeverity, unitTimeStamp }
	DESCRIPTION
		"Receive multiplexer synced to net 5."
        ::= 60

    dl5400UseRxClk6Alarm TRAP-TYPE
	ENTERPRISE dl5400
	VARIABLES { unitEventSeverity, unitTimeStamp }
	DESCRIPTION
		"Receive multiplexer synced to net 6."
        ::= 61

    dl5400UseRxClk7Alarm TRAP-TYPE
	ENTERPRISE dl5400
	VARIABLES { unitEventSeverity, unitTimeStamp }
	DESCRIPTION
		"Receive multiplexer synced to net 7."
        ::= 62

    dl5400UseRxClk8Alarm TRAP-TYPE
	ENTERPRISE dl5400
	VARIABLES { unitEventSeverity, unitTimeStamp }
	DESCRIPTION
		"Receive multiplexer synced to net 8."
        ::= 63

    dl5400MLpppPOSTFail TRAP-TYPE
	ENTERPRISE dl5400
	VARIABLES { unitEventSeverity , unitTimeStamp }
	DESCRIPTION
		"ML-PPP POST failed."
        ::= 64

    dl5400MLpppPOSTok TRAP-TYPE
	ENTERPRISE dl5400
	VARIABLES { unitEventSeverity , unitTimeStamp }
	DESCRIPTION
		"ML-PPP Port OK."
        ::= 65

    dl5400MLpppModuleMissing TRAP-TYPE
	ENTERPRISE dl5400
	VARIABLES { unitEventSeverity , unitTimeStamp }
	DESCRIPTION
		"ML-PPP Module is Missing "
        ::= 66

    dl5400MLpppModuleOK TRAP-TYPE
	ENTERPRISE dl5400
	VARIABLES { unitEventSeverity , unitTimeStamp }
	DESCRIPTION
		"ML-PPP Module is OK "

        ::= 67

    dl5400MLpppInsufficientLinks	TRAP-TYPE
	ENTERPRISE dl5400
	VARIABLES { unitEventSeverity , unitTimeStamp }
	DESCRIPTION
		"ML-PPP Insufficient links reported."
        ::= 68

    dl5400MLpppInsufficientLinksOk 	 TRAP-TYPE
	ENTERPRISE dl5400
	VARIABLES { unitEventSeverity , unitTimeStamp }
	DESCRIPTION
		"Insufficient ML-PPP links alarm remitted."
        ::= 69

    dl5400ModulesFail TRAP-TYPE
        ENTERPRISE dl5400
        VARIABLES { unitEventSeverity , unitTimeStamp }
        DESCRIPTION
                "There is a module failed in the device."
        ::= 70

    dl5400ModulesUp      TRAP-TYPE
        ENTERPRISE dl5400
        VARIABLES { unitEventSeverity , unitTimeStamp }
        DESCRIPTION
                "There is a module up in the device."
        ::= 71

    dl5400LossOfSignalStart TRAP-TYPE
	ENTERPRISE dl5400
	VARIABLES { unitEventOriginPortNum, unitEventSeverity , unitTimeStamp }
	DESCRIPTION
		"Loss of Signal occured on the specified Network port."
        ::= 100

    dl5400LossOfSignalEnd TRAP-TYPE
	ENTERPRISE dl5400
	VARIABLES { unitEventOriginPortNum, unitEventSeverity , unitTimeStamp }
	DESCRIPTION
		"Loss of Signal ended on the specified Network port."
        ::= 101

    dl5400LossOfFrameStart TRAP-TYPE
	ENTERPRISE dl5400
	VARIABLES { unitEventOriginPortNum, unitEventSeverity , unitTimeStamp }
	DESCRIPTION
		"Loss of Frame ended on the specified Network port."
        ::= 102

    dl5400LossOfFrameEnd TRAP-TYPE
	ENTERPRISE dl5400
	VARIABLES { unitEventOriginPortNum, unitEventSeverity , unitTimeStamp }
	DESCRIPTION
		"Loss of Frame ended on the specified Network port."
        ::= 103

    dl5400AisStart TRAP-TYPE
	ENTERPRISE dl5400
	VARIABLES { unitEventOriginPortNum, unitEventSeverity , unitTimeStamp }
	DESCRIPTION
		"AIS Alarm started on the specified Network port."
        ::= 104

    dl5400AisEnd TRAP-TYPE
	ENTERPRISE dl5400
	VARIABLES { unitEventOriginPortNum, unitEventSeverity , unitTimeStamp }
	DESCRIPTION
		"AIS Alarm started on the specified Network port."
        ::= 105

    dl5400RaiStart TRAP-TYPE
	ENTERPRISE dl5400
	VARIABLES { unitEventOriginPortNum, unitEventSeverity , unitTimeStamp }
	DESCRIPTION
		"RAI Alarm(Yellow) received on the specified Network port."
        ::= 106

    dl5400RaiEnd TRAP-TYPE
	ENTERPRISE dl5400
	VARIABLES { unitEventOriginPortNum, unitEventSeverity , unitTimeStamp }
	DESCRIPTION
		"RAI Alarm(Yellow) Ended on the specified Network port."
        ::= 107

    dl5400netLineRemoteLoopbackStart TRAP-TYPE
	ENTERPRISE dl5400
	VARIABLES { unitEventOriginPortNum, unitEventSeverity , unitTimeStamp }
	DESCRIPTION
		"Network Line/Remote Loopback on specified Network port ."
        ::= 158

    dl5400netLineRemoteLoopbackEnd TRAP-TYPE
	ENTERPRISE dl5400
	VARIABLES { unitEventOriginPortNum, unitEventSeverity , unitTimeStamp }
	DESCRIPTION
		"Network Line/Remote Loopback ended on specified Network port ."
        ::= 159

    dl5400pppEchoTimeout TRAP-TYPE
	ENTERPRISE dl5400
	VARIABLES { unitEventOriginPortNum, unitEventSeverity , unitTimeStamp }
	DESCRIPTION
		"PPP Echo Timeout."
        ::= 164

    dl5400pppEchoTimeoutRemit TRAP-TYPE
	ENTERPRISE dl5400
	VARIABLES { unitEventOriginPortNum, unitEventSeverity , unitTimeStamp }
	DESCRIPTION
		"PPP Echo Timeout Alarm Remitted."
        ::= 165

    dl5400pppLineLoopbackStart TRAP-TYPE
	ENTERPRISE dl5400
	VARIABLES { unitEventOriginPortNum, unitEventSeverity , unitTimeStamp }
	DESCRIPTION
		"PPP Line Loopback Start."
        ::= 166

    dl5400pppLineLoopbackEnd TRAP-TYPE
	ENTERPRISE dl5400
	VARIABLES { unitEventOriginPortNum, unitEventSeverity , unitTimeStamp }
	DESCRIPTION
		"PPP Line Loopback End."
        ::= 167

    dl5400pppLinkFallbackStart TRAP-TYPE
	ENTERPRISE dl5400
	VARIABLES { unitEventOriginPortNum, unitEventSeverity , unitTimeStamp }
	DESCRIPTION
		"PPP Link FallbackStart."
        ::= 168

    dl5400pppLinkFallbackEnd TRAP-TYPE
	ENTERPRISE dl5400
	VARIABLES { unitEventOriginPortNum, unitEventSeverity , unitTimeStamp }
	DESCRIPTION
		"PPP Link Fallback End."
        ::= 169

    dl5400dteLocalLoopbackStart TRAP-TYPE
	ENTERPRISE dl5400
	VARIABLES { unitEventOriginPortNum, unitEventSeverity , unitTimeStamp }
	DESCRIPTION
		"Network DTE Local Loopback on specified Network port ."
        ::= 170

    dl5400dteLocalLoopbackEnd TRAP-TYPE
	ENTERPRISE dl5400
	VARIABLES { unitEventOriginPortNum, unitEventSeverity , unitTimeStamp }
	DESCRIPTION
		"Network DTE Local Loopback ended on specified Network port ."
        ::= 171

    dl5400dteRemoteLoopbackStart TRAP-TYPE
	ENTERPRISE dl5400
	VARIABLES { unitEventOriginPortNum, unitEventSeverity , unitTimeStamp }
	DESCRIPTION
		"Network DTE Remote Loopback on specified Network port ."
        ::= 172

    dl5400dteRemoteLoopbackEnd TRAP-TYPE
	ENTERPRISE dl5400
	VARIABLES { unitEventOriginPortNum, unitEventSeverity , unitTimeStamp }
	DESCRIPTION
		"Network DTE Remote Loopback ended on specified Network port ."
        ::= 173

    dl5400MLpppLinkDown	TRAP-TYPE
	ENTERPRISE dl5400
	VARIABLES { unitEventOriginPortNum, unitEventSeverity , unitTimeStamp }
	DESCRIPTION
		"ML-PPP links down caused by ML-PPP Protocol Layer."
        ::= 174

    dl5400MLpppLinkUp 	 TRAP-TYPE
	ENTERPRISE dl5400
	VARIABLES { unitEventOriginPortNum, unitEventSeverity , unitTimeStamp }
	DESCRIPTION
		"ML-PPP links up caused by ML-PPP Protocol Layer."
        ::= 175

END
