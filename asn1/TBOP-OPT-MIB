-- Version 2.15.1.2, modified 2001-10-20 11:28:44-04

        TBOP-OPT-MIB DEFINITIONS ::= BEGIN

        IMPORTS
            Counter, enterprises
                FROM RFC1155-SMI

            OBJECT-TYPE
                FROM RFC-1212;

        -- Codex MIB Group definitions

                  codex OBJECT IDENTIFIER ::= { enterprises 449 }
         cdxProductSpecific OBJECT IDENTIFIER ::= { codex 2 }
                cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

        cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

          cdx6500Controls OBJECT IDENTIFIER ::= { cdx6500 4 }

        -- Textual conventions

        Counter16 ::= INTEGER (0..65535)

        DisplayString ::= OCTET STRING


        -- The TBOP Port Configuration Table

        cdx6500PPCTTBOPPortTable OBJECT-TYPE
            SYNTAX SEQUENCE OF Cdx6500PPCTTBOPPortEntry
            ACCESS not-accessible
            STATUS mandatory
            DESCRIPTION
                "This table contains TBOP Port configuration parameters."
        ::= { cdx6500PCTPortProtocolGroup 7 }

        cdx6500PPCTTBOPPortEntry OBJECT-TYPE
            SYNTAX Cdx6500PPCTTBOPPortEntry
            ACCESS not-accessible
            STATUS mandatory
            DESCRIPTION
                "Each PortEntry contains the configuration
                 parameters for one TBOP port."
            INDEX { cdx6500TBOPCfgPortNumber }
        ::= { cdx6500PPCTTBOPPortTable 1 }

        Cdx6500PPCTTBOPPortEntry ::=
            SEQUENCE {
                cdx6500TBOPCfgPortNumber
                    INTEGER,
                cdx6500TBOPCfgPortEIAOpt
                    INTEGER,
                cdx6500TBOPCfgPortClockType
                    INTEGER,
                cdx6500TBOPCfgPortClockSpeed
                    INTEGER,
                cdx6500TBOPCfgPortTxCoding
                    INTEGER,
                cdx6500TBOPCfgPortByteCount
                    INTEGER,
                cdx6500TBOPCfgPortEIASigAction
                    DisplayString,
                cdx6500TBOPCfgPortOptions
                    INTEGER,
                cdx6500TBOPCfgPortRTSCTSDelay
                    INTEGER,
                cdx6500TBOPCfgPortDcdOnDelay
                    INTEGER,
                cdx6500TBOPCfgPortAutoCallMnem
                    DisplayString,
                cdx6500TBOPCfgPortAutoCallTO
                    INTEGER,
                cdx6500TBOPCfgPortMaxAutoTries
                    INTEGER,
                cdx6500TBOPCfgPortSubAddress
                    DisplayString,
                cdx6500TBOPCfgPortCUG
                    DisplayString,
                cdx6500TBOPCfgPortEnableBill
                    INTEGER,
                cdx6500TBOPCfgDimType
                    INTEGER,
                cdx6500TBOPCfgPortMaxRxQSize
                    INTEGER,
                cdx6500TBOPCfgPortMaxTxQSize
                    INTEGER,
                cdx6500TBOPCfgPortChanT1E1-Conn
                    INTEGER,
                cdx6500TBOPCfgPortIdleFlagCount
                    INTEGER,
                cdx6500TBOPCfgPortElectricalInterfaceType
                    INTEGER,
                cdx6500TBOPCfgPortV24ElectricalInterfaceOption
                    INTEGER,
                cdx6500TBOPCfgPortHighSpeedElectricalInterfaceOption
                    INTEGER,
                cdx6500TBOPCfgPortMaxFrameSize
                    INTEGER
                }
        
        cdx6500TBOPCfgPortNumber OBJECT-TYPE
            SYNTAX INTEGER (1..54)
            ACCESS read-only
            STATUS mandatory
            DESCRIPTION
                "Port number of the port being used by TBOP."
        ::= { cdx6500PPCTTBOPPortEntry 1 }
        
        cdx6500TBOPCfgPortEIAOpt OBJECT-TYPE
            SYNTAX INTEGER {
                    simp       (0),
                    dtr        (1),
                    dtrd       (2),
                    dtrp       (8),
                    newvalSimp (50),
                    nc         (100)
                    }
            ACCESS read-only
            STATUS mandatory
            DESCRIPTION
                "Specifies the control signal handshake and clocking
                 required for a connection to be made to this port
                 legal values are :
                 simp   - Simple, no control signals required.
                 dtr    - Dedicated, require the data terminal ready
                          signal (DTR).
                 dtrd   - Same as DTR, except data set ready (DSR)
                          drops between calls.
                 dtrp  -  Same as DTR, except DSR/DCD/CTS are held
                          low in the idle state.
                 newvalSimp - same functionality as 'simp', new enumeration
                          added for RFC1155 compatibility.
                 nc    -  Parameter not configured."
        ::= { cdx6500PPCTTBOPPortEntry 2 }
        
        cdx6500TBOPCfgPortClockType OBJECT-TYPE
            SYNTAX INTEGER {
                    int       (0),
                    ext       (1),
                    newvalInt (50),
                    nc        (100)
                    }
            ACCESS read-only
            STATUS mandatory
            DESCRIPTION
                "int - internal clock source.
                 ext - external clock source.
                 newval - same functionality as 'int', new enumeration
                       added for RFC1155 compatibility.
                 nc  - parameter not configured."
        ::= { cdx6500PPCTTBOPPortEntry 3 }
        
        cdx6500TBOPCfgPortClockSpeed OBJECT-TYPE
            SYNTAX INTEGER (0..384000)
            ACCESS read-only
            STATUS mandatory
            DESCRIPTION
                "This is the speed of the port in bits per second,
                 Clock Source = int. Legal Range=1200-384000. 
                 A value 0 indicates parameter not configured."
        ::= { cdx6500PPCTTBOPPortEntry 4 }
        
        cdx6500TBOPCfgPortTxCoding OBJECT-TYPE
            SYNTAX INTEGER {
                    nrz       (0),
                    nrzi      (1),
                    newvalNrz (50),
                    nc        (100)
                    }
            ACCESS read-only
            STATUS mandatory
            DESCRIPTION
                "This is the data encoding used on the TBOP port.
                 nrz  - Non Return to Zero.
                 nrzi - Non Return to Zero Inverted.
                 newvalNrz - same functionality as 'nrz', new enumeration
                        added for RFC1155 compatibility.
                 nc   - Parameter not configured."
        ::= { cdx6500PPCTTBOPPortEntry 5 }
        
        cdx6500TBOPCfgPortByteCount OBJECT-TYPE
            SYNTAX INTEGER (0..1045)
            ACCESS read-only
            STATUS mandatory
            DESCRIPTION
                "This is the number of bytes collected from the line
                 before data is forwarded. Legal values are :
                 128, 256, 384, 512, 640, 768, 896, 1036 and 1045.
                 A value 0 indicates the parameter is not configured."
        ::= { cdx6500PPCTTBOPPortEntry 6 }
        
        cdx6500TBOPCfgPortEIASigAction OBJECT-TYPE
            SYNTAX DisplayString (SIZE(3..15))
            ACCESS read-only
            STATUS mandatory
            DESCRIPTION
                "This specifies the EIA signaling actions allowed on
                 the port:
                 NONE   - none
                 SWITCH - switched carrier
                 CTS    - raise CTS in response to RTS
                 A combination of CTS and SWITCH may be specified by summing
                 (e.g. SWITCH+CTS).
                 NC     - Indicates the parameter not configued."
        ::= { cdx6500PPCTTBOPPortEntry 7 }
        
        cdx6500TBOPCfgPortOptions OBJECT-TYPE
            SYNTAX INTEGER {
                    none       (0),  
                    marki      (1),
                    cbr        (2),
                    newvalNone (50),
                    nc         (100)
                    }
            ACCESS read-only
            STATUS mandatory
            DESCRIPTION
                "Select options on this TBOP port as follows:
                 none  - port uses flag idle between frame exchanges and
                         operates with as little as 2 idle flags between
                         frames.   
                 marki - port uses mark idle between frame exchanges.
                         (Required by System 36 - AS/400 series).
                 cbr   - for constant bit rate applications, the port operates
                         with as little as 1 idle flag between frames. Also,
                         if the outbound queue overflows, all frames on this
                         queue will be purged.
                 newvalNone - same functionality as 'none', new enumeration
                         added for RFC1155 compatibility.
                 nc    - parameter not configured."
        ::= { cdx6500PPCTTBOPPortEntry 8 }
        
        cdx6500TBOPCfgPortRTSCTSDelay OBJECT-TYPE
            SYNTAX INTEGER (0..200)
            ACCESS read-only
            STATUS mandatory
            DESCRIPTION
                "This specifies how long the TBOP port will delay CTS
                 after RTS is raised when EIA Signaling Action = CTS.
                 The delay is specified in 50 milliseconds units
                 (1 = 50 milliseconds). Legal Range = 2-200. 
                 A value 0 indicates parameter not configured."
        ::= { cdx6500PPCTTBOPPortEntry 9 }
        
        cdx6500TBOPCfgPortDcdOnDelay OBJECT-TYPE
            SYNTAX INTEGER (0..255)
            ACCESS read-only
            STATUS mandatory
            DESCRIPTION
                "This specifies the length of time that DCD is held
                 high before data is transmitted to the attached
                 device. This is used when EIA Signaling Action = SWITCH.
                 The delay is specified in milliseconds. Legal Range=1-255.
                 A value 0 indicates parameter not configured."
        ::= { cdx6500PPCTTBOPPortEntry 10 }
        
        cdx6500TBOPCfgPortAutoCallMnem OBJECT-TYPE
            SYNTAX DisplayString (SIZE(0..8))
            ACCESS read-only
            STATUS mandatory
            DESCRIPTION
                "This mnemonic name is used for auto calling."
        ::= { cdx6500PPCTTBOPPortEntry 11 }
        
        cdx6500TBOPCfgPortAutoCallTO OBJECT-TYPE
            SYNTAX INTEGER (5..255)
            ACCESS read-only
            STATUS mandatory
            DESCRIPTION
                "This is the time interval in seconds between call
                 attempts when auto calling."
        ::= { cdx6500PPCTTBOPPortEntry 12 }
        
        cdx6500TBOPCfgPortMaxAutoTries OBJECT-TYPE
            SYNTAX INTEGER (0..255)
            ACCESS read-only
            STATUS mandatory
            DESCRIPTION
                "This specifies the number of times the TBOP port will
                 attempt to call. A value of 0 will allow unlimited attempts."
        ::= { cdx6500PPCTTBOPPortEntry 13 }
        
        cdx6500TBOPCfgPortSubAddress OBJECT-TYPE
            SYNTAX DisplayString (SIZE(0..3))
            ACCESS read-only
            STATUS mandatory
            DESCRIPTION
                "Calls addressed to this node, with this subaddress
                 will be routed to this TBOP port."
        ::= { cdx6500PPCTTBOPPortEntry 14 }
        
        cdx6500TBOPCfgPortCUG OBJECT-TYPE
            SYNTAX DisplayString (SIZE(2..23))
            ACCESS read-only
            STATUS mandatory
            DESCRIPTION
                "The TBOP port may be a member of up to 8 different
                 Closed User Groups. Each CUG membership must be a two
                 digit number (except --) and separated by a comma.
                 ( e.g. 12,34,56,09,02,03 ).
                 --    - No CUG Membership
                 00-99 - CUG Membership"
        ::= { cdx6500PPCTTBOPPortEntry 15 }
        
        cdx6500TBOPCfgPortEnableBill OBJECT-TYPE
            SYNTAX INTEGER {
                    off       (0),
                    on        (1),
                    newvalOff (50)
                    }
            ACCESS read-only
            STATUS mandatory
            DESCRIPTION
                "This controls whether billing (accounting) records
                 will be created for calls on this TBOP port.
                 newvalOff - same functionality as 'off', new enumeration
                 added for RFC1155 compatibility."
        ::= { cdx6500PPCTTBOPPortEntry 16 }

        cdx6500TBOPCfgDimType OBJECT-TYPE
            SYNTAX INTEGER {
                    off       (0),
                    on        (1),
                    newvalOff (50)
                    }
            ACCESS read-only
            STATUS mandatory
            DESCRIPTION
                "This controls the Interface Type."
        ::= { cdx6500PPCTTBOPPortEntry 17 }

        cdx6500TBOPCfgPortMaxRxQSize OBJECT-TYPE
            SYNTAX INTEGER (0..501) 
            ACCESS read-only
            STATUS mandatory
            DESCRIPTION
                "This parameter should be used with extreme caution. If using 
                 a non-default value, it is assumed you have discussed your
                 application requirements with the manufacturer's support staff.
                 A non-default value may result in excessive consumption of buffers,
                 which can significantly impair the operation of all traffic over
                 the node. This parameter defines the maximum number of frames which
                 the inbound queue will contain. Frames are placed in this queue
                 when they cannot be forwarded to the network link. If pipelining
                 is enabled, this queue may contain frame segments. Therefore with
                 pipelining enabled, this queue will typicaly contain more entries
                 during network congestion. The default value of zero will result 
                 in a queue size between 32 and 100 depending on available memory.
                 Legal Range=0,16-500. A value 501 indicates parameter not configured."

        ::= { cdx6500PPCTTBOPPortEntry 18 }

        cdx6500TBOPCfgPortMaxTxQSize OBJECT-TYPE
            SYNTAX INTEGER (16..800) 
            ACCESS read-only
            STATUS mandatory
            DESCRIPTION
                "This defines the maximum number of frames which the outbound 
                 queue will contain. These frames are recombined frames, as 
                 they were originaly received by the remote TBOP port."
        ::= { cdx6500PPCTTBOPPortEntry 19 }

        cdx6500TBOPCfgPortChanT1E1-Conn OBJECT-TYPE
            SYNTAX INTEGER {
                    no       (1),  
                    yes      (2),
                    nc       (100)
                    }
            ACCESS read-only
            STATUS mandatory
            DESCRIPTION
                "This specifies whether a frame check sequence is generated for
                 transmitted frames and whether the frame check sequence is
                 stripped from received frames.  It should be set to YES when
                 connecting to a virtual TBOP port which maps to a T1 or E1 port.
                 YES  - Generate FCS for transmitted frames and
                        strip FCS from received frames.
                 NO   - Don't generate FCS for transmitted frames or
                        strip FCS from received frames.
                 NC   - Indicates the parameter not configured."
        ::= { cdx6500PPCTTBOPPortEntry 20 }

        cdx6500TBOPCfgPortIdleFlagCount OBJECT-TYPE
            SYNTAX INTEGER (0..15) 
            ACCESS read-only
            STATUS mandatory
            DESCRIPTION
                "The Minimum number of Idle flags between frames.
                 If MARKi option is used, this should be greater 
                 or equal to 2 and this many number of Idle flags 
                 will be inserted between frames apart from Mark 
                 Flag(FF)s. Legal Range = 1-15. 
                 A value 0 indicates parameter not configured."
        ::= { cdx6500PPCTTBOPPortEntry 21 }

        cdx6500TBOPCfgPortElectricalInterfaceType OBJECT-TYPE
            SYNTAX INTEGER {
                    v24       (1),
                    v35       (2),
                    v36       (3),
                    x21       (4),
                    none      (5)
                    }
            ACCESS read-only
            STATUS mandatory
            DESCRIPTION
                 "Specify the Electrical Interface Type:
                   V.24  - V.24 Electrical Interface Type
                   V.35  - V.35 Electrical Interface Type
                   V.36  - V.36 Electrical Interface Type
                   X.21  - X.21 Electrical Interface Type
                   NONE  - Electrically disabled"
        ::= { cdx6500PPCTTBOPPortEntry 22 }

        cdx6500TBOPCfgPortV24ElectricalInterfaceOption OBJECT-TYPE
            SYNTAX INTEGER {
                    ri        (1),
                    tm        (2)
                    }
            ACCESS read-only
            STATUS mandatory
            DESCRIPTION
                 "Specify the Pin 22 option:
                  RI    - V.24 uses Pin 22 for Ring Indicator output signal
                  TM    - V.24 uses Pin 22 for Test Mode input signal"
        ::= { cdx6500PPCTTBOPPortEntry 23 }

        cdx6500TBOPCfgPortHighSpeedElectricalInterfaceOption OBJECT-TYPE
            SYNTAX INTEGER {
                    none      (1),
                    xover     (2)
                    }
            ACCESS read-only
            STATUS mandatory
            DESCRIPTION
                 "Specify the cable type:
                  NONE  - V.35/V.36/X.21 DCE with straight through cable
                  XOVER - V.35/V.36/X.21 DCE with crossover adapter cable"
        ::= { cdx6500PPCTTBOPPortEntry 24 }

        cdx6500TBOPCfgPortMaxFrameSize OBJECT-TYPE
            SYNTAX INTEGER (0..16384)
            ACCESS read-only
            STATUS mandatory
            DESCRIPTION
                "This defines the maximum frame size which can be received 
                 by TBOP. The frame size is defined as the total number of
                 octets in between flags. This parameter must be programmed 
                 as an even value. Legal Range = 1036-16384. 
                 A value 0 indicates the parameter not configured."
        ::= { cdx6500PPCTTBOPPortEntry 25 }

        -- TBOP Port Statistics

        cdx6500PPSTTBOPPortTable OBJECT-TYPE
            SYNTAX SEQUENCE OF Cdx6500PPSTTBOPPortEntry
            ACCESS not-accessible
            STATUS mandatory
            DESCRIPTION
                "This table holds statistics items for TBOP ports"
        ::= { cdx6500PSTPortProtocolGroup 7 }

        cdx6500PPSTTBOPPortEntry OBJECT-TYPE
            SYNTAX Cdx6500PPSTTBOPPortEntry
            ACCESS not-accessible
            STATUS mandatory
            DESCRIPTION
                "This entry holds the statistics items for one TBOP port."
            INDEX { cdx6500TBOPStPortNumber }
        ::= { cdx6500PPSTTBOPPortTable 1 }
        
        Cdx6500PPSTTBOPPortEntry ::=
            SEQUENCE {
                cdx6500TBOPStPortNumber
                    INTEGER,
                cdx6500TBOPStPortStatus
                    DisplayString,
                cdx6500TBOPStPortState
                    DisplayString,
                cdx6500TBOPStPortSpeed
                    INTEGER,
                cdx6500TBOPStOverrunErrors
                    Counter16,
                cdx6500TBOPStUnderrunErrors
                    Counter16,
                cdx6500TBOPStCRCErrors
                    Counter16,
                cdx6500TBOPStPortRxChars
                    Counter,
                cdx6500TBOPStPortRxCharsSec
                    INTEGER,
                cdx6500TBOPStPortRxFrames
                    Counter,
                cdx6500TBOPStPortRxFramesSec
                    INTEGER,
                cdx6500TBOPStPortTxChars
                    Counter,
                cdx6500TBOPStPortTxCharsSec
                    INTEGER,
                cdx6500TBOPStPortTxFrames
                    Counter,
                cdx6500TBOPStPortTxFramesSec
                    INTEGER,
                cdx6500TBOPStPortRxUtil
                    INTEGER,
                cdx6500TBOPStPortTxUtil
                    INTEGER,
                cdx6500TBOPStPortFramesQueued
                    Counter
                }
        
        cdx6500TBOPStPortNumber OBJECT-TYPE
            SYNTAX INTEGER (1..54)
            ACCESS read-only
            STATUS mandatory
            DESCRIPTION
                "The port number for this TBOP entry."
        ::= { cdx6500PPSTTBOPPortEntry 1 }

        cdx6500TBOPStPortStatus OBJECT-TYPE
            SYNTAX DisplayString (SIZE(2..8))
            ACCESS read-only
            STATUS mandatory
            DESCRIPTION
                "Specifies current port Status.
                 Up       : Port is enabled by the CTP
                 Disabled : Port is disabled by CTP
                 Busy Out : The port is busy out by the CTP
                 Down     : Port is not enabled disables, or busy
                            out by the CTP.
                 Note     : Port Status indicates Down state only if
                            the TBOP port CMEM record entry portEnable
                            gets corrupted. "
        ::= { cdx6500PPSTTBOPPortEntry 2 }

        cdx6500TBOPStPortState OBJECT-TYPE
            SYNTAX DisplayString (SIZE(0..30))
            ACCESS read-only
            STATUS mandatory
            DESCRIPTION
                "The EIA state of the port."
        ::= { cdx6500PPSTTBOPPortEntry 3 }
        
        cdx6500TBOPStPortSpeed OBJECT-TYPE
            SYNTAX INTEGER
            ACCESS read-only
            STATUS mandatory
            DESCRIPTION
                "The measured port speed in bits per second."
        ::= { cdx6500PPSTTBOPPortEntry 4 }        
        
        cdx6500TBOPStOverrunErrors OBJECT-TYPE
            SYNTAX Counter16
            ACCESS read-only
            STATUS mandatory
            DESCRIPTION
                "Total number of overrun errors counted by the I/O driver."
        ::= { cdx6500PPSTTBOPPortEntry 5 }

        cdx6500TBOPStUnderrunErrors OBJECT-TYPE
            SYNTAX Counter16
            ACCESS read-only
            STATUS mandatory
            DESCRIPTION
                "Total number of underrun errors counted by the I/O driver."
        ::= { cdx6500PPSTTBOPPortEntry 6 }

        cdx6500TBOPStCRCErrors OBJECT-TYPE
            SYNTAX Counter16
            ACCESS read-only
            STATUS mandatory
            DESCRIPTION
                "Total number of CRC errors counted by the I/O driver."
        ::= { cdx6500PPSTTBOPPortEntry 7 }

        cdx6500TBOPStPortRxChars OBJECT-TYPE
            SYNTAX Counter
            ACCESS read-only
            STATUS mandatory
            DESCRIPTION
                "Total number of data characters received since last boot
                 or statistics reset, header characters are not included."
        ::= { cdx6500PPSTTBOPPortEntry 8 }
        
        cdx6500TBOPStPortRxCharsSec OBJECT-TYPE
            SYNTAX INTEGER
            ACCESS read-only
            STATUS mandatory
            DESCRIPTION
                "The average number of characters received per second."
        ::= { cdx6500PPSTTBOPPortEntry 9 }
        
        cdx6500TBOPStPortRxFrames OBJECT-TYPE
            SYNTAX Counter
            ACCESS read-only
            STATUS mandatory
            DESCRIPTION
                "Total number of SDLC frames received since last boot
                 or statistices reset."
        ::= { cdx6500PPSTTBOPPortEntry 10 }
        
        cdx6500TBOPStPortRxFramesSec OBJECT-TYPE
            SYNTAX INTEGER
            ACCESS read-only
            STATUS mandatory
            DESCRIPTION
                "The average number of frames received per second."
        ::= { cdx6500PPSTTBOPPortEntry 11 }
        
        cdx6500TBOPStPortTxChars OBJECT-TYPE
            SYNTAX Counter
            ACCESS read-only
            STATUS mandatory
            DESCRIPTION
                "Total number of data characters transmitted since last boot
                 or statistics reset, header characters are not included."
        ::= { cdx6500PPSTTBOPPortEntry 12 }
        
        cdx6500TBOPStPortTxCharsSec OBJECT-TYPE
            SYNTAX INTEGER
            ACCESS read-only
            STATUS mandatory
            DESCRIPTION
                "The average number of characters transmitted per second."
        ::= { cdx6500PPSTTBOPPortEntry 13 }
        
        cdx6500TBOPStPortTxFrames OBJECT-TYPE
            SYNTAX Counter
            ACCESS read-only
            STATUS mandatory
            DESCRIPTION
                "Total number of SDLC frames trnsmitted since last boot or
                 statistics reset."
        ::= { cdx6500PPSTTBOPPortEntry 14 }
        
        cdx6500TBOPStPortTxFramesSec OBJECT-TYPE
            SYNTAX INTEGER
            ACCESS read-only
            STATUS mandatory
            DESCRIPTION
                "The average number of frames transmitted per second."
        ::= { cdx6500PPSTTBOPPortEntry 15 }
        
        cdx6500TBOPStPortRxUtil OBJECT-TYPE
            SYNTAX INTEGER (0..100)
            ACCESS read-only
            STATUS mandatory
            DESCRIPTION
                "Percentage of port receive bandwidth used."
        ::= { cdx6500PPSTTBOPPortEntry 16 }

        cdx6500TBOPStPortTxUtil OBJECT-TYPE
            SYNTAX INTEGER (0..100)
            ACCESS read-only
            STATUS mandatory
            DESCRIPTION
                "Percentage of port transmit bandwidth used."
        ::= { cdx6500PPSTTBOPPortEntry 17 }

        cdx6500TBOPStPortFramesQueued OBJECT-TYPE
            SYNTAX Counter
            ACCESS read-only
            STATUS mandatory
            DESCRIPTION
                "Number of SDLC frames queued to the I/O drivers."
        ::= { cdx6500PPSTTBOPPortEntry 18 }

        END
