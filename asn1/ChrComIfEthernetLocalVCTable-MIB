ChrComIfEthernetLocalVCTable-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfEthernet			FROM  Chromatis-MIB
	RowStatusEnum				FROM  EthernetTypes-MIB;

-- chrComIfEthernetLocalVCTable Table

chrComIfEthernetLocalVCTableTable		OBJECT-TYPE
	SYNTAX		SEQUENCE OF ChrComIfEthernetLocalVCTableEntry
	MAX-ACCESS	not-accessible
	STATUS		current
	DESCRIPTION
	"Associates each active <LVM, Member. LQC> value with the VC it should be Associates each active <LVM, Member. LQC> value with the VC it should be Associates each active <LVM, Member. LQC> value with the VC it should be transmitted on"
	::= { chrComIfEthernet 2}

chrComIfEthernetLocalVCTableEntry		OBJECT-TYPE
	SYNTAX		ChrComIfEthernetLocalVCTableEntry
	MAX-ACCESS	not-accessible
	STATUS		current
	DESCRIPTION
	""
	INDEX  {  chrComIfEthernetEquipIndex, chrComIfEthernetLocalElmIndex, chrComIfEthernetLvmID, chrComIfEthernetPeerMemberID, chrComIfEthernetLQC }

--DEFAULT  get-function-async  MNIL_GetRoutine
--DEFAULT  set-function-async  MNIL_SetRoutine
--DEFAULT  next-function-async MNIL_NextRoutine
--DEFAULT  test-function-async MNIL_TestRoutine
--DEFAULT  cookie "LocalVCTable"
	::= { chrComIfEthernetLocalVCTableTable  1 }

ChrComIfEthernetLocalVCTableEntry  ::=
	SEQUENCE  {
	chrComIfEthernetEquipIndex		Integer32	(0..65535),
	chrComIfEthernetLocalElmIndex		Integer32	(0..1),
	chrComIfEthernetLvmID			Integer32	(0..7),
	chrComIfEthernetPeerMemberID		Unsigned32	(0..27),
	chrComIfEthernetLQC			Integer32	(0..2),
	chrComIfEthernetVCI			Unsigned32	(256..510),
	chrComIfEthernetRowStatus		RowStatusEnum
}

chrComIfEthernetEquipIndex 	OBJECT-TYPE
	SYNTAX		Integer32	(0..65535)
	MAX-ACCESS 	read-write
	STATUS 		current
	DESCRIPTION
	"LocalVcIndex"
	::= { chrComIfEthernetLocalVCTableEntry  1 }

chrComIfEthernetLocalElmIndex 	OBJECT-TYPE
	SYNTAX		Integer32	(0..1)
	MAX-ACCESS 	read-write
	STATUS 		current
	DESCRIPTION
	"ELM index within card (up to 2 ELMs per card; current card has only 1)"
	::= { chrComIfEthernetLocalVCTableEntry  2 }

chrComIfEthernetLvmID 	OBJECT-TYPE
	SYNTAX		Integer32	(0..7)
	MAX-ACCESS 	read-write
	STATUS 		current
	DESCRIPTION
	"ID of LVM within this ELM"
	::= { chrComIfEthernetLocalVCTableEntry  3 }

chrComIfEthernetPeerMemberID 	OBJECT-TYPE
	SYNTAX		Unsigned32	(0..27)
	MAX-ACCESS 	read-write
	STATUS 		current
	DESCRIPTION
	"Member-ID of peer LVM to which this VC is connected"
	::= { chrComIfEthernetLocalVCTableEntry  4 }

chrComIfEthernetLQC 	OBJECT-TYPE
	SYNTAX		Integer32	(0..2)
	MAX-ACCESS 	read-write
	STATUS 		current
	DESCRIPTION
	"Local QoS code for which this VC is used"
	::= { chrComIfEthernetLocalVCTableEntry  5 }

chrComIfEthernetVCI 	OBJECT-TYPE
	SYNTAX		Unsigned32	(256..510)
	MAX-ACCESS 	read-write
	STATUS 		current
	DESCRIPTION
	"VCI used for this VC (it is assumed that VPI=0 is used for all VCs)"
	::= { chrComIfEthernetLocalVCTableEntry  6 }

chrComIfEthernetRowStatus 	OBJECT-TYPE
	SYNTAX		RowStatusEnum
	MAX-ACCESS 	read-write
	STATUS 		current
	DESCRIPTION
	""
	::= { chrComIfEthernetLocalVCTableEntry  7 }


END
