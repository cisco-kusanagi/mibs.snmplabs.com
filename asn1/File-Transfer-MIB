-->#
--># Copyright (C) Siemens AG 1999
-->#               All rights reserved
-->#
-->#protocol specification
-->%PROTOCOL SNMP
-->#
-->#configuration
-->%REMCONFIG NO
-->%REMOPERATION NO
-->#

File-Transfer-MIB DEFINITIONS ::= BEGIN

--
-- Title:   MIB for the File Transfer (openFT) - all versions
-- Date:    15. November 1999
-- Author:  E. Fuehrer, PSE KB D2
-- MIB-Version: 3


IMPORTS
	TRAP-TYPE FROM RFC-1215
        enterprises
            FROM RFC1155-SMI
        DisplayString
            FROM RFC1213-MIB
        OBJECT-TYPE
            FROM RFC-1212;


sni                 OBJECT IDENTIFIER ::= { enterprises 231 }
sniProductMibs      OBJECT IDENTIFIER ::= { sni 2 }
sniFT               OBJECT IDENTIFIER ::= { sniProductMibs 18 }
sniFTStartandStop   OBJECT IDENTIFIER ::= { sniFT 1 }
sniFTSysParam       OBJECT IDENTIFIER ::= { sniFT 2 }
sniFTEncryptKey     OBJECT IDENTIFIER ::= { sniFT 3 }
sniFTStatistics     OBJECT IDENTIFIER ::= { sniFT 4 }
sniFTDiagnostics    OBJECT IDENTIFIER ::= { sniFT 5 }
sniFTTraps          OBJECT IDENTIFIER ::= { sniFT 6 }
sniFTPollInterval   OBJECT IDENTIFIER ::= { sniFT 7 }
sniFTPartners       OBJECT IDENTIFIER ::= { sniFT 8 }
sniFTTrapData       OBJECT IDENTIFIER ::= { sniFT 9 }
sniFTTrapSwitches   OBJECT IDENTIFIER ::= { sniFT 10 }

--
-- FT Start/Stop Management
--

ftStartandStop         OBJECT-TYPE
        SYNTAX  INTEGER
        {
           start     (1),
           stop      (2),
           on        (3),
           off       (4),
           undefined (255)
        }
        ACCESS  read-write
        STATUS  mandatory
        DESCRIPTION "Object is supported in FT-BS2000 and FT-SINIX:
                     Reading: Status of FT STARTED or NOT STARTED;
                     writing: START or TERMINATE Filetransfer"
        ::= {sniFTStartandStop 1}

ftStartandStopFTAM     OBJECT-TYPE
        SYNTAX  INTEGER
        {
           start     (1),
           stop      (2),
           on        (3),
           off       (4),
           not-yet   (5),
           undefined (255)
        }
        ACCESS  read-write
        STATUS  mandatory
        DESCRIPTION "Object is supported only in FT-SINIX:
                     Reading: Status of FTAM - on or off;
                     writing: START or TERMINATE FTAM"
        ::= {sniFTStartandStop 2}


--
-- FT Information and Scheduling Management
--

ftSysparVersion       OBJECT-TYPE
        SYNTAX  DisplayString (SIZE (1..32))
        ACCESS  read-only
        STATUS  mandatory
        DESCRIPTION "Object is supported in FT-BS2000 and FT-SINIX:
                     Type and version of FT-system e.g. FT-BS2000 V5.2A20"
        ::= {sniFTSysParam 1}

ftSysparTransportUnitSize       OBJECT-TYPE
        SYNTAX  INTEGER (128..32767)
        ACCESS  read-write
        STATUS  mandatory
        DESCRIPTION "Object is supported in FT-BS2000 and FT-SINIX:
                     Maximum size of transport unit (in Bytes)"
        ::= {sniFTSysParam 2}

ftSysparTaskLimit               OBJECT-TYPE
        SYNTAX  INTEGER (0..32)
        ACCESS  read-write
        STATUS  mandatory
        DESCRIPTION "Object is supported only in FT-BS2000:
                     Maximum number of tasks that can be reserved
                     simultaneously for the execution of the FT requests"
        ::= {sniFTSysParam 3}

ftSysparConnectionLimit               OBJECT-TYPE
        SYNTAX  INTEGER (1..255)
        ACCESS  read-write
        STATUS  mandatory
        DESCRIPTION "Object is supported only in FT-BS2000:
                     Maximum number of transport connections that can
                     be reserved for the execution of FT requests"
        ::= {sniFTSysParam 4}

ftSysparRequestWaitLevel        OBJECT-TYPE
        SYNTAX  INTEGER (1..2500)
        ACCESS  read-write
        STATUS  mandatory
        DESCRIPTION "Object is supported only in FT-BS2000:
                     Number of waiting requests that must exist before
                     a parallel connection to that remote system is created"
        ::= {sniFTSysParam 5}

ftSysparPartnerCheck            OBJECT-TYPE
        SYNTAX  INTEGER
        {
           std                 (1),
           transport-address   (2)
        }
        ACCESS  read-write
        STATUS  mandatory
        DESCRIPTION "Object is supported only in FT-BS2000:
                     Modification/Display of the extended authentication
                     check"
        ::= {sniFTSysParam 6}

ftSysparMaxOSP                  OBJECT-TYPE
        SYNTAX  INTEGER (0..128)
        ACCESS  read-write
        STATUS  mandatory
        DESCRIPTION "Object is supported only in FT-SINIX:
                     Maximum number of requests issued locally (outbound)
                     that can be processed simultaneously"
        ::= {sniFTSysParam 7}

ftSysparMaxISP                  OBJECT-TYPE
        SYNTAX  INTEGER (0..128)
        ACCESS  read-write
        STATUS  mandatory
        DESCRIPTION "Object is supported only in FT-SINIX:
                     Maximum number of requests issued remotely (inbound)
                     that can be processed simultaneously"
        ::= {sniFTSysParam 8}

ftSysparProcessorName           OBJECT-TYPE
        SYNTAX  DisplayString (SIZE (0..16))
        ACCESS  read-write
        STATUS  mandatory
        DESCRIPTION "Object is supported only in FT-SINIX:
                     Processor name assigned to target system"
        ::= {sniFTSysParam 9}

ftSysparStationName             OBJECT-TYPE
        SYNTAX  DisplayString (SIZE (0..16))
        ACCESS  read-write
        STATUS  mandatory
        DESCRIPTION "Object is supported only in FT-SINIX:
                     Station name assigned to target system"
        ::= {sniFTSysParam 10}

ftSysparCode                    OBJECT-TYPE
        SYNTAX  INTEGER
        {
            iso8859-1  (1),
            iso8859-2  (2),
            iso8859-5  (5),
            iso8859-6  (6),
            iso8859-7  (7),
            iso8859-9  (9),
            undefined  (255)
        }
        ACCESS  read-write
        STATUS  mandatory
        DESCRIPTION "Object is supported only in FT-SINIX:
                     eXtended Host Code Support (XHCS);
                     possible values: ISO8859-i (i = 1,2,5,6,7,9)"
        ::= {sniFTSysParam 11}

ftSysparMaxInboundReqs          OBJECT-TYPE
        SYNTAX  INTEGER (0..1024)
        ACCESS  read-write
        STATUS  mandatory
        DESCRIPTION "Object is supported in FT-BS2000 and FT-SINIX (FTOS-only):
                     Maximum number of inbound requests per partner system"
        ::= {sniFTSysParam 12}

ftSysparMaxLifeTime             OBJECT-TYPE
        SYNTAX  INTEGER (0..400)
        ACCESS  read-write
        STATUS  mandatory
        DESCRIPTION "Object is supported in FT-SINIX (FTOS-only) and FT-BS2000:
                     Maximum lifetime (in days) for requests in the
                     request queue (max. 400 days)
                     BS2000: 0 is the value for unlimited"
        ::= {sniFTSysParam 13}


--
-- FT Public Key Management
--

ftEncryptKey       OBJECT-TYPE
        SYNTAX  INTEGER
        {
           create-new-key   (1)
        }
        ACCESS  read-write
        STATUS  mandatory
        DESCRIPTION "Object is supported in FT-BS2000 and FT-SINIX:
                     Ability to create a new code for encryption"
        ::= {sniFTEncryptKey 1}


--
-- FT Statistic Infos
--

ftStatSuspend       OBJECT-TYPE
        SYNTAX  INTEGER
        ACCESS  read-only
        STATUS  mandatory
        DESCRIPTION "Object is supported only in FT-BS2000:
                     Number of requests that are currently in SUSPEND status"
        ::= {sniFTStatistics 1}

ftStatLocked       OBJECT-TYPE
        SYNTAX  INTEGER
        ACCESS  read-only
        STATUS  mandatory
        DESCRIPTION "Object is supp. in FT-BS2000 and FT-SINIX (FTOS-only):
                     Number of requests that are currently in LOCKED status"
        ::= {sniFTStatistics 2}

ftStatWait       OBJECT-TYPE
        SYNTAX  INTEGER
        ACCESS  read-only
        STATUS  mandatory
        DESCRIPTION "Object is supported in FT-BS2000 and FT-SINIX:
                     Number of requests that are currently in WAIT status"
        ::= {sniFTStatistics 3}

ftStatActive       OBJECT-TYPE
        SYNTAX  INTEGER
        ACCESS  read-only
        STATUS  mandatory
        DESCRIPTION "Object is supported in FT-BS2000 and FT-SINIX:
                     Number of requests that are currently in ACTIVE status"
        ::= {sniFTStatistics 4}

ftStatCanceled       OBJECT-TYPE
        SYNTAX  INTEGER
        ACCESS  read-only
        STATUS  mandatory
        DESCRIPTION "Object is supported in FT-BS2000 and FT-SINIX:
                     Number of reqs that are currently in CANCELED status"
        ::= {sniFTStatistics 5}

ftStatFinished       OBJECT-TYPE
        SYNTAX  INTEGER
        ACCESS  read-only
        STATUS  mandatory
        DESCRIPTION "Object is supp. in FT-BS2000 and FT-SINIX (FTOS-only):
                     Number of reqs that are currently in FINISHED status"
        ::= {sniFTStatistics 6}

ftStatHold       OBJECT-TYPE
        SYNTAX  INTEGER
        ACCESS  read-only
        STATUS  mandatory
        DESCRIPTION "Object is supported in FT-BS2000 and FT-SINIX:
                     Number of requests that are currently in HOLD status"
        ::= {sniFTStatistics 7}

ftStatLocalReqs       OBJECT-TYPE
        SYNTAX  INTEGER
        ACCESS  read-only
        STATUS  mandatory
        DESCRIPTION "Object is supported in FT-BS2000 and FT-SINIX:
                     Number of async. requests issued in the local system,
                     but not yet executed"
        ::= {sniFTStatistics 8}

ftStatRemoteReqs       OBJECT-TYPE
        SYNTAX  INTEGER
        ACCESS  read-only
        STATUS  mandatory
        DESCRIPTION "Object is supported in FT-BS2000 and FT-SINIX:
                     Number of requests issued in the remote system,
                     but not yet executed"
        ::= {sniFTStatistics 9}


--
-- FT Diagnosis Management
--

ftDiagStatus       OBJECT-TYPE
        SYNTAX  INTEGER
        {
      off   (1),
      snn   (2),
      pnn   (3),
      mnn   (4),
      nnn   (5),
      ssn   (6),
      sns   (7),
      sss   (8),
      psn   (9),
      pns   (10),
      pss   (11),
      msn   (12),
      mns   (13),
      mss   (14),
      nsn   (15),
      nns   (16),
      nss   (17),
      on    (18),
      smnn  (19),
      smsn  (20),
      smns  (21),
      smss  (22),
      pmnn  (23),
      pmsn  (24),
      pmns  (25),
      pmss  (26),
      mmnn  (27),
      mmsn  (28),
      mmns  (29),
      mmss  (30),
      undefined (255)
        }
        ACCESS  read-write
        STATUS  mandatory
        DESCRIPTION "Object is supported in FT-BS2000 and FT-SINIX:
                     Switches FT function on or off; abbreviations are:
                     1.pos=ftnea, 2.pos=ftam, 3.pos=session
                     s: standard; n: none; m: minimum; p: partner
                     4-character abbreviations (2nd character m - memory)
                     means ftnea-Trace only in Memory (only FT-BS2000)"
--          possible values are:
--          "off", "snn", "pnn", "mnn", "nnn", "ssn", "sns", "sss", "psn",
--          "pns", "pss", "msn", "mns", "mss", "nsn", "nns", "nss"
--          "smnn", "smsn", "smns", "smss", "smnn", "pmnn", "pmsn", "pmns",
--          "pmss", "mmnn", "mmsn", "mmns", "mmss"
        ::= {sniFTDiagnostics 1}


--
-- FT Trap group
--

ftTrapsSubsystemState           OBJECT-TYPE
        SYNTAX  INTEGER
        {
           off       (1),
           on        (2)
        }
        ACCESS  read-write
        STATUS  mandatory
        DESCRIPTION "Object is supported in FT-BS2000 only:
		     Switch on/off sending of the traps
		     ftSubsystemStartTrap and ftSubsystemStopTrap"
        ::= {sniFTTrapSwitches 1}

ftTrapsFTState                  OBJECT-TYPE
        SYNTAX  INTEGER
        {
           off       (1),
           on        (2)
        }
        ACCESS  read-write
        STATUS  mandatory
        DESCRIPTION "Object is supported in FT-BS2000 only:
		     Switch on/off sending of the traps
		     ftStopTrap and ftStartTrap"
        ::= {sniFTTrapSwitches 2}

ftTrapsPartState                  OBJECT-TYPE
        SYNTAX  INTEGER
        {
           off       (1),
           on        (2)
        }
        ACCESS  read-write
        STATUS  mandatory
        DESCRIPTION "Object is supported in FT-BS2000 only:
		     Switch on/off sending of the trap
		     ftPartnerStateTrap"
        ::= {sniFTTrapSwitches 3}

ftTrapsPartnerUnreachable         OBJECT-TYPE
        SYNTAX  INTEGER
        {
           off       (1),
           on        (2)
        }
        ACCESS  read-write
        STATUS  mandatory
        DESCRIPTION "Object is supported in FT-BS2000 only:
		     Switch on/off sending of the trap
		     ftPartnerUnreachableTrap"
        ::= {sniFTTrapSwitches 4}

ftTrapsRequestQueueState          OBJECT-TYPE
        SYNTAX  INTEGER
        {
           off       (1),
           on        (2)
        }
        ACCESS  read-write
        STATUS  mandatory
        DESCRIPTION "Object is supported in FT-BS2000 only:
		     Switch on/off sending of the traps
		     ftRequestQueueLowerLimitTrap and ftRequestQueueUpperLimitTrap"
        ::= {sniFTTrapSwitches 5}

ftTrapsTransSucc                  OBJECT-TYPE
        SYNTAX  INTEGER
        {
           off       (1),
           on        (2)
        }
        ACCESS  read-write
        STATUS  mandatory
        DESCRIPTION "Object is supported in FT-BS2000 only:
		     Switch on/off sending of the trap
		     ftRequestSuccessfulTrap"
        ::= {sniFTTrapSwitches 6}

ftTrapsTransFail                  OBJECT-TYPE
        SYNTAX  INTEGER
        {
           off       (1),
           on        (2)
        }
        ACCESS  read-write
        STATUS  mandatory
        DESCRIPTION "Object is supported in FT-BS2000 only:
		     Switch on/off sending of the trap
		     ftRequestErrorTrap"
        ::= {sniFTTrapSwitches 7}


ftStopTrap     TRAP-TYPE
        ENTERPRISE sniFTTraps
        DESCRIPTION "Sending a TRAP, if FT has exited/aborted (FT-SINIX and FT-BS2000)"
      ::= 1

ftMaxRequestTrap     TRAP-TYPE
        ENTERPRISE sniFTTraps
        DESCRIPTION "Sending a TRAP, if the maximum number of FT requests
                     is reached (only FT-SINIX)"
      ::= 2

ftErrorLimitTrap     TRAP-TYPE
        ENTERPRISE sniFTTraps
        DESCRIPTION "Sending a TRAP, if the error limit is reached
                     (concerning restarts - only FT-SINIX)"
      ::= 3

ftPartnerStateTrap   TRAP-TYPE
        ENTERPRISE   sniFTTraps
        VARIABLES    { ftPartnerName,
                       ftPartnerState }
        DESCRIPTION "Sending a TRAP, if the Partner changed state (only FT-BS2000)"
      ::= 4

ftPartnerUnreachableTrap   TRAP-TYPE
        ENTERPRISE   sniFTTraps
        VARIABLES    { ftPartnerName }
        DESCRIPTION "Maybe Partner ist unreachable (only FT-BS2000)"
      ::= 5

ftStartTrap     TRAP-TYPE
        ENTERPRISE sniFTTraps
        DESCRIPTION "Sending a TRAP, if FT has been started (only FT-BS2000)"
      ::= 6

ftRequestQueueUpperLimitTrap TRAP-TYPE
        ENTERPRISE   sniFTTraps
        DESCRIPTION "at least 85 percent of Request file full (only FT-BS2000)"
      ::= 7

ftRequestQueueLowerLimitTrap TRAP-TYPE
        ENTERPRISE   sniFTTraps
        DESCRIPTION "at least 20 percent of Request queue unoccupied (only FT-BS2000)"
      ::= 8

ftRequestSuccessfulTrap TRAP-TYPE
        ENTERPRISE   sniFTTraps
        VARIABLES    { ftRequestInitiator,
                       ftRequestID,
                       ftRequestPartnerName,
                       ftRequestUserID,
                       ftRequestFileName }
        DESCRIPTION "Ft-Request was finished successfully (only FT-BS2000)"
      ::= 9

ftRequestErrorTrap TRAP-TYPE
        ENTERPRISE   sniFTTraps
        VARIABLES    { ftRequestInitiator,
                       ftRequestID,
                       ftRequestPartnerName,
                       ftRequestUserID,
                       ftRequestFileName,
                       ftRequestError }
        DESCRIPTION "FT-Request finished with error (only FT-BS2000)"
      ::= 10

ftSubsystemStartTrap     TRAP-TYPE
        ENTERPRISE sniFTTraps
        DESCRIPTION "Sending a TRAP, if Subsystem FT is started (only FT-BS2000)"
      ::= 11

ftSubsystemStopTrap     TRAP-TYPE
        ENTERPRISE sniFTTraps
        DESCRIPTION "Sending a TRAP, if Subsystem FT is stopped (only FT-BS2000)"
      ::= 12


--
-- FT Poll Interval
--

ftPollInterval         OBJECT-TYPE
        SYNTAX  INTEGER
        ACCESS  read-write
        STATUS  mandatory
        DESCRIPTION "Object is supported only in FT-SINIX.
                     The poll interval is the time in minutes between
                     poll actions for verifying whether FT has been 
                     stopped, in order to send an ftStopTrap.
                     The value 0 (zero) means: no polling.
                     Default: 0
                     Reading: Informs poll interval.
                     Writing: Sets poll interval."
        ::= {sniFTPollInterval 1}

--
-- FT Partner Information
--

ftPartnerTable      OBJECT-TYPE
        SYNTAX  SEQUENCE OF FtPartnerEntry
        ACCESS  not-accessible
        STATUS  mandatory
        DESCRIPTION "Table of FT or FTAM-Partners
                     supported in FT-BS2000"
        ::= {sniFTPartners 1}

ftPartnerEntry      OBJECT-TYPE
        SYNTAX  FtPartnerEntry
        ACCESS  not-accessible
        STATUS  mandatory
        DESCRIPTION "Entry describes one FT-(FTAM-)Partner"
        INDEX   {ftPartnerName}
        ::= {ftPartnerTable 1}

FtPartnerEntry ::=
        SEQUENCE {
            ftPartnerName
                DisplayString (SIZE (1..8)),

            ftPartnerType
                INTEGER,

            ftPartnerState
                INTEGER,

            ftPartnerNetworkAddr
                DisplayString (SIZE (1..8)),

            ftPartnerTransportSel
                DisplayString (SIZE (1..19)),

            ftPartnerSessionSel
                DisplayString (SIZE (1..35)),

            ftPartnerPresentationSel
                DisplayString (SIZE (1..35))
        }

ftPartnerName       OBJECT-TYPE
        SYNTAX  DisplayString (SIZE (1..8))
        ACCESS  read-only
        STATUS  mandatory
        DESCRIPTION "Object is supported in FT-BS2000:
                     Name of FT-Partner"
        ::= {ftPartnerEntry 1}

ftPartnerType       OBJECT-TYPE
        SYNTAX  INTEGER
        {
           openft    (1),
           ftam      (2)
        }
        ACCESS  read-only
        STATUS  mandatory
        DESCRIPTION "Object is supported in FT-BS2000:
                     Partner to be reached with openFT / FTAM - Protocol"
        ::= {ftPartnerEntry 2}

ftPartnerState       OBJECT-TYPE
        SYNTAX  INTEGER
        {
           act       (1),
           inact     (2),
           nocon     (3),
           lunk      (4),
           runk      (5),
           adeact    (6),
           ainact    (7)
        }
        ACCESS  read-write
        STATUS  mandatory
        DESCRIPTION "Object is supported in FT-BS2000:
                     Status of FT-Partner
                     READ: Status ACT - AINACT, WRITE: Status ACT, DEACT, ADEAC"
        ::= {ftPartnerEntry 3}

ftPartnerNetworkAddr    OBJECT-TYPE
        SYNTAX  DisplayString (SIZE (1..8))
        ACCESS  read-only
        STATUS  mandatory
        DESCRIPTION "Object is supported in FT-BS2000:
                     Layer 3 Address of Partner"
        ::= {ftPartnerEntry 4}

ftPartnerTransportSel   OBJECT-TYPE
        SYNTAX  DisplayString (SIZE (1..19))
        ACCESS  read-only
        STATUS  mandatory
        DESCRIPTION "Object is supported in FT-BS2000:
                     Layer 4 Address of Partner"
        ::= {ftPartnerEntry 5}

ftPartnerSessionSel     OBJECT-TYPE
        SYNTAX  DisplayString (SIZE (1..35))
        ACCESS  read-only
        STATUS  mandatory
        DESCRIPTION "Object is supported in FT-BS2000:
                     Layer 5 Address of Partner"
        ::= {ftPartnerEntry 6}

ftPartnerPresentationSel  OBJECT-TYPE
        SYNTAX  DisplayString (SIZE (1..35))
        ACCESS  read-only
        STATUS  mandatory
        DESCRIPTION "Object is supported in FT-BS2000:
                     Layer 6 Address of Partner"
        ::= {ftPartnerEntry 7}


--
-- FT Trap Informations
--

ftRequestID               OBJECT-TYPE
        SYNTAX  INTEGER
        ACCESS  not-accessible
        STATUS  mandatory
        DESCRIPTION "Transfer ID of FT-Request (only FT-BS2000)"
        ::= {sniFTTrapData 1}

ftRequestInitiator        OBJECT-TYPE
        SYNTAX  INTEGER
        {
           local     (1),
           remote    (2)
        }
        ACCESS  not-accessible
        STATUS  mandatory
        DESCRIPTION "Initiator of FT-Request (only FT-BS2000)"
        ::= {sniFTTrapData 2}

ftRequestPartnerName      OBJECT-TYPE
        SYNTAX  DisplayString (SIZE (1..8))
        ACCESS  not-accessible
        STATUS  mandatory
        DESCRIPTION "Partner of FT-Request (only FT-BS2000)"
        ::= {sniFTTrapData 3}

ftRequestUserID           OBJECT-TYPE
        SYNTAX  DisplayString (SIZE (1..8))
        ACCESS  not-accessible
        STATUS  mandatory
        DESCRIPTION "UserID of FT-Request (only FT-BS2000)"
        ::= {sniFTTrapData 4}

ftRequestFileName         OBJECT-TYPE
        SYNTAX  DisplayString (SIZE (1..221))
        ACCESS  not-accessible
        STATUS  mandatory
        DESCRIPTION "name of transferred File (only FT-BS2000)"
        ::= {sniFTTrapData 5}

ftRequestError         OBJECT-TYPE
        SYNTAX  DisplayString (SIZE (1..7))
        ACCESS  not-accessible
        STATUS  mandatory
        DESCRIPTION "Error in Request (only FT-BS2000)"
        ::= {sniFTTrapData 6}


END
