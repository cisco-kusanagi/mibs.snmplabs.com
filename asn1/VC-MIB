VC-MIB DEFINITIONS ::= BEGIN

-- Allot communication V4.1 MIB
-- January 16, 2001

 
IMPORTS
    neStatistics		FROM NE-STAT-MIB
    OBJECT-TYPE		        FROM RFC-1212
    Counter		 	FROM RFC1155-SMI
    DisplayString               FROM SNMPv2-TC;
    

vcStatMIB OBJECT IDENTIFIER ::= { neStatistics 3 }
vcStat    OBJECT IDENTIFIER ::= { vcStatMIB 1 }

--vc statistic

vcStatTable OBJECT-TYPE
      SYNTAX  SEQUENCE OF VcEntry
      ACCESS  not-accessible
      STATUS  mandatory
      DESCRIPTION
         "A list of vc entries."
      ::= { vcStat 1 }

vcEntry OBJECT-TYPE
      SYNTAX  VcEntry
      ACCESS  not-accessible
      STATUS  mandatory
      DESCRIPTION
         "A vc entry contains statistical objects for one vc."
      INDEX   { vcPipePosition,
                vcPipeInstancePosition,
                vcPosition,
                vcInstancePosition }
      ::= { vcStatTable 1 }

VcEntry ::= SEQUENCE {
        vcPipePosition                                  INTEGER,
        vcPipeInstancePosition                          INTEGER,
        vcPosition                                      INTEGER,
        vcInstancePosition                              INTEGER,
        
        vcName                                          DisplayString,
        
        vcByteCountIn                                   Counter,
        vcByteCountOut                                  Counter,
	vcByteCountTotal                                Counter,
 	vcLiveConnections                               Counter,
	vcNewConnections                                Counter,
	vcPacketsIn                                     Counter,
	vcPacketsOut                                    Counter,
	vcPacketsTotal                                  Counter
       	
	}

vcPipePosition      OBJECT-TYPE
    SYNTAX      INTEGER
    ACCESS  read-only
    STATUS      mandatory
    DESCRIPTION
        "Position of pipe in table"
    ::= { vcEntry 1 }
      
vcPipeInstancePosition      OBJECT-TYPE
    SYNTAX      INTEGER
    ACCESS  read-only
    STATUS      mandatory
    DESCRIPTION
        "Position of pipe instance in group"
    ::= { vcEntry 2 }
      
vcPosition      OBJECT-TYPE
    SYNTAX      INTEGER
    ACCESS  read-only
    STATUS      mandatory
    DESCRIPTION
        "Position of VC in pipe"
    ::= { vcEntry 3 }
      
vcInstancePosition      OBJECT-TYPE
    SYNTAX      INTEGER
    ACCESS  read-only
    STATUS      mandatory
    DESCRIPTION
        "Position of VC instance in group"
    ::= { vcEntry 4 }
       
vcName          OBJECT-TYPE
    SYNTAX      DisplayString
    ACCESS  read-only
    STATUS      mandatory
    DESCRIPTION
        "vc name"
    ::= { vcEntry 5 }

vcByteCountIn   OBJECT-TYPE
    SYNTAX      Counter
    ACCESS  read-only
    STATUS      mandatory
    DESCRIPTION
        "Bytes in per vc"
    ::= { vcEntry 6 }

vcByteCountOut   OBJECT-TYPE
    SYNTAX      Counter
    ACCESS  read-only
    STATUS      mandatory
    DESCRIPTION
        "Bytes out per vc"
    ::= { vcEntry 7 }

vcByteCountTotal   OBJECT-TYPE
    SYNTAX      Counter
    ACCESS  read-only
    STATUS      mandatory
    DESCRIPTION
        "Total Bytes per vc"
    ::= { vcEntry 8 }

vcLiveConnections   OBJECT-TYPE
    SYNTAX      Counter
    ACCESS  read-only
    STATUS      mandatory
    DESCRIPTION
        "Live Connections per vc"
    ::= { vcEntry 9 }

vcNewConnections   OBJECT-TYPE
    SYNTAX      Counter
    ACCESS  read-only
    STATUS      mandatory
    DESCRIPTION
        "New Connections per vc"
    ::= { vcEntry 10 }

vcPacketsIn   OBJECT-TYPE
    SYNTAX      Counter
    ACCESS  read-only
    STATUS      mandatory
    DESCRIPTION
        "Packets in per vc"
    ::= { vcEntry 11 }

vcPacketsOut   OBJECT-TYPE
    SYNTAX      Counter
    ACCESS  read-only
    STATUS      mandatory
    DESCRIPTION
        "Packets out per vc"
    ::= { vcEntry 12 }

vcPacketsTotal   OBJECT-TYPE
    SYNTAX      Counter
    ACCESS  read-only
    STATUS      mandatory
    DESCRIPTION
        "Total Packets per vc"
    ::= { vcEntry 13 }

	    

END
