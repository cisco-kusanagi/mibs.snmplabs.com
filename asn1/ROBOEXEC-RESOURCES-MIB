ROBOEXEC-RESOURCES-MIB DEFINITIONS ::= BEGIN
   IMPORTS
      OBJECT-TYPE, NOTIFICATION-TYPE, MODULE-IDENTITY, OBJECT-IDENTITY,
	  Counter32, Integer32
            FROM SNMPv2-SMI
	  common, UsrConfigStatus
            FROM USR-DEFINITIONS-MIB
      DisplayString, DateAndTime
            FROM SNMPv2-TC;
    roboExec MODULE-IDENTITY
         LAST-UPDATED "200208231355Z"
         ORGANIZATION "CommWorks Corporation, a 3Com Company"
         CONTACT-INFO "Customer Support"
         DESCRIPTION
                 "The commWorks enterprise defined MIB objects
                   for the RoboExec"
--      REVISION "200208231355Z"
--      DESCRIPTION "CLarified usage and labels for usrreMemoryTrapStatus."
--      REVISION "200205052006Z"
--      DESCRIPTION "Converted to SNMPv2"
         ::= { common 3 }
   usrreSystem		  OBJECT IDENTIFIER ::= { roboExec 1 }
   usrreSWRun		  OBJECT IDENTIFIER ::= { roboExec 2 }
   usrreEvents		  OBJECT IDENTIFIER ::= { roboExec 3 }
   usrreCounters	  OBJECT IDENTIFIER ::= { roboExec 5 }
   usrreNames		  OBJECT IDENTIFIER ::= { roboExec 6 }
   usrreFiles		  OBJECT IDENTIFIER ::= { roboExec 7 }
   usrreMemTrapSettings   OBJECT IDENTIFIER ::= { roboExec 8 }
   usrreTraps             OBJECT IDENTIFIER ::= { roboExec 9 }
   -- textual conventions
   -- memory size, expressed in units of 1024bytes
   KBytes ::=	  Integer32 (0..2147483647)
   -- The RoboExec Resources System Group
   --
   -- Implementation of this group is mandatory for all RoboExec systems.
   usrreSystemDate OBJECT-TYPE
	  SYNTAX DateAndTime
	  MAX-ACCESS read-write
	  STATUS current
	  DESCRIPTION
		    "The RoboExec's notion of the local date and time of
		    day."
	  ::= { usrreSystem 1 }
   usrreMemorySize OBJECT-TYPE
	  SYNTAX KBytes
	  MAX-ACCESS read-only
	  STATUS current
	  DESCRIPTION
		    "The amount of physical main memory maintained by
		    the RoboExec."
	  ::= { usrreSystem 2 }
   usrreFreeMemorySize OBJECT-TYPE
	  SYNTAX KBytes
	  MAX-ACCESS read-only
	  STATUS current
	  DESCRIPTION
		    "The amount of free physical main memory maintained by
		    the RoboExec."
	  ::= { usrreSystem 3 }
   usrreTextSize OBJECT-TYPE
	  SYNTAX KBytes
	  MAX-ACCESS read-only
	  STATUS current
	  DESCRIPTION
		    "The number of Kbytes of text (code) in the executable."
	  ::= { usrreSystem 4 }
   usrreInitDataSize OBJECT-TYPE
	  SYNTAX KBytes
	  MAX-ACCESS read-only
	  STATUS current
	  DESCRIPTION
		    "The number of Kbytes of initialized data in the executable."
	  ::= { usrreSystem 5 }
   usrreUninitDataSize OBJECT-TYPE
	  SYNTAX KBytes
	  MAX-ACCESS read-only
	  STATUS current
	  DESCRIPTION
		    "The number of Kbytes of uninitialized data in the executable."
	  ::= { usrreSystem 6 }
   usrreStackSize OBJECT-TYPE
	  SYNTAX KBytes
	  MAX-ACCESS read-only
	  STATUS current
	  DESCRIPTION
		    "The size of the stack in Kbytes provided for the executable."
	  ::= { usrreSystem 7 }
   usrreMaxHeapAllocated OBJECT-TYPE
	  SYNTAX KBytes
	  MAX-ACCESS read-only
	  STATUS current
	  DESCRIPTION
		    "The maximum amount of memory ever allocated from the
		    RoboExec heap."
	  ::= { usrreSystem 8 }
   usrreLargestMemoryBlockAddress OBJECT-TYPE
       SYNTAX DisplayString
       MAX-ACCESS read-only
       STATUS current
       DESCRIPTION
              "The address of the largest memory block ever
               allocated from heap."
       ::= { usrreSystem 9 }
      usrreLargestMemoryBlockSize OBJECT-TYPE
       SYNTAX KBytes
       MAX-ACCESS read-only
       STATUS current
       DESCRIPTION
              "The size (in kilobytes) of the largest memory block ever 
               allocated from heap."
       ::= { usrreSystem 10 }
      usrreLargestMemoryBlockCorrelator OBJECT-TYPE
       SYNTAX DisplayString
       MAX-ACCESS read-only
       STATUS current
       DESCRIPTION
              "An ASCII string indicating what process allocated 
               the largest memory block from heap."
       ::= { usrreSystem 11 }
      usrreLargestMemoryBlockState OBJECT-TYPE
       SYNTAX INTEGER {
                free(0),             -- Memory block was freed for further reuse
                allocated(1)  
            }       
       MAX-ACCESS read-only
       STATUS current
       DESCRIPTION
              "The state of the largest memory block:
                        0 - was freed for further reuse;
                        1 - is allocated."
       ::= { usrreSystem 12 }
      usrreCPULoadAvg OBJECT-TYPE
	  SYNTAX Integer32 (0..100)
       MAX-ACCESS read-only
       STATUS current
       DESCRIPTION
              "System CPU load Percentage (Instantaneous)."
       ::= { usrreSystem 13 }
      usrreCPULoadAvgMinute OBJECT-TYPE
	  SYNTAX Integer32 (0..100)
       MAX-ACCESS read-only
       STATUS current
       DESCRIPTION
              "System CPU load Percentage for last minute."
       ::= { usrreSystem 14 }
      usrreCPULoadAvgHour OBJECT-TYPE
	  SYNTAX Integer32 (0..100)
       MAX-ACCESS read-only
       STATUS current
       DESCRIPTION
              "System CPU load Percentage for last hour."
       ::= { usrreSystem 15 }
      usrreCPULoadAvgDay OBJECT-TYPE
	  SYNTAX Integer32 (0..100)
       MAX-ACCESS read-only
       STATUS current
       DESCRIPTION
              "System CPU load Percentage for last day."
       ::= { usrreSystem 16 }
     usrreFreeMemorySize1HourBefore OBJECT-TYPE
      SYNTAX KBytes
      MAX-ACCESS read-only
      STATUS current
      DESCRIPTION
            "The amount of free physical main memory maintained by
            the RoboExec 1 Hour Before."
      ::= { usrreSystem 17 }
      usrreFreeMemorySize12HourBefore OBJECT-TYPE
      SYNTAX KBytes
      MAX-ACCESS read-only
      STATUS current
      DESCRIPTION
            "The amount of free physical main memory maintained by
            the RoboExec 12 Hour Before."
      ::= { usrreSystem 18 }
      usrreFreeMemorySize24HourBefore OBJECT-TYPE
      SYNTAX KBytes
      MAX-ACCESS read-only
      STATUS current
      DESCRIPTION
            "The amount of free physical main memory maintained by
            the RoboExec 24 Hours Before."
      ::= { usrreSystem 19 }
      usrreTotalBufferCache OBJECT-TYPE
      SYNTAX KBytes
      MAX-ACCESS read-only
      STATUS current
      DESCRIPTION
            "The amount of total allocated buffer cache maintained
             by RoboExec."
      ::= { usrreSystem 20 }
      usrreFreeBufferCache OBJECT-TYPE
      SYNTAX KBytes
      MAX-ACCESS read-only
      STATUS current
      DESCRIPTION
            "The amount of free buffer cache maintained by
             RoboExec."
      ::= { usrreSystem 21 }
      usrreFlashMemorySize OBJECT-TYPE
	  SYNTAX KBytes
	  MAX-ACCESS read-only
	  STATUS current
	  DESCRIPTION
		    "The amount of physical flash memory maintained by
		    the RoboExec."
	  ::= { usrreSystem 22 }
   usrreFreeMemoryMaxSize OBJECT-TYPE
	  SYNTAX KBytes
	  MAX-ACCESS read-only
	  STATUS current
	  DESCRIPTION
		    "The maximum possible amount of free physical main memory
		    maintained by the RoboExec."
	  ::= { usrreSystem 23 }
   -- The RoboExec Resources Running Software Group
   --
   -- Implementation of this group is mandatory.
   --
   -- The reSWRunTable contains an entry for each distinct piece of
   -- software that is running or loaded into physical or virtual
   -- memory in preparation for running.  This includes the RoboExec's
   -- operating system, device drivers, and applications.
   usrreSWRunTable OBJECT-TYPE
	  SYNTAX SEQUENCE OF UsrreSWRunEntry
	  MAX-ACCESS not-accessible
	  STATUS current
	  DESCRIPTION
		    "The (conceptual) table of software running on the
		    RoboExec."
	  ::= { usrreSWRun 1 }
   usrreSWRunEntry OBJECT-TYPE
	  SYNTAX UsrreSWRunEntry
	  MAX-ACCESS not-accessible
	  STATUS current
	  DESCRIPTION
		    "A (conceptual) entry for one piece of software
		    running on the RoboExec Note that because the installed
		    software table only contains information for
		    software stored locally on this RoboExec, not every
		    piece of running software will be found in the
		    installed software table.	 This is true of software
		    that was loaded and run from a non-local source,
		    such as a network-mounted file system.
		    As an example of how objects in this table are
		    named, an instance of the reSWRunName object might
		    be named reSWRunName.1287"
	  INDEX { usrreSWRunIndex }
	  ::= { usrreSWRunTable 1 }
   UsrreSWRunEntry ::= SEQUENCE {
		 usrreSWRunIndex		Integer32,
		 usrreSWRunName		DisplayString,
		 usrreSWRunType		INTEGER,
		 usrreSWRunStatus		INTEGER,
		 usrreSWRunStartTime	Integer32,
		 usrreSWRunMsgSent		Counter32,
		 usrreSWRunMsgRcvd		Counter32,
      	 usrreSWRunMsgPassedFrom Counter32,
		 usrreSWRunMsgPassedTo	Counter32,
		 usrreSWRunMboxScheduled	Counter32,
		 usrreSWRunAllocated	KBytes,
		 usrreSWRunFreed		KBytes
	  }
   usrreSWRunIndex OBJECT-TYPE
	  SYNTAX Integer32 (1..2147483647)
	  MAX-ACCESS not-accessible
	  STATUS current
	  DESCRIPTION
		    "A unique value for each piece of software running
		    on the RoboExec.  Wherever possible, this should be the
		    system's native, unique identification number."
	  ::= { usrreSWRunEntry 1 }
   usrreSWRunName OBJECT-TYPE
	  SYNTAX DisplayString (SIZE (0..64))
	  MAX-ACCESS read-only
	  STATUS current
	  DESCRIPTION
		    "The name of the RoboExec Process."
	  ::= { usrreSWRunEntry 2 }
   usrreSWRunType OBJECT-TYPE
	  SYNTAX INTEGER {
			    unknown(1),
			    operatingSystem(2),
			    deviceDriver(3),
			    application(4),
			    forwarder(5)
		    }
	  MAX-ACCESS read-only
	  STATUS current
	  DESCRIPTION
			"The type of this software."
	  ::= { usrreSWRunEntry 3 }
   usrreSWRunStatus OBJECT-TYPE
	  SYNTAX INTEGER {
			running(1),
			runnable(2),	 -- waiting for resource (CPU, memory, IO)
			notRunnable(3), -- loaded but waiting for event
 			invalid(4)	 -- not loaded
		 }
	  MAX-ACCESS read-only
	  STATUS current
	  DESCRIPTION
		    "The status of this running piece of software."
	  ::= { usrreSWRunEntry 4 }
   usrreSWRunStartTime OBJECT-TYPE
	 SYNTAX Integer32 (0..2147483647)
      MAX-ACCESS read-only
      STATUS current
      DESCRIPTION
             "The time when this process started. 
              NOTE: Time equal 0 indicates that per process
              statistic information is not capturing."
      ::= { usrreSWRunEntry 5 }
   usrreSWRunMsgSent OBJECT-TYPE
	 SYNTAX Counter32
      MAX-ACCESS read-only
      STATUS current
      DESCRIPTION
             "Number of messages were sent by this process.
              NOTE: Number of messages equal 0 indicates
              that per process statistic information is not capturing."
      ::= { usrreSWRunEntry 6 }
   usrreSWRunMsgRcvd OBJECT-TYPE
	 SYNTAX Counter32
      MAX-ACCESS read-only
      STATUS current
      DESCRIPTION
             "Number of messages were received by this process.
              NOTE: Number of messages equal 0 indicates
              that per process statistic information is not capturing."
      ::= { usrreSWRunEntry 7 }
   usrreSWRunMsgPassedFrom OBJECT-TYPE
	 SYNTAX Counter32
      MAX-ACCESS read-only
      STATUS current
      DESCRIPTION
             "Number of messages were passed from this process.
              NOTE: Number of messages equal 0 indicates
              that per process statistic information is not capturing."
      ::= { usrreSWRunEntry 8 }
   usrreSWRunMsgPassedTo OBJECT-TYPE
	 SYNTAX Counter32
      MAX-ACCESS read-only
      STATUS current
      DESCRIPTION
             "Number of messages were passed this process.
              NOTE: Number of messages equal 0 indicates
              that per process statistic information is not capturing."
      ::= { usrreSWRunEntry 9 }
   usrreSWRunMboxScheduled OBJECT-TYPE
	 SYNTAX Counter32
      MAX-ACCESS read-only
      STATUS current
      DESCRIPTION
             "The total number of times all mailboxes owned by 
             this process were scheduled.
             NOTE: Number equal 0 indicates
             that per process statistic information is not capturing."
      ::= { usrreSWRunEntry 10 }
   usrreSWRunAllocated OBJECT-TYPE
	 SYNTAX KBytes
      MAX-ACCESS read-only
      STATUS current
      DESCRIPTION
             "The total amount of memory that was allocated for
             this process.
             NOTE: 0 KB indicates that per process statistic 
             information is not capturing."
      ::= { usrreSWRunEntry 11 }
   usrreSWRunFreed OBJECT-TYPE
	 SYNTAX KBytes
      MAX-ACCESS read-only
      STATUS current
      DESCRIPTION
             "The total amount of memory that was freed while
             this process was running.
             NOTE: 0 KB indicates that per process statistic 
             information is not capturing."
      ::= { usrreSWRunEntry 12 }
   -- The RoboExec Logging Level Group
   --
   -- Implementation of this group is mandatory for all RoboExec's
   --
   -- The reLogLevelTable contains an entry for each software 
   -- facility running on the RoboExec.
   usrreLogLevelConfigFileName OBJECT-TYPE
	  SYNTAX DisplayString
	  MAX-ACCESS read-only
	  STATUS current
	  DESCRIPTION		
		    "The name of a ConfigFile to read/write permanent database
		    records. If the value of this object is an empty string, then
		    the process uses the default name
		    `@file://RoboExecNMProcess.cfg'."
	  ::= { usrreEvents 1 }
   usrreLogLevelCFMStatusFlag	 OBJECT-TYPE
	  SYNTAX UsrConfigStatus
	  MAX-ACCESS read-write
	  STATUS current
	  DESCRIPTION
		    "Setting the value of this object to `save' causes the values
			of the RoboExec Logging Level Group to be written out to the
			current config file, which is stored in the
			reLogLevelConfigFileName object. While the new ConfigFile is
			being written, the value of this flag will be set to `saving'.
			Any attempts to set the value while it is  not `normal'
			(i.e. the file is currently being written to the ConfigFile)
			will result in a badValue error being returned. Setting the
			value to `normal' will result in no action."
	  ::= { usrreEvents 2 }
   usrreLogLevelTable OBJECT-TYPE
	  SYNTAX SEQUENCE OF UsrreLogLevelEntry
	  MAX-ACCESS not-accessible
	  STATUS current
	  DESCRIPTION
		    "The (conceptual) table of event log levels for the
		    RoboExec."
	  ::= { usrreEvents 3 }
   usrreLogLevelEntry OBJECT-TYPE
	  SYNTAX UsrreLogLevelEntry
	  MAX-ACCESS not-accessible
	  STATUS current
	  DESCRIPTION
		    "A (conceptual) entry for one facility on the RoboExec
		    As an example of how objects in this table are
		    named, an instance of the reSWRunName object might
		    be named reSWRunName.1287"
	  INDEX { usrreLLFacility }
	  ::= { usrreLogLevelTable 1 }
   UsrreLogLevelEntry ::= SEQUENCE {
		 usrreLLFacility	   Integer32,
		 usrreLLFacilityName   DisplayString,
		 usrreLLLogLevel	   INTEGER
	  }
   usrreLLFacility OBJECT-TYPE
	  SYNTAX Integer32 (1..64)
	  MAX-ACCESS not-accessible
	  STATUS current
	  DESCRIPTION
		    "A unique value for each software facility
		    on the RoboExec."
	  ::= { usrreLogLevelEntry 1 }
   usrreLLFacilityName OBJECT-TYPE
	  SYNTAX DisplayString (SIZE (0..64))
	  MAX-ACCESS read-only
	  STATUS current
	  DESCRIPTION
		    "A textual name of the software facility."
	  ::= { usrreLogLevelEntry 2 }
   usrreLLLogLevel OBJECT-TYPE
	  SYNTAX INTEGER { critical(0),
				    unusual(1),
				    common(2),
				    verbose(3),
				    debug(4) }
	  MAX-ACCESS read-write
	  STATUS current
	  DESCRIPTION
		    "The Logging level for this software facility."
	  --CONFIGURABLE
	  ::= { usrreLogLevelEntry 3 }
   usrreEvLocalFile OBJECT-TYPE
	  SYNTAX DisplayString
	  MAX-ACCESS read-only
	  STATUS current
	  DESCRIPTION
		    "The file name of the local NVRAM logfile."
	  ::= { usrreEvents 4 }
   usrreEvOldLocalFile OBJECT-TYPE
	  SYNTAX DisplayString
	  MAX-ACCESS read-only
	  STATUS current
	  DESCRIPTION
		    "The name of the file that the Event Handler should copy the
		    old LocalFile contents to when the pilgrim system reboots."
	  ::= { usrreEvents 5 }
   usrreEvCriticalMsgsTable OBJECT-TYPE
	  SYNTAX SEQUENCE OF UsrreEvCriticalMsgsEntry
	  MAX-ACCESS not-accessible
	  STATUS current
	  DESCRIPTION
		    "The (conceptual) table of critical event messages."
	  ::= { usrreEvents 6 }
   usrreEvStatus OBJECT-TYPE
	  SYNTAX INTEGER {
		disable(0),
		enable(1)
	}
	  MAX-ACCESS read-write
	  STATUS current
	  DESCRIPTION
              "This switch allows disabling or enabling all logging
               of critical events to the local flash file system.
               This is disable by default."
	  --CONFIGURABLE
	  ::= { usrreEvents 7 }
   usrreEvCriticalMsgsEntry OBJECT-TYPE
	  SYNTAX UsrreEvCriticalMsgsEntry
	  MAX-ACCESS not-accessible
	  STATUS current
	  DESCRIPTION
		    "A (conceptual) entry for one critical event message."
	  INDEX { usrreEvCritMsgTimeStamp }
	  ::= { usrreEvCriticalMsgsTable 1 }
   UsrreEvCriticalMsgsEntry ::= SEQUENCE {
	  usrreEvCritMsgTimeStamp Integer32,
	  usrreEvCriticalMsg  DisplayString
	}
   usrreEvCritMsgTimeStamp OBJECT-TYPE
	  SYNTAX Integer32
	  MAX-ACCESS not-accessible
	  STATUS current
	  DESCRIPTION
		    "Index into the table of critical event messages saved in the
		    NVRAM local file. This represents the time, in hundredths of
		    seconds since system startup, at which the critical event
		    occurred."
	  ::= { usrreEvCriticalMsgsEntry 1 }
   usrreEvCriticalMsg OBJECT-TYPE
	  SYNTAX DisplayString
	  MAX-ACCESS read-only
	  STATUS current
	  DESCRIPTION
		    "Text of a critical event message."
	  ::= { usrreEvCriticalMsgsEntry 2 }
   -- The RoboExec System Counters Group
   --
   -- This group references counters defined in the RoboExec for
   -- certain system calls.
   -- This section of the MIB is still under development and it is likely
   -- that counters will be obsoleted or more counters will be added.
   --
   -- Implementation of this group is mandatory for a RoboExec system.
   --
   -- Define the groups within the counters group
   usrreCntBuffers	OBJECT IDENTIFIER ::= { usrreCounters 1 }
   usrreCntHeap	OBJECT IDENTIFIER ::= { usrreCounters 2 }
   usrreCntMessage	OBJECT IDENTIFIER ::= { usrreCounters 3 }
   usrreCntEvents	OBJECT IDENTIFIER ::= { usrreCounters 4 }
   usrreCntNames	OBJECT IDENTIFIER ::= { usrreCounters 5 }
   usrreCntSched	OBJECT IDENTIFIER ::= { usrreCounters 6 }
	--
	-- Counters for the buffer calls
	--
	usrreCBgetBuffer OBJECT-TYPE
		SYNTAX Counter32
		MAX-ACCESS read-only
		STATUS current
		DESCRIPTION	"The number of times exec_get_buffer() was called"
		::= { usrreCntBuffers 1 }
	usrreCBfreeBchain OBJECT-TYPE
		SYNTAX Counter32
		MAX-ACCESS read-only
		STATUS current
		DESCRIPTION	"The number of times exec_free_bchain() was called"
		::= { usrreCntBuffers 2 }
	usrreCBreplicateBufdesc OBJECT-TYPE
		SYNTAX Counter32
		MAX-ACCESS read-only
		STATUS current
		DESCRIPTION	"The number of times exec_replicate_bufdesc() was called"
		::= { usrreCntBuffers 3 }
	usrreCBreplicateListToBchain OBJECT-TYPE
		SYNTAX Counter32
		MAX-ACCESS read-only
		STATUS current
		DESCRIPTION	"The number of times exec_replicate_list_to_bchain() was called"
		::= { usrreCntBuffers 4 }
	usrreCBreplPartialBchain OBJECT-TYPE
		SYNTAX Counter32
		MAX-ACCESS read-only
		STATUS current
		DESCRIPTION	"The number of times exec_repl_partial_bchain() was called"
		::= { usrreCntBuffers 5 }
	usrreCBduplicateBchain OBJECT-TYPE
		SYNTAX Counter32
		MAX-ACCESS read-only
		STATUS current
		DESCRIPTION	"The number of times exec_duplicate_bchain() was called"
		::= { usrreCntBuffers 6 }
	usrreCBpullupBchain OBJECT-TYPE
		SYNTAX Counter32
		MAX-ACCESS read-only
		STATUS current
		DESCRIPTION	"The number of times exec_pullup_bchain() was called"
		::= { usrreCntBuffers 7 }
	usrreCBjoinBchains OBJECT-TYPE
		SYNTAX Counter32
		MAX-ACCESS read-only
		STATUS current
		DESCRIPTION	"The number of times exec_join_bchains() was called"
		::= { usrreCntBuffers 8  }
	usrreCBtrimBchain OBJECT-TYPE
		SYNTAX Counter32
		MAX-ACCESS read-only
		STATUS current
		DESCRIPTION	"The number of times exec_trim_bchain() was called"
		::= { usrreCntBuffers 9 }
	usrreCBmaskBchain OBJECT-TYPE
		SYNTAX Counter32
		MAX-ACCESS read-only
		STATUS current
		DESCRIPTION	"The number of times exec_mask_bchain() was called"
		::= { usrreCntBuffers 10 }
	usrreCBunmaskBchain OBJECT-TYPE
		SYNTAX Counter32
		MAX-ACCESS read-only
		STATUS current
		DESCRIPTION	"The number of times exec_unmask_bchain() was called"
		::= { usrreCntBuffers 11 }
	usrreCBsetBchainSize OBJECT-TYPE
		SYNTAX Counter32
		MAX-ACCESS read-only
		STATUS current
		DESCRIPTION	"The number of calls to exec_set_bchain_size()."
		::= { usrreCntBuffers 12 }
	usrreCBbchainSize OBJECT-TYPE
		SYNTAX Counter32
		MAX-ACCESS read-only
		STATUS current
		DESCRIPTION	"The number of calls to exec_bchain_size()."
		::= { usrreCntBuffers 13 }
	usrreCBbchainCount OBJECT-TYPE
		SYNTAX Counter32
		MAX-ACCESS read-only
		STATUS current
		DESCRIPTION	"The number of calls to exec_bchain_count()."
		::= { usrreCntBuffers 14 }
	usrreCBcheckBchain OBJECT-TYPE
		SYNTAX Counter32
		MAX-ACCESS read-only
		STATUS current
		DESCRIPTION	"The number of calls to exec_check_bchain()."
		::= { usrreCntBuffers 15 }
	usrreCBcopyBchainToBlock OBJECT-TYPE
		SYNTAX Counter32
		MAX-ACCESS read-only
		STATUS current
		DESCRIPTION	"The number of calls to exec_copy_bchain_to_block()."
		::= { usrreCntBuffers 16 }
	usrreCBcopyBlockToBchain OBJECT-TYPE
		SYNTAX Counter32
		MAX-ACCESS read-only
		STATUS current
		DESCRIPTION	"The number of calls to exec_copy_block_to_bchain()."
		::= { usrreCntBuffers 17 }
	usrreCBprependToBchain OBJECT-TYPE
		SYNTAX Counter32
		MAX-ACCESS read-only
		STATUS current
		DESCRIPTION	"The number of calls to exec_prepend_to_bchain()."
		::= { usrreCntBuffers 18 }
	usrreCBappendToBchain OBJECT-TYPE
		SYNTAX Counter32
		MAX-ACCESS read-only
		STATUS current
		DESCRIPTION	"The number of calls to exec_append_to_bchain()."
		::= { usrreCntBuffers 19 }
	usrreCBdetachBuffer OBJECT-TYPE
		SYNTAX Counter32
		MAX-ACCESS read-only
		STATUS current
		DESCRIPTION	"The number of calls to exec_detach_buffer()."
		::= { usrreCntBuffers 20 }
	usrreCBbufferFromBlock OBJECT-TYPE
		SYNTAX Counter32
		MAX-ACCESS read-only
		STATUS current
		DESCRIPTION	"The number of calls to exec_buffer_from_block()."
		::= { usrreCntBuffers 21 }
	usrreCBallocProtocolBuffer OBJECT-TYPE
		SYNTAX Counter32
		MAX-ACCESS read-only
		STATUS current
		DESCRIPTION	"The number of calls to exec_alloc_protocol_buffer()."
		::= { usrreCntBuffers 22 }
	usrreCBsplitBchain OBJECT-TYPE
		SYNTAX Counter32
		MAX-ACCESS read-only
		STATUS current
		DESCRIPTION	"The number of calls to exec_split_bchain()."
		::= { usrreCntBuffers 23 }
	usrreCBtimestampBchain OBJECT-TYPE
		SYNTAX Counter32
		MAX-ACCESS read-only
		STATUS current
		DESCRIPTION	"The number of calls to exec_timestamp_bchain()."
		::= { usrreCntBuffers 24 }
	usrreCBtimediffBchain OBJECT-TYPE
		SYNTAX Counter32
		MAX-ACCESS read-only
		STATUS current
		DESCRIPTION	"The number of calls to exec_timediff_bchain()."
		::= { usrreCntBuffers 25 }
	usrreCBbchainSetCorrelator OBJECT-TYPE
		SYNTAX Counter32
		MAX-ACCESS read-only
		STATUS current
		DESCRIPTION	"The number of calls to exec_bchain_set_correlator()."
		::= { usrreCntBuffers 26 }
	usrreCBprotectBchain OBJECT-TYPE
		SYNTAX Counter32
		MAX-ACCESS read-only
		STATUS current
		DESCRIPTION	"The number of calls to exec_protect_bchain()."
		::= { usrreCntBuffers 27 }
	usrreCBunprotectBchain OBJECT-TYPE
		SYNTAX Counter32
		MAX-ACCESS read-only
		STATUS current
		DESCRIPTION	"The number of calls to exec_unprotect_bchain()."
		::= { usrreCntBuffers 28 }
	--
	-- Counters for the memory heap calls
	--
	usrreCHallocateHeap OBJECT-TYPE
		SYNTAX Counter32
		MAX-ACCESS read-only
		STATUS current
		DESCRIPTION	"The number of calls to exec_allocate_heap()."
		::= { usrreCntHeap 1 }
	usrreCHfreeHeap OBJECT-TYPE
		SYNTAX Counter32
		MAX-ACCESS read-only
		STATUS current
		DESCRIPTION	"The number of calls to exec_free_heap()."
		::= { usrreCntHeap 2 }
	usrreCHreallocHeap OBJECT-TYPE
		SYNTAX Counter32
		MAX-ACCESS read-only
		STATUS current
		DESCRIPTION	"The number of calls to exec_realloc_heap()."
		::= { usrreCntHeap 3 }
	usrreCHduplicateHeap OBJECT-TYPE
		SYNTAX Counter32
		MAX-ACCESS read-only
		STATUS current
		DESCRIPTION	"The number of calls to exec_duplicate_heap()."
		::= { usrreCntHeap 4 }
	usrreCHheapCoalesce OBJECT-TYPE
		SYNTAX Counter32
		MAX-ACCESS read-only
		STATUS current
		DESCRIPTION	"The number of calls to exec_heap_coalesce()."
		::= { usrreCntHeap 5 }
	usrreCHcoalesceToABlock OBJECT-TYPE
		SYNTAX Counter32
		MAX-ACCESS read-only
		STATUS current
		DESCRIPTION	"The number of successful calls to exec_coalesce_to_a_block()."
		::= { usrreCntHeap 6 }
	usrreCHheapInfo OBJECT-TYPE
		SYNTAX Counter32
		MAX-ACCESS read-only
		STATUS current
		DESCRIPTION	"The number of calls to exec_heap_info()."
		::= { usrreCntHeap 7 }
	usrreCHheapSetCorrelator OBJECT-TYPE
		SYNTAX Counter32
		MAX-ACCESS read-only
		STATUS current
		DESCRIPTION	"The number of calls to exec_heap_set_correlator()."
		::= { usrreCntHeap 8 }
	usrreCHuseHeap OBJECT-TYPE
		SYNTAX Counter32
		MAX-ACCESS read-only
		STATUS current
		DESCRIPTION	"The number of calls to exec_use_heap()."
		::= { usrreCntHeap 9 }
	usrreCHheapGetUseCnt OBJECT-TYPE
		SYNTAX Counter32
		MAX-ACCESS read-only
		STATUS current
		DESCRIPTION	"The number of calls to exec_heap_get_usecnt()."
		::= { usrreCntHeap 10 }
	usrreCHfreeCacheBlocks OBJECT-TYPE
		SYNTAX Counter32
		MAX-ACCESS read-only
		STATUS current
		DESCRIPTION	"The number of outstanding free blocks in the heap cache."
		::= { usrreCntHeap 11 }
	usrreCHfreeHeapBlocks OBJECT-TYPE
		SYNTAX Counter32
		MAX-ACCESS read-only
		STATUS current
		DESCRIPTION	"The number of outstanding free blocks in the heap's heap."
		::= { usrreCntHeap 12 }
	usrreCHheapCheckProtection OBJECT-TYPE
		SYNTAX Counter32
		MAX-ACCESS read-only
		STATUS current
		DESCRIPTION	"The number of calls to exec_heap_check_protection()."
		::= { usrreCntHeap 13 }
	usrreCHheapSetProtection OBJECT-TYPE
		SYNTAX Counter32
		MAX-ACCESS read-only
		STATUS current
		DESCRIPTION	"The number of calls to exec_heap_set_protection()."
		::= { usrreCntHeap 14 }
	usrreCHheapRemoveProtection OBJECT-TYPE
		SYNTAX Counter32
		MAX-ACCESS read-only
		STATUS current
		DESCRIPTION	"The number of calls to exec_heap_remove_protection()."
		::= { usrreCntHeap 15 }
	usrreCHheapProtectionInfo OBJECT-TYPE
		SYNTAX Counter32
		MAX-ACCESS read-only
		STATUS current
		DESCRIPTION	"The number of calls to exec_heap_protection_info()."
		::= { usrreCntHeap 16 }
	--
	-- Counters for the message calls
	--
	usrreCMallocMsg OBJECT-TYPE
		SYNTAX Counter32
		MAX-ACCESS read-only
		STATUS current
		DESCRIPTION	"The number of calls to exec_alloc_msg()."
		::= { usrreCntMessage 1 }
	usrreCMfreemsg OBJECT-TYPE
		SYNTAX Counter32
		MAX-ACCESS read-only
		STATUS current
		DESCRIPTION	"The number of calls to exec_freemsg()."
		::= { usrreCntMessage 2 }
	usrreCMwasMsgPassed OBJECT-TYPE
		SYNTAX Counter32
		MAX-ACCESS read-only
		STATUS current
		DESCRIPTION	"The number of calls to exec_was_msg_passed()."
		::= { usrreCntMessage 3 }
	usrreCMrespondToMsg OBJECT-TYPE
		SYNTAX Counter32
		MAX-ACCESS read-only
		STATUS current
		DESCRIPTION	"The number of calls to exec_respond_to_msg()."
		::= { usrreCntMessage 4 }
	usrreCMmessageSend OBJECT-TYPE
		SYNTAX Counter32
		MAX-ACCESS read-only
		STATUS current
		DESCRIPTION	"The number of calls to exec_message_send()."
		::= { usrreCntMessage 5 }
	usrreCMsendmsg OBJECT-TYPE
		SYNTAX Counter32
		MAX-ACCESS read-only
		STATUS current
		DESCRIPTION	"The number of calls to exec_sendmsg()."
		::= { usrreCntMessage 6 }
	usrreCMreceiveMail OBJECT-TYPE
		SYNTAX Counter32
		MAX-ACCESS read-only
		STATUS current
		DESCRIPTION	"The number of calls to exec_receive_mail()."
		::= { usrreCntMessage 7 }
	usrreCMpassmsg OBJECT-TYPE
		SYNTAX Counter32
		MAX-ACCESS read-only
		STATUS current
		DESCRIPTION	"The number of calls to exec_passmg()."
		::= { usrreCntMessage 8 }
	usrreCMcountMail OBJECT-TYPE
		SYNTAX Counter32
		MAX-ACCESS read-only
		STATUS current
		DESCRIPTION	"The number of calls to exec_count_mail()."
		::= { usrreCntMessage 9 }
	--
	-- Counters for the event calls
	--
	usrreCEevents OBJECT-TYPE
		SYNTAX Counter32
		MAX-ACCESS read-only
		STATUS current
		DESCRIPTION	"The number of calls to exec_events()."
		::= { usrreCntEvents 1 }
	usrreCEeventsLogged OBJECT-TYPE
		SYNTAX Counter32
		MAX-ACCESS read-only
		STATUS current
		DESCRIPTION	"The number of calls to exec_events() that were logged."
		::= { usrreCntEvents 2 }
	usrreCEeventsDropped OBJECT-TYPE
		SYNTAX Counter32
		MAX-ACCESS read-only
		STATUS current
		DESCRIPTION	"The number of calls to exec_events() that were dropped."
		::= { usrreCntEvents 3 }
	--
	-- Counters for the Name calls
	--
	usrreCNregisterName OBJECT-TYPE
		SYNTAX Counter32
		MAX-ACCESS read-only
		STATUS current
		DESCRIPTION	"The number of calls to exec_register_name()."
		::= { usrreCntNames 1 }
	usrreCNresolveName OBJECT-TYPE
		SYNTAX Counter32
		MAX-ACCESS read-only
		STATUS current
		DESCRIPTION	"The number of calls to exec_resolve_name()."
		::= { usrreCntNames 2 }
	usrreCNremoveName OBJECT-TYPE
		SYNTAX Counter32
		MAX-ACCESS read-only
		STATUS current
		DESCRIPTION	"The number of calls to exec_remove_name()."
		::= { usrreCntNames 3 }
	usrreCNremoveNameForData OBJECT-TYPE
		SYNTAX Counter32
		MAX-ACCESS read-only
		STATUS current
		DESCRIPTION
			"The number of names that were removed because the data they
			 pointed to was no longer there (mailbox delete e.g.)."
		::= { usrreCntNames 4 }
	usrreCNremoveNameForProc OBJECT-TYPE
		SYNTAX Counter32
		MAX-ACCESS read-only
		STATUS current
		DESCRIPTION
			"The number of names that were removed because the process
			 that owned them was killed."
		::= { usrreCntNames 5 }
	--
	-- Counters for the scheduling information
	--
	usrreCScurrentMsgsQueued OBJECT-TYPE
		SYNTAX Counter32
		MAX-ACCESS read-only
		STATUS current
		DESCRIPTION	"The current number of messages queued."
		::= { usrreCntSched 1 }
	usrreCSmaxMsgsQueued OBJECT-TYPE
		SYNTAX Counter32
		MAX-ACCESS read-only
		STATUS current
		DESCRIPTION	"The all time high number of messages queued."
		::= { usrreCntSched 2 }
	usrreCSrunTotalMsgsQueued OBJECT-TYPE
		SYNTAX Counter32
		MAX-ACCESS read-only
		STATUS current
		DESCRIPTION	"The a running total of the messages queued."
		::= { usrreCntSched 3 }
	usrreCScurrentMboxesReady OBJECT-TYPE
		SYNTAX Counter32
		MAX-ACCESS read-only
		STATUS current
		DESCRIPTION	"The current number of mailboxes ready to run."
		::= { usrreCntSched 4 }
	usrreCSmaxMboxesReady OBJECT-TYPE
		SYNTAX Counter32
		MAX-ACCESS read-only
		STATUS current
		DESCRIPTION	"The all time high number of mailboxes ready to run."
		::= { usrreCntSched 5 }
	usrreCSrunTotalMboxesReady OBJECT-TYPE
		SYNTAX Counter32
		MAX-ACCESS read-only
		STATUS current
		DESCRIPTION	"The a running total of the mailboxes ready to run."
		::= { usrreCntSched 6 }
	usrreCSschedLoops OBJECT-TYPE
		SYNTAX Counter32
		MAX-ACCESS read-only
		STATUS current
		DESCRIPTION
			"The number of times we've run through the scheduling loop."
		::= { usrreCntSched 7 }
	--
	-- The RoboExec Name Group
	--
	usrreNameTable OBJECT-TYPE
		SYNTAX SEQUENCE OF UsrreNameEntry
		MAX-ACCESS not-accessible
		STATUS current
		DESCRIPTION
			  "The (conceptual) table of the names kept by the RoboExec."
		::= { usrreNames 1 }
	 usrreNameEntry OBJECT-TYPE
		SYNTAX UsrreNameEntry
		MAX-ACCESS not-accessible
		STATUS current
		DESCRIPTION
			  "A (conceptual) entry for one name."
		INDEX { usrreNameType, usrreNameName }
		::= { usrreNameTable 1 }
	 UsrreNameEntry ::= SEQUENCE {
		usrreNameType			DisplayString,
		usrreNameName		 	DisplayString,
		usrreNameIntOrString	INTEGER,
		usrreNameIntValue		Integer32,
		usrreNameStringValue	DisplayString,
		usrreNameOwner			Integer32
		}
	 usrreNameType OBJECT-TYPE
		SYNTAX DisplayString (SIZE (0..64))
		MAX-ACCESS not-accessible
		STATUS current
		DESCRIPTION
			  "The internal type of the name."
		::= { usrreNameEntry 1 }
	 usrreNameName OBJECT-TYPE
		SYNTAX DisplayString (SIZE (0..64))
		MAX-ACCESS not-accessible
		STATUS current
		DESCRIPTION
			  "The name in the RoboExec"
		::= { usrreNameEntry 2 }
	 usrreNameIntOrString OBJECT-TYPE
		SYNTAX INTEGER {
				  integer(1),
				  string(2),
				  neither(3)
			  }
		MAX-ACCESS read-only
		STATUS current
		DESCRIPTION
			"Is the data for this name a string or an integer?"
		::= { usrreNameEntry 3 }
	 usrreNameIntValue OBJECT-TYPE
		SYNTAX Integer32
		MAX-ACCESS read-only
		STATUS current
		DESCRIPTION
			  "If the name has a numerical value, this is it.
			   Otherwise, this value is 0."
		::= { usrreNameEntry 4 }
	 usrreNameStringValue OBJECT-TYPE
		SYNTAX DisplayString (SIZE (0..200))
		MAX-ACCESS read-only
		STATUS current
		DESCRIPTION
			  "If the name has a string value, this is it.
			   Otherwise, this value is blank."
		::= { usrreNameEntry 5 }
	 usrreNameOwner OBJECT-TYPE
		SYNTAX Integer32
		MAX-ACCESS read-only
		STATUS current
		DESCRIPTION
			"The process ID of the owner of this name.
			This should correlate with the usrreSWRunIndex."
		::= { usrreNameEntry 6 }
	--
	-- The RoboExec FileSystem Group
	--
	--
	-- File system information
	--
	usrreFSInfoTable OBJECT-TYPE
		SYNTAX SEQUENCE OF UsrreFSInfoEntry
		MAX-ACCESS not-accessible
		STATUS current
		DESCRIPTION
			  "The (conceptual) table of the File System information kept
			   by the RoboExec."
		::= { usrreFiles 1 }
	 usrreFSInfoEntry OBJECT-TYPE
		SYNTAX UsrreFSInfoEntry
		MAX-ACCESS not-accessible
		STATUS current
		DESCRIPTION
			  "A (conceptual) entry for one file system."
		INDEX { usrreFSInfoIndex }
		::= { usrreFSInfoTable 1 }
	 UsrreFSInfoEntry ::= SEQUENCE {
		usrreFSInfoIndex		Integer32,
		usrreFSInfoName		DisplayString,
		usrreFSInfoType		INTEGER
		}
	 usrreFSInfoIndex OBJECT-TYPE
		SYNTAX Integer32
		MAX-ACCESS not-accessible
		STATUS current
		DESCRIPTION
			  "And index to the file systems."
		::= { usrreFSInfoEntry 1 }
	 usrreFSInfoName OBJECT-TYPE
		SYNTAX DisplayString (SIZE (0..64))
		MAX-ACCESS read-only
		STATUS current
		DESCRIPTION
			  "A name given to the file system."
		::= { usrreFSInfoEntry 2 }
	 usrreFSInfoType OBJECT-TYPE
		SYNTAX INTEGER {
				flashRAM(1),
				ram(2),
				floppyDisk(3),
				hardDisk(4)
			  }
		MAX-ACCESS read-only
		STATUS current
		DESCRIPTION
			"The type of this file system."
		::= { usrreFSInfoEntry 3 }
	--
	-- File Table
	--
	usrreFileTable OBJECT-TYPE
		SYNTAX SEQUENCE OF UsrreFileTableEntry
		MAX-ACCESS not-accessible
		STATUS current
		DESCRIPTION
			  "The (conceptual) table of the files for a file system."
		::= { usrreFiles 2 }
	 usrreFileTableEntry OBJECT-TYPE
		SYNTAX UsrreFileTableEntry
		MAX-ACCESS not-accessible
		STATUS current
		DESCRIPTION
			  "A (conceptual) entry for one file system."
		INDEX { usrreFileTableFileSystem, usrreFileTableName }
		::= { usrreFileTable 1 }
	 UsrreFileTableEntry ::= SEQUENCE {
		usrreFileTableFileSystem	Integer32,
		usrreFileTableName		 DisplayString,
		usrreFileTableSize		 Integer32,
		usrreFileTableRenameTo	 DisplayString,
		usrreFileTableStatus	 INTEGER,
		usrreFileTableCopyTo	 DisplayString,
		usrreFileTableErrorString DisplayString
		}
	 usrreFileTableFileSystem OBJECT-TYPE
		SYNTAX Integer32
		MAX-ACCESS not-accessible
		STATUS current
		DESCRIPTION
			  "The file system containing this file. This must
			   match the file system from the File System Info Table."
		::= { usrreFileTableEntry 1 }
	 usrreFileTableName OBJECT-TYPE
		SYNTAX DisplayString (SIZE (0..64))
		MAX-ACCESS not-accessible
		STATUS current
		DESCRIPTION
			  "The name given to the file."
		::= { usrreFileTableEntry 2 }
	 usrreFileTableSize OBJECT-TYPE
		SYNTAX Integer32
		MAX-ACCESS read-only
		STATUS current
		DESCRIPTION
			"The size, in octets, of the file."
		::= { usrreFileTableEntry 3 }
	 usrreFileTableRenameTo OBJECT-TYPE
		SYNTAX DisplayString (SIZE (0..64))
		MAX-ACCESS read-write
		STATUS current
		DESCRIPTION
			"In order to change the name of this file, the
			new name should be written to this object. This
            value cannot be SET to NULL but it will revert
            to NULL when name has been changed."
		::= { usrreFileTableEntry 4 }
	usrreFileTableStatus OBJECT-TYPE
		SYNTAX INTEGER {
				normal(1),
				delete(2),
				copying(3),       -- File copying in progress
				failed(4)         -- Operation failed		
			}
		MAX-ACCESS read-write
		STATUS current
		DESCRIPTION
			"The status of the file. Valid row entries in this
			table have the status field set to normal.
			The settable value is delete: write 2 to this variable 
			to delete the file. The values normal(1), in_progress(3), 
			and failed(4) are read-only"
		::= { usrreFileTableEntry 5 }
	usrreFileTableCopyTo OBJECT-TYPE
		SYNTAX DisplayString (SIZE (0..64))
		MAX-ACCESS read-write
		STATUS current
		DESCRIPTION
			"In order to copy this file, the
			new name should be written to this object. This
            value cannot be SET to NULL but it will revert
            to NULL when file has been copied."
		::= { usrreFileTableEntry 6 }
	usrreFileTableErrorString OBJECT-TYPE
         SYNTAX  DisplayString (SIZE (0..255))
         MAX-ACCESS  read-only
         STATUS  current
         DESCRIPTION
            "The error string returned when file copy or rename fails.
             Otherwise, this field is NULL."		
		::= { usrreFileTableEntry 7 }
-- Memory Trap Settings Group
	usrreMemoryTrapUpperThreshold OBJECT-TYPE
		SYNTAX Integer32 (1..100)
		MAX-ACCESS read-write
		STATUS current
		DESCRIPTION
       			"Specifies the upper Water Mark for Memory
                 Threshold. If the used memory exceeds this
                 limit, then a trap is sent."
		--CONFIGURABLE
	::= { usrreMemTrapSettings 1 }
	usrreMemoryTrapLowerThreshold OBJECT-TYPE
		SYNTAX Integer32 (1..100)
		MAX-ACCESS read-write
		STATUS current
		DESCRIPTION
       			"Specifies the lower Water Mark for Memory
                 Threshold. If the used memory size touches 
                 this lower threshold after touching the Upper
                 threshold, then only a trap will be sent whenever
                 next time it exceeds the Upper Threshold."
		--CONFIGURABLE
	::= { usrreMemTrapSettings 2 }
	usrreMemoryTrapStatus OBJECT-TYPE
   		SYNTAX     INTEGER {
                        enabled(1),
                        disabled(2)
                        }
		MAX-ACCESS read-write
		STATUS current
   		DESCRIPTION
       		        "Memory Trap Enabled or Disabled."
                --CONFIGURABLE
	::= { usrreMemTrapSettings 3 }
-- Memory Traps Group
    usrreTrapsV2    OBJECT-IDENTITY
        STATUS  current
        DESCRIPTION
            "The events for the RoboExec process."
    ::= { usrreTraps 0 }
	usrreMemoryTrapThresholdReached NOTIFICATION-TYPE
		OBJECTS {    
                usrreMemoryTrapUpperThreshold,
                usrreMemoryTrapLowerThreshold,
                usrreFreeMemorySize
        		}
        STATUS  current
		DESCRIPTION
			"This trap is generated when Used Memory Size
                         reaches Upper Threshold."
        --#TYPE "Alarm"
	    --#SUMMARY	"Memory Upper Threshold reached"
	    --#SEVERITY MAJOR
	    --#STATE	OPERATIONAL
        ::= { usrreTrapsV2 1 }
END  -- End of    ROBOEXEC-RESOURCES-MIB DEFINITIONS
-- ************************************************************************
--
--	EEgg.mib - The Pilgrim Easter Egg MIB
--
