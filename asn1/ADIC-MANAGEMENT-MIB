-- Name:       ADIC Enterprise Management Control Blade (MCB) MIB 
--
-- $Id: ADIC_MANAGEMENT_MIB.mib 1.93 2005/02/16 20:07:58EST dhawthorne dev  $
--
--             **********************************************************
--             *                                                        *
--             *                   SMI v1 version                       *
--             *                                                        *
--             **********************************************************
--
-- Copyright (c) 2002 Advanced Digital Information Corporation
-- 
-- Revision History:
--      $Log: ADIC_MANAGEMENT_MIB.mib  $
--      Revision 1.93 2005/02/16 20:07:58EST dhawthorne 
--      Add trap #117, drive firmware update start
--      Revision 1.92 2004/12/03 17:07:40EST dhawthorne 
--      Added trapIntendedUsage to trap 406 payload
--      Revision 1.91 2004/10/01 18:08:20EDT dhawthorne 
--      Added noUnload(5) to operatingMode enum
--      Revision 1.90 2004/08/30 17:40:49EDT dhawthorne 
--      Move networkTimeServer2 variable to the end of the globalStatusTable
--      Revision 1.89 2004/08/30 16:06:51EDT dhawthorne 
--      Add second time server to globalStatusTable
--      Revision 1.88 2004/08/13 14:25:07EDT dhawthorne 
--      Correct a typo
--      Revision 1.87 2004/08/13 14:20:14EDT dhawthorne 
--      Add loMediaTypeCheckingPolicy (read/write)
--      Revision 1.86 2004/08/13 13:26:35EDT dhawthorne 
--      Changed name of logical SN feature enable
--      Revision 1.85 2004/08/05 11:38:13EDT dhawthorne 
--      Added driveLogicalSerialNumberMode
--      Revision 1.84 2004/03/29 17:53:59EST dhawthorne 
--      Added totalRawCapcity, totalFreeCapacity, and totalUsedCapacity
--      Revision 1.83 2004/03/09 14:26:59EST dhawthorne 
--      Added phDriveWwPortName.
--      Revision 1.82 2004/03/04 17:23:13EST dhawthorne 
--      Change unimplemented tables/variables to status "optional" 
--      Comment out unimplemented traps 
--      Revision 1.81 2004/02/20 10:55:58EST dhawthorne 
--      Added numPhFrames
--      Revision 1.80 2004/02/19 11:14:19EST dhawthorne 
--      Update phDriveCommand description clause
--      Revision 1.79 2004/02/19 11:10:18EST dhawthorne 
--      Add driveBrickUpdate(7) to phDriveCommand enumeration.
--      Revision 1.78 2004/02/19 10:58:27EST dhawthorne 
--      Added installProcessStatus variables for mcb, cmb, rcu, fcb and amc
--      Revision 1.77 2004/02/02 15:03:29EST dhawthorne 
--      Removed phDriveRow from drive FW update traps, added serial number and FW version
--      Revision 1.76 2004/01/23 17:37:09EST dhawthorne 
--      Add element address range to trap # 116
--      Revision 1.75 2004/01/23 16:35:48EST dhawthorne 
--      Add new trap, #116, physLibraryRESChange 
--      Revision 1.74 2004/01/19 11:04:19EST dhawthorne 
--      Added rasEventNotification trap.
--      Revision 1.73 2004/01/12 11:08:23EST dhawthorne 
--      Add physLibraryConfigurationChange trap to MIB
--      Revision 1.72 2003/12/29 11:13:43EST dhawthorne 
--      Added traps 113 and 114, drive brick firmware update success/failure
--      Revision 1.71 2003/12/17 17:43:40EST dhawthorne 
--      Cleaned up some description clauses
--      Made loNumLibraries obsolete
--      Revision 1.70 2003/12/16 17:33:54EST dhawthorne 
--      Incorporate i2k M2 changes to FDM interface (softwareInstallation table)
--      Revision 1.69 2003/12/16 15:19:32EST dhawthorne 
--      Added ethernet preferredSpeed, actualSpeed, and duplex
--      Revision 1.68 2003/11/12 12:48:44EST dhawthorne 
--      Changed loLtoTapeTags to have three state: prefix, suffix, disabled
--      Revision 1.67 2003/10/22 13:44:19EDT dhawthorne 
--      Add driveActivityUpdate trap.
--      Revision 1.66 2003/09/30 17:47:20EDT dhawthorne 
--      Added syncRcuToFlash(3) to installCommand
--      Revision 1.65 2003/09/25 12:23:39EDT dhawthorne 
--      Added rasTicketFilterSeverity
--      Revision 1.64 2003/09/16 14:19:28EDT dhawthorne 
--      Added rasReportHeadReport
--      Revision 1.63 2003/09/12 10:38:25EDT dhawthorne 
--      Added rasTicketKeyReport variable
--      Revision 1.62 2003/09/10 13:52:22EDT dhawthorne 
--      Added loLtoTapeTags to logiclaLibraryTable
--      Revision 1.61 2003/09/10 12:13:14EDT dhawthorne 
--      Added phDriveErrorCodeBytes and phDriveRasStatus variables
--      Revision 1.60 2003/08/22 14:18:00EDT dhawthorne 
--      Add rcuReady and rcuNotReady traps to Management MIB
--      Revision 1.59 2003/07/02 15:11:42EDT dhawthorne 
--      Add installCommand and  installStatusText variables
--      Revision 1.58 2003/05/01 12:26:00EDT dhawthorne 
--      Added ieStationInventoryPerformed trap, # 109
--      Revision 1.57 2003/04/26 16:26:40EDT dhawthorne 
--      Correct syntax error in AdicRasTicketState enum definition.
--      Revision 1.56 2003/04/23 16:41:04EDT dhawthorne 
--      Added rasTIcketFilterTable
--      Create AdicRasTicketState type definition (enumerated type)
--      Added all(99) value to AdicStatusGroup enumeration
--      Revision 1.55 2003/04/21 11:55:08EDT dhawthorne 
--      Changed AdicStatusGroupState enumeration to match Greg Prestas' code
--      Revision 1.54 2003/04/18 17:16:44EDT dhawthorne 
--      Added RAS ticket time opened, time closed, and count
--      Revision 1.53 2003/04/15 13:15:22EDT dhawthorne 
--      Create AutoPartitionTable
--      Moved numAutoPartition and mediaTypeCommand from MediaTypeTable to AutoPartitionTable
--      Renamed mediaTypeCommand to autoPartitionCommand
--      Revision 1.52 2003/04/09 13:02:52EDT dhawthorne 
--      Declared new enumeration adicFcPortSpeed
--      Changed fcPortPreferredSpeed and fcPortNegotiatedSpeed to be of type adicFcPortSpeed, not INTEGER
--      Revision 1.51 2003/04/07 12:16:58EDT dhawthorne 
--      Added trapSeverity varbind to traps 104 thru 108; these should all be informational(5) traps
--      Revision 1.50 2003/04/03 12:07:19EST dhawthorne 
--      Added licenseKeyAppliedDate
--      Revision 1.49 2003/03/28 18:02:42EST dhawthorne 
--      Added five new traps
--      Revision 1.48 2003/03/15 18:01:20EST dhawthorne 
--      Changed wording of description clause for phDriveOnlineStatus
--      Revision 1.47 2003/03/15 17:50:00EST dhawthorne 
--      Added phDriveOnlineStatus (read-only)
--      Revision 1.46 2003/03/15 17:07:53EST dhawthorne 
--      Remove underscore character from fcPreferredPortType enumeration values (n_port, nl_port)
--      (Underscore is not strictly legal in an SMIv1 enumeration)
--      Declared AdicFcPortType type assignment - use it for fcPreferredPortType and fcNegotiatedPortType
--      Revision 1.45 2003/03/07 15:41:48EST dhawthorne 
--      New group/table for FC port parameters
--      Revision 1.44 2003/02/05 16:34:39EST dhawthorne 
--      Added rasFruStatSerialNumber and rasFruStatState
--      Added rasFruStatIndex
--      ** Re-Indexed FruStatTable: now indexed by componentId and fruStatIndex (not fruStatInstanceID) **
--      ** Put fruStatIndex first in table and shifted the remaining OIDs downward **
--      Revision 1.43 2003/02/04 15:08:02EST dhawthorne 
--      Added license quantity variables.
--      Revision 1.42 2003/02/04 13:19:50EST dhawthorne 
--      Made RAS ticket and report serial numbers read-only
--      Revision 1.41 2003/02/04 12:58:23EST dhawthorne 
--      Added AdicFruSerialNumber type assignment
--      Added rasTicketSerialNumber
--      Added rasReportSerialNumber
--      Revision 1.40 2003/02/03 18:40:08EST dhawthorne 
--      Added trigger to pull log files (logSnapshotCommand) and trap to indicate log retrieval is complete (logRetrievalComplete)
--      Correted enableDaylightSavingsTime to be of type AdicEnable
--      Revision 1.39 2003/01/13 18:37:02EST dhawthorne 
--      Add enableDaylightSavingsTIme to globalStatusTable
--      Revision 1.38 2003/01/07 10:38:45MST dhawthorne 
--      Import Gauge from RFC 1155-SMI
--      Import TRAP-TYPE from RFC-1215
--      Declare rasTicketClosedBy and rasTicketVerifedBy to be type INTEGER (were incorrectly declared as type AdicStatusGroup)
--      Revision 1.37 2003/01/06 11:24:57EST dhawthorne 
--      Added ipAddressSubnetMask (read-write)
--      Revision 1.36 2002/12/23 18:49:15EST dhawthorne 
--      Changed MIB to include index 4 in lo stat table
--      Revision 1.35 2002/12/21 13:49:14EST dhawthorne 
--      MIB changes here - add ticketId and reportId to status change traps
--      Revision 1.34 2002/12/20 18:30:36EST dhawthorne 
--      Changed rasReportSubsytem to rasReportStatusGroup and made it of type AdicStatusGroup.
--      
--      Revision 1.33 2002/12/19 19:41:12EST dhawthorne 
--      Removed RAS Ticket/Report traps
--      Broken System Status Trap in six traps, one for each status group.
--      Added rasReportRepeatCounter
--      Revision 1.32 2002/12/19 16:27:07EST dhawthorne 
--      Added:
--      loStatsNumPuts          INTEGER ,
--      loStatsNumPutRetries    INTEGER ,
--      loStatsNumGetRetries    INTEGER ,
--      loStatsNumScanRetries   INTEGER
--      Revision 1.31 2002/12/18 19:12:03EST dhawthorne 
--      Added trapSummaryText field.
--      Revision 1.29 2002/12/18 16:18:20EST dhawthorne 
--      Added rasReportOrcDescription to RAS report table
--      Revision 1.28 2002/12/17 11:52:38EST dhawthorne 
--      Added RED id to IE station, drive and transport element tables
--      Revision 1.27 2002/12/16 16:00:27EST dhawthorne 
--      Added trap definitions
--      Added I/E station table to allow traps to refer to exact I/E station
--      Revision 1.26 2002/12/13 20:44:16EST dhawthorne 
--      Added numCleaningSlots to MediaDomainTable
--      Revision 1.25 2002/12/13 17:28:58MST dhawthorne 
--      Added softwareInstallationTable
--      Revision 1.24 2002/12/12 09:44:27MST dhawthorne 
--      Made logical library assigned LUN read-only
--      Also fixed a syntax error in the rasFruStatFruCategory enumeration: value 2 was used twice.
--      Revision 1.23 2002/12/12 09:18:01MST dhawthorne 
--      Changed operatingMode access to read-write
--      Revision 1.22 2002/12/12 09:08:14MST dhawthorne 
--      Changed Gauge32 declarartions to Gauge; Gauge32 is SMIv2 syntax
--      Revision 1.21 2002/12/10 17:17:58MST dhawthorne 
--      Added ticket, report and FRU statistics table.
--      Defined AdicStatusGroup enumeration.
--      Revision 1.20 2002/12/07 17:39:13EST dhawthorne 
--      Added rasSystemStatusTable to ADIC-MANAGEMENT-MIB
--      Revision 1.19 2002/12/06 22:04:16EST dhawthorne 
--      Added phDriveStatHistoryTable
--      Revision 1.18 2002/12/06 16:08:57EST jmulder 
--      None
--      Revision 1.17 2002/11/21 11:19:13MST dhawthorne 
--      Corrected terminology.
--      Revision 1.15 2002/11/20 20:16:44EST dhawthorne 
--      Use AdicEnable type assignement for RCU modes
--      Interface types are defined in IntelligentStorage MIB
--      Revision 1.14 2002/11/20 18:45:57EST dhawthorne 
--      Added phIeSegCommand with a single value import(1)
--      Revision 1.13 2002/11/20 18:06:58EST dhawthorne 
--      Added physLibraryAutoCleaning variable
--      Use AdicEnable where applicable
--      Revision 1.12 2002/11/20 17:02:10EST dhawthorne 
--      Added physLibraryManagerLun to phGeneralInfoTable
--      Revision 1.11 2002/11/19 15:54:36EST dhawthorne 
--      Changed loStatus enumeration to { online(1) offline(2) }
--      Revision 1.10 2002/11/08 16:49:08EST dhawthorne 
--      Changed productName to productIdName to resolve jMIBC naming conflict
--      Revision 1.9 2002/10/08 16:40:12EDT dhawthorne 
--      Corrected description clause of managementMibVersion object
--      Revision 1.8 2002/10/07 13:58:01EDT dhawthorne 
--      Removed extra index (phIeSegIndex) from phIeSlotEntry INDEX clause
--      Changed index from "phCleaningRow" to "phCleaningMediaRow" in  phCleaningMediaEntry INDEX clause
--      Commented out any imports which caused compiler warnings with Emissary compiler
--      Revision 1.7 2002/10/04 18:34:41EDT dhawthorne 
--      Removed all enum or SIZE definitions from SEQUENCE clauses to satisfy jMIBc compiler
--      Revision 1.6 2002/10/03 12:16:55EDT dhawthorne 
--      Changed AdicSegmentType enum to match enum used by robotics team
--      Revision 1.5 2002/08/26 16:41:08EDT dhawthorne 
--      Remove hostIndex from registration table
--      Index by IP address and UDP port number
--      Revision 1.4 2002/08/23 11:09:02EDT dhawthorne 
--      Removed userId from table 
--      Moved userId to column 1 in UserEntry sequence
--      Replaced userId with userName in userEntry INDEX clause
--      Revision 1.3 2002/08/22 17:38:26EDT dhawthorne 
--      Added networkTimeEnable object.
--      Revision 1.2 2002/08/13 18:31:47EDT dhawthorne 
--      Added segment Starting Row to physical and logical segment tables
--      Re-indexed segment tables to include Starting Row in instance ID
--      Added phDriveSegMediaType and phDriveSegInterfaceType
--      Added loDriveSegMediaType and loDriveSegInterfaceType
--      Renamed phGeneralInfo.numMediaTypes to numElementDomains (still integer)
--      Revision 1.1 2002/08/12 09:53:03EDT jbruegger 
--      Initial revision
--      Member imported to project e:/mks/projects/mib/mib.pj
--

ADIC-MANAGEMENT-MIB
  
DEFINITIONS ::= BEGIN

IMPORTS                                                 
    Gauge, 
    IpAddress    
                FROM RFC1155-SMI
    OBJECT-TYPE                 
                FROM RFC-1212
    DisplayString            
                FROM RFC1213-MIB 
   TRAP-TYPE                
                FROM RFC-1215 

-- **********************************************************
-- *                                                        *
-- * Imports from ADIC-INTELLIGENT-STORAGE-MIB              *
-- *                                                        *
-- **********************************************************
-- ADIC enterprises ID
   --adic,
-- OID Hierarchy
   		hardware , 
		componentId,
-- Common Trap Payload Objects
        trapSequenceNumber ,
        trapSeverity ,
        trapSummaryText ,  
        trapIntendedUsage ,
--Type assignments
        AdicEnable,
    	AdicAgentStatus,
    	AdicOnlineStatus,
    	--AdicGlobalId ,
    	AdicInterfaceType ,
    	AdicDateAndTime ,
    	AdicMibVersion , 
    	AdicComponentType ,
    	RowStatus ,
    	AdicDoorStatus ,
    	AdicREDIdentifier
    			FROM ADIC-INTELLIGENT-STORAGE-MIB;     

-- **********************************************************
-- *                                                        *
-- * ADIC MANAGEMENT MIB Definitions                        *
-- *                                                        *
-- **********************************************************

-- the mcb node can be located anywhere in the hierarchy
    management     				OBJECT IDENTIFIER    ::= { hardware 20 }
--
    globalStatus				OBJECT IDENTIFIER    ::= { management  10 }
    globalEthernetManager		OBJECT IDENTIFIER    ::= { management  15 }
    systemManager				OBJECT IDENTIFIER    ::= { management  20 }
	persistentData				OBJECT IDENTIFIER    ::= { management  30 }
	security					OBJECT IDENTIFIER    ::= { management  40 }
	licensing 					OBJECT IDENTIFIER    ::= { management  50 }  
	eventManager				OBJECT IDENTIFIER    ::= { management  70 }
	physicalLibrary				OBJECT IDENTIFIER    ::= { management  80 }
	logicalLibrary				OBJECT IDENTIFIER    ::= { management  90 }
	ras							OBJECT IDENTIFIER    ::= { management 100 }

-- **********************************************************
-- *                                                        *
-- * ADIC MCB MIB Textual Conventions                       *
-- *                                                        *
-- **********************************************************

-- a truth value
	Boolean ::=   INTEGER { true(1), false(2) }

-- Ethernet port definitions
    AdicEthernetSpeed ::= INTEGER { baseT10(1) , baseT100(2) }
    
	AdicBarCode ::= DisplayString  
	AdicSegmentType ::= INTEGER{ gripper(1) , storage(2) , ie(3) , drive(4) }
	
	AdicInstallStatus ::= INTEGER { ok(1) , inProgress(2) , failed(3) , updateAborted(4) }

	-- Fibre Channel Port definitions
	AdicFcPortType ::= INTEGER { auto(1) , nPort(2) , nlPort(3) }
    AdicFcPortSpeed ::= INTEGER { auto(1) , megabits1000(1000) , megabits2000(2000)  }

	-- RAS definitions
	AdicStatusGroup ::= INTEGER { connectivity(1), control(2), cooling(3), drivesAndMedia(4), 
	                              power(5), robotics(6), all(99) }	
	AdicStatusGroupState ::= INTEGER { good(1), failed(2), degraded(3), warning(4), 
	                                   informational(5), unknown(6), invalid(7) }	
    AdicRasTicketState ::= INTEGER { new(1), open(2), suspended(3), closed(4), verified(5), all(99) }
	AdicFruSerialNumber ::= DisplayString ( SIZE( 0 .. 40 ) )
    AdicRasTicketSeverity ::= INTEGER { high(1), medium(2), low(3) }

	
-- ***************************************************************** 
-- 
-- MCB Global Status Group 
-- 
-- ***************************************************************** 
    globalStatusTable OBJECT-TYPE 
        SYNTAX SEQUENCE OF GlobalStatusEntry 
        ACCESS not-accessible 
        STATUS mandatory 
        DESCRIPTION 
            ""
        ::= { globalStatus 10 }

    globalStatusEntry OBJECT-TYPE 
        SYNTAX GlobalStatusEntry 
        ACCESS not-accessible 
        STATUS mandatory 
        DESCRIPTION 
            "" 
        INDEX { componentId } 
        ::= { globalStatusTable 1 } 

        GlobalStatusEntry ::= 
            SEQUENCE {  
                role					    INTEGER ,
                status					    AdicAgentStatus ,
                systemDateAndTime		    AdicDateAndTime ,
                networkTimeServer1		    IpAddress ,
                networkTimeProtocol		    INTEGER ,  
                networkTimeEnable		    AdicEnable ,
                managementMibVersion	    AdicMibVersion ,
                enableDaylightSavingsTime   AdicEnable ,
                networkTimeServer2		    IpAddress                 
            }
--
-- Begin definitions
--
    role  OBJECT-TYPE
       SYNTAX INTEGER { master(1) , slave(2) }
       ACCESS read-only
       STATUS mandatory
       DESCRIPTION
            "The role of this MCB in the
            management hierarchy."
       ::= { globalStatusEntry 1 }

    status  OBJECT-TYPE
       SYNTAX AdicAgentStatus
       ACCESS read-only
       STATUS mandatory
       DESCRIPTION
            "Status of this MCB."
       ::= { globalStatusEntry 2 }

    systemDateAndTime  OBJECT-TYPE
       SYNTAX AdicDateAndTime
       ACCESS read-write
       STATUS mandatory
       DESCRIPTION
            "Current time as set on system realtime
            clock.  Also allows system realtime clock 
            to be set."
       ::= { globalStatusEntry 3 }  
 
    networkTimeServer1 OBJECT-TYPE
       SYNTAX IpAddress
       ACCESS read-write
       STATUS mandatory
       DESCRIPTION
            "IP address of the time server to be used."
       ::= { globalStatusEntry 4 }

    networkTimeProtocol OBJECT-TYPE
       SYNTAX INTEGER { ntp(1) }
       ACCESS read-write
       STATUS mandatory
       DESCRIPTION
            "Protocol to use when with network time server."
       ::= { globalStatusEntry 5 }   

    networkTimeEnable OBJECT-TYPE
       SYNTAX AdicEnable
       ACCESS read-write
       STATUS mandatory
       DESCRIPTION
            "Enable/disabled the use of a network time server."
       ::= { globalStatusEntry 6 }          

    managementMibVersion	OBJECT-TYPE
       SYNTAX AdicMibVersion
       ACCESS read-only
       STATUS mandatory
       DESCRIPTION
            "Version of the ADIC-MANAGEMENT-MIB on which this
            agent is based."
       ::= { globalStatusEntry 7 }

    enableDaylightSavingsTime	OBJECT-TYPE
       SYNTAX AdicEnable
       ACCESS read-write
       STATUS mandatory
       DESCRIPTION
            "Enable automatic adjustment of the system date
            and time for daylight savings time."
       ::= { globalStatusEntry 8 }

    networkTimeServer2 OBJECT-TYPE
       SYNTAX IpAddress
       ACCESS read-write
       STATUS mandatory
       DESCRIPTION
            "IP address of the second time server to be used. 
            Multiple time servers may be used for redundancy
            and (or) improved time accuracy."
       ::= { globalStatusEntry 9 }
       
-- TODO: Add LED read-write control

-- ***************************************************************** 
-- 
-- MCB Global Ethernet Manager Group 
-- 
-- ***************************************************************** 
    globalEthernetTable OBJECT-TYPE 
        SYNTAX SEQUENCE OF GlobalEthernetEntry 
        ACCESS not-accessible 
        STATUS mandatory 
        DESCRIPTION 
            "Some Ethernet settings/switches.  Routing tables
            are part of MIB-II, so we don't include them here."
        ::= { globalEthernetManager 10 }

    globalEthernetEntry OBJECT-TYPE 
        SYNTAX GlobalEthernetEntry 
        ACCESS not-accessible 
        STATUS mandatory 
        DESCRIPTION 
            "" 
        INDEX { componentId } 
        ::= { globalEthernetTable 1 } 

        GlobalEthernetEntry ::= 
            SEQUENCE {
            	mcbHostName		      DisplayString ,
            	ipAddress		      IpAddress ,
            	dhcpStatus		      AdicEnable ,
            	ipAddressSubnetMask   IpAddress ,
            	speedAutoNegotiation  AdicEnable ,
            	preferredSpeed        AdicEthernetSpeed ,
            	actualSpeed           AdicEthernetSpeed ,
            	ethernetDuplex        INTEGER
            }
--
-- Begin definitions
--
    mcbHostName OBJECT-TYPE
       SYNTAX DisplayString
       ACCESS read-write
       STATUS mandatory
       DESCRIPTION
            "Host name of this MCB."
       ::= { globalEthernetEntry 1 }

    ipAddress OBJECT-TYPE
       SYNTAX IpAddress
       ACCESS read-write
       STATUS mandatory
       DESCRIPTION
            "IP Address of this MCB's external Ethernet port."
       ::= { globalEthernetEntry 2 }

    dhcpStatus  OBJECT-TYPE
       SYNTAX AdicEnable
       ACCESS read-write
       STATUS mandatory
       DESCRIPTION
            "State of DHCP support."
       ::= { globalEthernetEntry 3 }     

    ipAddressSubnetMask OBJECT-TYPE
       SYNTAX IpAddress
       ACCESS read-write
       STATUS mandatory
       DESCRIPTION
           "Read-Write version of MIB-II ipAdEntNetMask Object.
           
              ** Description clause from MIB-II text **
           The subnet mask associated with the IP address of
           this entry.  The value of the mask is an IP
           address with all the network bits set to 1 and all
           the hosts bits set to 0."
       ::= { globalEthernetEntry 4 }            

    speedAutoNegotiation  OBJECT-TYPE
       SYNTAX AdicEnable
       ACCESS read-write
       STATUS mandatory
       DESCRIPTION
            "Enables/disables automatic Ehternet speed 
            negotiation."
       ::= { globalEthernetEntry 5 }
                                          
    preferredSpeed  OBJECT-TYPE
       SYNTAX AdicEthernetSpeed
       ACCESS read-write
       STATUS mandatory
       DESCRIPTION
            "The preferred Ethernet speed for this
            Ethernet port."
       ::= { globalEthernetEntry 6 }
       
    actualSpeed  OBJECT-TYPE
       SYNTAX AdicEthernetSpeed
       ACCESS read-only
       STATUS mandatory
       DESCRIPTION
            "The actual (negotiated) speed for this
            Ethernet port."
       ::= { globalEthernetEntry 7 }

    ethernetDuplex  OBJECT-TYPE
       SYNTAX INTEGER { half(1) , full(2) }
       ACCESS read-write
       STATUS mandatory
       DESCRIPTION
            "The duplex setting for this Ethernet port."
       ::= { globalEthernetEntry 8 }
                                                 
-- ***************************************************************** 
-- 
-- MCB System Manager Group 
-- 
-- ***************************************************************** 
    systemManagerTable OBJECT-TYPE 
        SYNTAX SEQUENCE OF SystemManagerEntry 
        ACCESS not-accessible 
        STATUS mandatory 
        DESCRIPTION 
            ""
        ::= { systemManager 10 }

    systemManagerEntry OBJECT-TYPE 
        SYNTAX SystemManagerEntry 
        ACCESS not-accessible 
        STATUS mandatory 
        DESCRIPTION 
            "The MCB System Manager (MSM) provides the high level 
            system management of the MCB.  The primary role of the
            MSM is to configure, initialize, and maintain the 
            software processes running on the MCB." 
        INDEX { componentId , softwareComponentIndex } 
        ::= { systemManagerTable 1 } 

        SystemManagerEntry ::= 
            SEQUENCE {  
            	softwareComponentIndex	INTEGER ,
                processRowStatus		RowStatus ,
                processPhysicalMemory	INTEGER ,
                processResidentMemory   INTEGER
            }
--
-- Begin definitions
--
    softwareComponentIndex  OBJECT-TYPE
       SYNTAX INTEGER 
       ACCESS read-only
       STATUS mandatory
       DESCRIPTION
            "Identifies which piece of MCB software
            is being addressed."
       ::= { systemManagerEntry 1 }
       
    processRowStatus  OBJECT-TYPE
       SYNTAX RowStatus
       ACCESS read-write
       STATUS mandatory
       DESCRIPTION
            "Row status object for creating/deleting 
            system components."
       ::= { systemManagerEntry 2 } 

    processPhysicalMemory  OBJECT-TYPE
       SYNTAX INTEGER 
       ACCESS read-only
       STATUS mandatory
       DESCRIPTION
            "The size in kilobytes of the actual software 
            process binary."
       ::= { systemManagerEntry 3 }
       
    processResidentMemory  OBJECT-TYPE
       SYNTAX INTEGER 
       ACCESS read-only
       STATUS mandatory
       DESCRIPTION
            "The size in kilobytes of the software process
            portion that is currently resident in memory."
       ::= { systemManagerEntry 4 }

   -- ***************************************************************** 
   -- 
   -- Component Software Installation Table
   -- 
   -- ***************************************************************** 
    softwareInstallationTable OBJECT-TYPE 
        SYNTAX SEQUENCE OF SoftwareInstallationEntry 
        ACCESS not-accessible 
        STATUS mandatory 
        DESCRIPTION 
            "This table controls installation of software
            packages/updates."
        ::= { systemManager 20 }

    softwareInstallationEntry OBJECT-TYPE 
        SYNTAX SoftwareInstallationEntry 
        ACCESS not-accessible 
        STATUS mandatory 
        DESCRIPTION 
            "" 
        INDEX { componentId } 
        ::= { softwareInstallationTable 1 } 

        SoftwareInstallationEntry ::= 
            SEQUENCE {  
            	installPackageName      DisplayString ,
                installProcessStatus        INTEGER ,
                installCommand              INTEGER ,
                installStatusText           DisplayString ,
                currentFirmwareVersion      DisplayString ,
                previousFirmwareVersion     DisplayString ,
                downloadedFirmwareVersion   DisplayString ,
                componentsInBundle          INTEGER ,
                mcbInstallStatusText        DisplayString , 
                cmbInstallStatusText        DisplayString ,
                rcuInstallStatusText        DisplayString ,
                fcbInstallStatusText        DisplayString ,
                amcInstallStatusText        DisplayString ,
                mcbInstallProcessStatus     AdicInstallStatus ,
                cmbInstallProcessStatus     AdicInstallStatus ,
                rcuInstallProcessStatus     AdicInstallStatus ,
                fcbInstallProcessStatus     AdicInstallStatus ,
                amcInstallProcessStatus     AdicInstallStatus 
            }
--
-- Begin definitions
--
    installPackageName  OBJECT-TYPE
       SYNTAX DisplayString 
       ACCESS read-write
       STATUS mandatory
       DESCRIPTION
            "Filename and path of the package to be installed.
            The management application writes the filename here,
            which initiates the update process."
       ::= { softwareInstallationEntry 1 }

    installProcessStatus  OBJECT-TYPE
       SYNTAX INTEGER { ok(1) , inProgress(2) , failed(3) ,
                        updateAborted(4) } 
       ACCESS read-only
       STATUS mandatory
       DESCRIPTION
            "ok - installation successful - this is the intial state
            inProgress - software package in being installed
            failed - software package installation failed.  The
                     status should return failed until another
                     write to installPackageFilename.
            updateAborted - software installation was cancel and system
               reverts back to previous version"
       ::= { softwareInstallationEntry 2 }       

    installCommand  OBJECT-TYPE 
       SYNTAX INTEGER { download(1) , install(2) , abort(3), timeEstimate(4) } 
       ACCESS read-write
       STATUS mandatory
       DESCRIPTION
            "download - copy firmware bundle to MCB but do not install
            install - commence installation (could be current bundle or 
               previously downloaded bundle)
            abort - abort installation in progress 
            rollback - rollback to the previous version of the system
               identified by the value in the previousFirmwareVersion field.
            timeEstimate - provides a estimate on the overall download time 
               for a previously downloaded bundle"
       ::= { softwareInstallationEntry 3 }   

    installStatusText  OBJECT-TYPE
       SYNTAX DisplayString (SIZE (0..80)) 
       ACCESS read-only
       STATUS mandatory
       DESCRIPTION
            "Indicates time to complete the entire installation:  
             example: Estimated time to complete download xx minutes"
            
       ::= { softwareInstallationEntry 4 }  

    currentFirmwareVersion  OBJECT-TYPE
       SYNTAX DisplayString 
       ACCESS read-only
       STATUS mandatory
       DESCRIPTION
            "Firmware revision currently on the i2000."
       ::= { softwareInstallationEntry 5 }

    previousFirmwareVersion  OBJECT-TYPE
       SYNTAX DisplayString 
       ACCESS read-only
       STATUS mandatory
       DESCRIPTION
            "Previous firmware revision on the i2000 that is 
            available for rollback."
       ::= { softwareInstallationEntry 6 }

    downloadedFirmwareVersion  OBJECT-TYPE
       SYNTAX DisplayString 
       ACCESS read-only
       STATUS mandatory
       DESCRIPTION
            "Identifier for a the bundle that was previously
            downloaded to the i2000 but not installed."
       ::= { softwareInstallationEntry 7 }

    componentsInBundle  OBJECT-TYPE
       SYNTAX INTEGER
       ACCESS read-only
       STATUS mandatory
       DESCRIPTION
            "Identifies the components being installed with this bundle
             **********************************************************
             (LSB) bit 0 - MCB 
                   bit 1 - CMB
                   bit 2 - RCU
                   bit 3 - FCB
                   bit 4 - AMC"
       ::= { softwareInstallationEntry 8}

    mcbInstallStatusText  OBJECT-TYPE
       SYNTAX DisplayString (SIZE (0..128)) 
       ACCESS read-only
       STATUS mandatory
       DESCRIPTION
            "Provides detailed information about the MCB component install
             Example:
                 download status (inprogress, complete, failed, not being upgraded) : current component : time to complete MCB"
       ::= { softwareInstallationEntry 9 }

    cmbInstallStatusText  OBJECT-TYPE
       SYNTAX DisplayString (SIZE (0..128)) 
       ACCESS read-only
       STATUS mandatory
       DESCRIPTION
            "Provides detailed information about the CMB component install
             Example:
                 download status (inprogress, complete, failed, not being upgraded) : current CMB : time to complete CMB/s"
       ::= { softwareInstallationEntry 10 }       

    rcuInstallStatusText  OBJECT-TYPE
       SYNTAX DisplayString (SIZE (0..128)) 
       ACCESS read-only
       STATUS mandatory
       DESCRIPTION
            "Provides detailed information about the RCU component install
             Example:
                 download status (inprogress, complete, failed, not being upgraded) : current component : time to complete RCU"
       ::= { softwareInstallationEntry 11 }       

    fcbInstallStatusText  OBJECT-TYPE
       SYNTAX DisplayString (SIZE (0..128)) 
       ACCESS read-only
       STATUS mandatory
       DESCRIPTION
            "Provides detailed information about the FCB component install
             Example:
                 download status (inprogress, complete, failed, not being upgraded) : current fcb : time to complete FCB/s"
       ::= { softwareInstallationEntry 12 }       

    amcInstallStatusText  OBJECT-TYPE
       SYNTAX DisplayString (SIZE (0..128)) 
       ACCESS read-only
       STATUS mandatory
       DESCRIPTION
            "Provides detailed information about the AMC component install
             Example:
                 download status (inprogress, complete, failed, not being upgraded) : current component : time to complete AMC"

       ::= { softwareInstallationEntry 13 }   

    mcbInstallProcessStatus  OBJECT-TYPE
       SYNTAX AdicInstallStatus
       ACCESS read-only
       STATUS mandatory
       DESCRIPTION
            ""
       ::= { softwareInstallationEntry 14 }       

    cmbInstallProcessStatus  OBJECT-TYPE
       SYNTAX AdicInstallStatus
       ACCESS read-only
       STATUS mandatory
       DESCRIPTION
            ""
       ::= { softwareInstallationEntry 15 }
       
    rcuInstallProcessStatus  OBJECT-TYPE
       SYNTAX AdicInstallStatus
       ACCESS read-only
       STATUS mandatory
       DESCRIPTION
            ""
       ::= { softwareInstallationEntry 16 }       
       
    fcbInstallProcessStatus  OBJECT-TYPE
       SYNTAX AdicInstallStatus
       ACCESS read-only
       STATUS mandatory
       DESCRIPTION
            ""
       ::= { softwareInstallationEntry 17 }

    amcInstallProcessStatus  OBJECT-TYPE
       SYNTAX AdicInstallStatus
       ACCESS read-only
       STATUS mandatory
       DESCRIPTION
            ""
       ::= { softwareInstallationEntry 18 }
                     
-- ***************************************************************** 
-- 
-- MCB Persistent Data Group 
-- 
-- ***************************************************************** 
    persistentDataTable OBJECT-TYPE 
        SYNTAX SEQUENCE OF PersistentDataEntry 
        ACCESS not-accessible 
        STATUS mandatory 
        DESCRIPTION 
            ""
        ::= { persistentData 10 }

    persistentDataEntry OBJECT-TYPE 
        SYNTAX PersistentDataEntry 
        ACCESS not-accessible 
        STATUS mandatory 
        DESCRIPTION 
            "" 
        INDEX { componentId } 
        ::= { persistentDataTable 1 } 

        PersistentDataEntry ::= 
            SEQUENCE {  
            	capacity		INTEGER ,
                freeSpace		INTEGER
            }
--
-- Begin definitions
--
    capacity  OBJECT-TYPE
       SYNTAX INTEGER 
       ACCESS read-only
       STATUS mandatory
       DESCRIPTION
            "The number of kilobytes of file space
            on this MCB."
       ::= { persistentDataEntry 1 }

    freeSpace  OBJECT-TYPE
       SYNTAX INTEGER 
       ACCESS read-only
       STATUS mandatory
       DESCRIPTION
            "The number of kilobytes of availble (unused)
            file space on this MCB."
       ::= { persistentDataEntry 2 }  
       
-- ***************************************************************** 
-- 
-- MCB Security Group 
-- 
-- ***************************************************************** 

	-- ***************************************************************** 
	-- 
	-- MCB User Table 
	-- 
	-- ***************************************************************** 
    userTable OBJECT-TYPE 
        SYNTAX SEQUENCE OF UserEntry 
        ACCESS not-accessible 
        STATUS obsolete 
        DESCRIPTION 
            "** This table is obsolete. **"
        ::= { security 20 }

    userEntry OBJECT-TYPE 
        SYNTAX UserEntry 
        ACCESS not-accessible 
        STATUS obsolete
        DESCRIPTION 
            "** This entry object is obsolete. **" 
        INDEX { componentId , userName  } 
        ::= { userTable 1 } 

        UserEntry ::= 
            SEQUENCE {              
            	userName				DisplayString ,
            	userRowStatus			RowStatus , 
            	userGroup				DisplayString , 
            	userPassword			DisplayString ,
            	userLibAccessList		DisplayString
            }

    userName  OBJECT-TYPE
       SYNTAX DisplayString
       ACCESS read-write
       STATUS obsolete
       DESCRIPTION
            "** This object is obsolete. ** 
            User's name."
       ::= { userEntry 1 }

    userRowStatus  OBJECT-TYPE
       SYNTAX RowStatus
       ACCESS read-write
       STATUS obsolete
       DESCRIPTION
            "** This object is obsolete. **
            Standard Row Status object. Used primarily to
            delete users."
       ::= { userEntry 2 }
              
    userGroup  OBJECT-TYPE
       SYNTAX DisplayString
       ACCESS read-write
       STATUS obsolete
       DESCRIPTION
            "** This object is obsolete. **
            User's group."
       ::= { userEntry 3 }                   

    userPassword  OBJECT-TYPE
       SYNTAX DisplayString
       ACCESS read-write
       STATUS obsolete
       DESCRIPTION
            "** This object is obsolete. **
            User's password."
       ::= { userEntry 4 }

    userLibAccessList  OBJECT-TYPE
       SYNTAX DisplayString
       ACCESS read-write
       STATUS obsolete
       DESCRIPTION
            "** This object is obsolete. **
            Delimited list of logical library identifiers
            to which this use has access."
       ::= { userEntry 5 }
       
--
-- Begin definitions
--
                          
-- ***************************************************************** 
-- 
-- MCB Licensing Group 
-- 
-- ***************************************************************** 
	-- ***************************************************************** 
	-- 
	-- MCB License Key Table
	--
	-- A list of license keys in the license database.  Includes
	-- a row status object to create/destroy entries in the database.
	-- 
	-- ***************************************************************** 
    licenseKeyTable OBJECT-TYPE 
        SYNTAX SEQUENCE OF LicenseKeyEntry 
        ACCESS not-accessible 
        STATUS mandatory 
        DESCRIPTION 
            ""
        ::= { licensing 10 }

    licenseKeyEntry OBJECT-TYPE 
        SYNTAX LicenseKeyEntry 
        ACCESS not-accessible 
        STATUS mandatory 
        DESCRIPTION 
            "" 
        INDEX { componentId , licenseKeyIndex } 
        ::= { licenseKeyTable 1 } 

        LicenseKeyEntry ::= 
            SEQUENCE {
            	licenseKeyIndex				INTEGER ,
            	licenseKeyRowStatus			RowStatus,
            	key							DisplayString , 
            	licenseKeyDuration			INTEGER ,
            	licenseKeyExpirationDate	AdicDateAndTime ,
            	licenseKeyAppliedDate       AdicDateAndTime
            }
--
-- Begin definitions
--
    licenseKeyIndex  OBJECT-TYPE
       SYNTAX INTEGER 
       ACCESS read-only
       STATUS mandatory
       DESCRIPTION
            "Ordinal inde for this table. 
            Identifies a license key database entry.
            Each key may enable multiple features.  A
            list of features enabled by each key can be
            found in the licenseFeatureTable."
       ::= { licenseKeyEntry 1 }

    licenseKeyRowStatus  OBJECT-TYPE
       SYNTAX RowStatus
       ACCESS read-write
       STATUS mandatory
       DESCRIPTION
            "Controls creation/deletion of rows in the 
            license key database."
       ::= { licenseKeyEntry 2 }

    key  OBJECT-TYPE
       SYNTAX DisplayString
       ACCESS read-write
       STATUS mandatory
       DESCRIPTION
            "The license key string."
       ::= { licenseKeyEntry 3 }

    licenseKeyDuration  OBJECT-TYPE
       SYNTAX INTEGER { permanent(1) , transient(2) }
       ACCESS read-only
       STATUS mandatory
       DESCRIPTION
            "Is this license key permanent or transient?
            Permanent keys have no expiration date, transient
            keys expire at the time found in the licenseKeyExpirationDate 
            object."
       ::= { licenseKeyEntry 4 }

    licenseKeyExpirationDate  OBJECT-TYPE
       SYNTAX AdicDateAndTime
       ACCESS read-only
       STATUS mandatory
       DESCRIPTION
            "Exact date and time when this license
            key expires.  Has no meaning if license 
            key is permanent."
       ::= { licenseKeyEntry 5 }   

    licenseKeyAppliedDate  OBJECT-TYPE
       SYNTAX AdicDateAndTime
       ACCESS read-only
       STATUS mandatory
       DESCRIPTION
            "Date and time when the license key 
            was applied.  This field indicates the
            chronological order in which the keys
            were applied.  If multiple keys enable
            the same feature, the most recent key 
            supercedes older keys."
       ::= { licenseKeyEntry 6 }
       
	-- ***************************************************************** 
	-- 
	-- MCB License Feature Table
	--
	-- A list of features which each key enables 
	-- 
	-- ***************************************************************** 
    licenseFeatureTable OBJECT-TYPE 
        SYNTAX SEQUENCE OF LicenseFeatureEntry 
        ACCESS not-accessible 
        STATUS mandatory 
        DESCRIPTION 
            "This table is a list of all features
            activated by a particular license key."
        ::= { licensing 20 }

    licenseFeatureEntry OBJECT-TYPE 
        SYNTAX LicenseFeatureEntry 
        ACCESS not-accessible 
        STATUS mandatory 
        DESCRIPTION 
            "" 
        INDEX { componentId , licenseKeyIndex , licenseFeatureIndex } 
        ::= { licenseFeatureTable 1 } 

        LicenseFeatureEntry ::= 
            SEQUENCE {
            	licenseFeatureIndex      INTEGER ,
            	featureName              DisplayString ,
            	licenseFeatureQuantity   INTEGER
            }
--
-- Begin definitions
--
    licenseFeatureIndex  OBJECT-TYPE
       SYNTAX INTEGER 
       ACCESS read-only
       STATUS mandatory
       DESCRIPTION
            "Feature index for this table, as well as 
            licensable feature table.  If a feature is
            not licensed, the row corresponding to that 
            feature does not appear here, but it does 
            appear in the licensableFeatureTable, as do
            all licensableFeatures."
       ::= { licenseFeatureEntry 1 }

    featureName  OBJECT-TYPE
       SYNTAX DisplayString
       ACCESS read-only
       STATUS mandatory
       DESCRIPTION
            "Name of the ADIC licensed feature enable
            by this row's license key.  The key is 
            specified by the value of licenseKeyIndex."
       ::= { licenseFeatureEntry 2 }

    licenseFeatureQuantity  OBJECT-TYPE
       SYNTAX INTEGER
       ACCESS read-only
       STATUS mandatory
       DESCRIPTION
            "The quantity of this licensed feature 
            enabled by this license key, if applicable.  
            For example, a license key which enables 1000 slots
            of Capacity-on-Demand storage would have 
            quantity = 1000.  For features which are not
            licensed by quantity, return 0."
       ::= { licenseFeatureEntry 3 }
       
	-- ***************************************************************** 
	-- 
	-- MCB Licensable Feature Table
	--
	-- A list of ALL licensable features
	-- Defines the mapping of licenseFatureIndex to feature name
	-- 
	-- ***************************************************************** 
    licensableFeatureTable OBJECT-TYPE 
        SYNTAX SEQUENCE OF LicensableFeatureEntry 
        ACCESS not-accessible 
        STATUS mandatory 
        DESCRIPTION 
            "This table is a list of all licensable features.
            It defines the mapping between a feature name
            and its licenseFeatureIndex."
        ::= { licensing 30 }

    licensableFeatureEntry OBJECT-TYPE 
        SYNTAX LicensableFeatureEntry 
        ACCESS not-accessible 
        STATUS mandatory 
        DESCRIPTION 
            "" 
        INDEX { componentId , licenseFeatureIndex } 
        ::= { licensableFeatureTable 1 } 

        LicensableFeatureEntry ::= 
            SEQUENCE {
            	licensableFeatureName      DisplayString ,
            	totalQuantityLicensed      INTEGER
            }   
--
-- Begin definitions
--
    licensableFeatureName  OBJECT-TYPE
       SYNTAX DisplayString
       ACCESS read-only
       STATUS mandatory
       DESCRIPTION
            "Name of the ADIC licensable feature to be 
            displayed to the user."
       ::= { licensableFeatureEntry 1 }    

    totalQuantityLicensed  OBJECT-TYPE
       SYNTAX INTEGER
       ACCESS read-only
       STATUS mandatory
       DESCRIPTION
            "The total licensed quantity for this feature.
            For features which are licensed by quantity,
            this object returns the sum of the indiviual
            quantities enabled by each license key (see
            licenseFeatureQuantity).  For example, if 
            there were two COD license keys installed, one 
            for 500 slots and one for 1000 slots, 
            totalQuantityLicensed would return 1500."
       ::= { licensableFeatureEntry 2 }    
       
-- ***************************************************************** 
-- 
-- MCB Event Manager Group 
-- 
-- ***************************************************************** 

	-- ***************************************************************** 
	-- 
	-- Notification (trap) Registration Table
	-- 
	-- ***************************************************************** 
    registrationTable OBJECT-TYPE 
        SYNTAX SEQUENCE OF RegistrationEntry 
        ACCESS not-accessible 
        STATUS mandatory 
        DESCRIPTION 
            ""
        ::= { eventManager 10 }

    registrationEntry OBJECT-TYPE 
        SYNTAX RegistrationEntry 
        ACCESS not-accessible 
        STATUS mandatory 
        DESCRIPTION 
            "" 
        INDEX { componentId , hostIpAddress , udpPort  } 
        ::= { registrationTable 1 } 

        RegistrationEntry ::= 
            SEQUENCE { 
            	hostIpAddress			IpAddress ,
            	udpPort					INTEGER ,
            	registrationRowStatus	RowStatus
            }
--
-- Begin definitions
--     
    hostIpAddress  OBJECT-TYPE
       SYNTAX IpAddress
       ACCESS read-write
       STATUS mandatory
       DESCRIPTION
            "Host IP address to which SNMP traps will be 
            sent/forwarded."
       ::= { registrationEntry 1 }

    udpPort  OBJECT-TYPE
       SYNTAX INTEGER
       ACCESS read-write
       STATUS mandatory
       DESCRIPTION
            "UDP Port number on which to send/forward 
            SNMP traps."
       ::= { registrationEntry 2 }
       
    registrationRowStatus  OBJECT-TYPE
       SYNTAX RowStatus
       ACCESS read-write
       STATUS mandatory
       DESCRIPTION
            "Controls creation/deletion of rows in the 
            notification (trap registration) table."
       ::= { registrationEntry 3 }     
 
-- ***************************************************************** 
-- 
-- Event Log Table
-- 
-- ***************************************************************** 
    logTable OBJECT-TYPE 
        SYNTAX SEQUENCE OF LogEntry 
        ACCESS not-accessible 
        STATUS optional 
        DESCRIPTION 
            "** This table is optional **
            Management functionality for general
            event logging.  Log entries are not 
            necessarily available via SNMP."
        ::= { eventManager 20 }

    logEntry OBJECT-TYPE 
        SYNTAX LogEntry 
        ACCESS not-accessible 
        STATUS optional 
        DESCRIPTION 
            "** This entry object is optional **" 
        INDEX { componentId , logName } 
        ::= { logTable 1 } 

        LogEntry ::= 
            SEQUENCE {
            	logName			DisplayString 
            }
--
-- Begin definitions
--
    logName  OBJECT-TYPE
       SYNTAX DisplayString
       ACCESS read-only
       STATUS optional
       DESCRIPTION
            "** This object is optional. **
            Name of the log to be accessed."
       ::= { logEntry 1 }

-- ***************************************************************** 
-- 
-- Log Snapshot Table
-- 
-- ***************************************************************** 
    logSnapshotTable OBJECT-TYPE 
        SYNTAX SEQUENCE OF LogSnapshotEntry 
        ACCESS not-accessible 
        STATUS optional
        DESCRIPTION 
            "** This table is optional. **
            Management functionality for generating 
            a snapshot archive containing all of the
            system logs"
        ::= { eventManager 30 }
 
    logSnapshotEntry OBJECT-TYPE 
        SYNTAX LogSnapshotEntry 
        ACCESS not-accessible 
        STATUS optional 
        DESCRIPTION 
            "** This entry object is optional. **" 
        INDEX { componentId } 
        ::= { logSnapshotTable 1 } 
 
        LogSnapshotEntry ::= 
            SEQUENCE {
               logSnapshotCommand   INTEGER 
            }
--
-- Begin definitions
--
    logSnapshotCommand  OBJECT-TYPE
       SYNTAX INTEGER { retrieveLogs(1) }
       ACCESS read-write
       STATUS optional
       DESCRIPTION
            "** This object is optional. **
            Commands are:
            **********************
            retrieveLogs - Gather snapshots of various
                         system logs in preparation to 
                         build snapshot archive file."
       ::= { logSnapshotEntry 1 }

-- ***************************************************************** 
-- 
-- MCB Physical Library Group 
-- 
-- *****************************************************************  

    phGeneralInfoTable OBJECT-TYPE 
        SYNTAX SEQUENCE OF PhGeneralInfoEntry 
        ACCESS not-accessible 
        STATUS mandatory 
        DESCRIPTION 
            ""
        ::= { physicalLibrary 10 }

    phGeneralInfoEntry OBJECT-TYPE 
        SYNTAX PhGeneralInfoEntry 
        ACCESS not-accessible 
        STATUS mandatory 
        DESCRIPTION 
            "" 
        INDEX { componentId  } 
        ::= { phGeneralInfoTable 1 } 

        PhGeneralInfoEntry ::= 
            SEQUENCE {
            	numElementDomains		INTEGER ,
            	numPhSlots				INTEGER ,
            	numPhIESlots			INTEGER ,
            	numPhDrives				INTEGER ,
            	onlineStatus			AdicOnlineStatus ,  
            	readiness				INTEGER ,
            	autoInventoryMode   	AdicEnable ,
            	autoCalibrateMode		AdicEnable ,
            	autoConfigureMode		AdicEnable ,
            	numPhAisles				INTEGER ,
            	operatingMode			INTEGER ,
            	numStorageCartridges	INTEGER ,
            	numCleaningCartridges	INTEGER ,
            	physLibraryManagerLun   INTEGER ,
            	physLibraryAutoCleaning AdicEnable ,
            	physLibraryDoorStatus   AdicDoorStatus ,
            	numPhFrames             INTEGER ,
            	totalRawCapacity        INTEGER ,
            	totalFreeCapacity       INTEGER ,
            	totalUsedCapacity       INTEGER ,
            	logicalSNAdressingMode  AdicEnable
           }
	--
	-- Begin library scalars definitions
	--
    numElementDomains  OBJECT-TYPE
       SYNTAX INTEGER
       ACCESS read-only
       STATUS mandatory
       DESCRIPTION
            "Number of element domains (such as DLT, LTO, 8mm, etc.) 
            currently installed in this physical library."
       ::= { phGeneralInfoEntry 1 }
 
     numPhSlots  OBJECT-TYPE
       SYNTAX INTEGER
       ACCESS read-only
       STATUS mandatory
       DESCRIPTION
            ""
       ::= { phGeneralInfoEntry 2 }

    numPhIESlots  OBJECT-TYPE
       SYNTAX INTEGER
       ACCESS read-only
       STATUS mandatory
       DESCRIPTION
            ""
       ::= { phGeneralInfoEntry 3 }
  
    numPhDrives  OBJECT-TYPE
       SYNTAX INTEGER
       ACCESS read-only
       STATUS mandatory
       DESCRIPTION
            ""
       ::= { phGeneralInfoEntry 4 }

    onlineStatus  OBJECT-TYPE
       SYNTAX AdicOnlineStatus
       ACCESS read-write
       STATUS mandatory
       DESCRIPTION
            ""
       ::= { phGeneralInfoEntry 5 }      
       
    readiness  OBJECT-TYPE
       SYNTAX INTEGER { ready(1) , notReady(2) }
       ACCESS read-only
       STATUS mandatory
       DESCRIPTION
            ""
       ::= { phGeneralInfoEntry 6 }      

    autoInventoryMode  OBJECT-TYPE
       SYNTAX AdicEnable 
       ACCESS read-write
       STATUS mandatory
       DESCRIPTION
            ""
       ::= { phGeneralInfoEntry 7 }   

    autoCalibrateMode  OBJECT-TYPE
       SYNTAX AdicEnable 
       ACCESS read-write
       STATUS mandatory
       DESCRIPTION
            ""
       ::= { phGeneralInfoEntry 8 }

    autoConfigureMode  OBJECT-TYPE
       SYNTAX AdicEnable 
       ACCESS read-write
       STATUS mandatory
       DESCRIPTION
            ""
       ::= { phGeneralInfoEntry 9 }

    numPhAisles  OBJECT-TYPE
       SYNTAX INTEGER 
       ACCESS read-only
       STATUS mandatory
       DESCRIPTION
            "Number of aisles in this library."
       ::= { phGeneralInfoEntry 10 }       
           
     operatingMode  OBJECT-TYPE
       SYNTAX INTEGER { normal(1) , delay(2) , unload(3) , 
                        delayAndUnload(4) , noUnload(5) }
       ACCESS read-write
       STATUS mandatory
       DESCRIPTION
            "Controls library behavior when retrieving
            tape from drives."
       ::= { phGeneralInfoEntry 11 } 

	numStorageCartridges  OBJECT-TYPE
       SYNTAX INTEGER
       ACCESS read-only
       STATUS mandatory
       DESCRIPTION
            "Total number of storage cartridges present
            in the library"
       ::= { phGeneralInfoEntry 12 } 

	numCleaningCartridges  OBJECT-TYPE
       SYNTAX INTEGER
       ACCESS read-only
       STATUS mandatory
       DESCRIPTION
            "Total number of cleaning cartridges present
            in the library"
       ::= { phGeneralInfoEntry 13 }

	physLibraryManagerLun  OBJECT-TYPE
       SYNTAX INTEGER
       ACCESS read-only
       STATUS mandatory
       DESCRIPTION
            "The SCSI logical unit number of the
            Physical Library Manager."
       ::= { phGeneralInfoEntry 14 }

	physLibraryAutoCleaning  OBJECT-TYPE
       SYNTAX AdicEnable
       ACCESS read-write
       STATUS mandatory
       DESCRIPTION
            "Enable/disable automatic drive cleaning for
            the entire physical library."
       ::= { phGeneralInfoEntry 15 }
    
    physLibraryDoorStatus  OBJECT-TYPE
       SYNTAX AdicDoorStatus
       ACCESS read-only
       STATUS mandatory
       DESCRIPTION
            "State of the library door: 
            (open/closed,locked/unlocked)."
       ::= { phGeneralInfoEntry 16 }
        
    numPhFrames  OBJECT-TYPE
       SYNTAX INTEGER
       ACCESS read-only
       STATUS mandatory
       DESCRIPTION
            "The number of physical frames in
            the library."
       ::= { phGeneralInfoEntry 17 }

    totalRawCapacity  OBJECT-TYPE
       SYNTAX INTEGER 
       ACCESS read-only
       STATUS mandatory
       DESCRIPTION
            "An estimate of the amount of data which the 
            library can hold.  Units are gigabytes.  May 
            be computed by multiplying the number of cells
            by the maximum number of gigabytes per tape."
       ::= { phGeneralInfoEntry 18 }

    totalFreeCapacity  OBJECT-TYPE
       SYNTAX INTEGER 
       ACCESS read-only
       STATUS mandatory
       DESCRIPTION
            "An estimate of the unused data capacity of the 
            library.  Units are gigabytes.  May be computed 
            by multiplying the number of empty cells
            by the maximum number of gigabytes per tape."
       ::= { phGeneralInfoEntry 19 }

    totalUsedCapacity  OBJECT-TYPE
       SYNTAX INTEGER 
       ACCESS read-only
       STATUS mandatory
       DESCRIPTION
            "An estimate of the used data capacity of the 
            library.  Units are gigabytes.  May be computed 
            by multiplying the number of full cells
            by the maximum number of gigabytes per tape."
       ::= { phGeneralInfoEntry 20 }

    logicalSNAdressingMode  OBJECT-TYPE
       SYNTAX AdicEnable 
       ACCESS read-write
       STATUS mandatory
       DESCRIPTION
            "Enables/disables the logical serial number
            addressing feature."
       ::= { phGeneralInfoEntry 21 }   

	--                                 
	-- End library scalars definitions
	--
	-- ***************************************************************** 
	-- 
	-- Physical Library Media Domain Table 
	-- 
	-- ***************************************************************** 
    mediaDomainTable OBJECT-TYPE 
        SYNTAX SEQUENCE OF MediaDomainEntry 
        ACCESS not-accessible 
        STATUS mandatory 
        DESCRIPTION 
            "Table of all media domains installed in
            the library."
        ::= { physicalLibrary 20 }

    mediaDomainEntry OBJECT-TYPE 
        SYNTAX MediaDomainEntry 
        ACCESS not-accessible 
        STATUS mandatory 
        DESCRIPTION 
            "" 
        INDEX { componentId , mediaDomainIndex  } 
        ::= { mediaDomainTable 1 } 

        MediaDomainEntry ::= 
            SEQUENCE {
            	mediaDomainIndex		INTEGER , 
            	mediaDomainName			DisplayString ,
            	numStorageElements		INTEGER ,
            	numIeElements			INTEGER ,
                numCleaningSlots        INTEGER 
           }
	--
	-- Begin media domain definitions
	--
    mediaDomainIndex  OBJECT-TYPE
       SYNTAX INTEGER 
       ACCESS read-only
       STATUS mandatory
       DESCRIPTION
            ""
       ::= { mediaDomainEntry 1 }

    mediaDomainName  OBJECT-TYPE
       SYNTAX DisplayString
       ACCESS read-only
       STATUS mandatory
       DESCRIPTION
            ""
       ::= { mediaDomainEntry 2 }
       
    numStorageElements  OBJECT-TYPE
       SYNTAX INTEGER
       ACCESS read-only
       STATUS mandatory
       DESCRIPTION
            "Total number of storage elements for this
            media domain in this physical library."
       ::= { mediaDomainEntry 3 }   

    numIeElements  OBJECT-TYPE
       SYNTAX INTEGER
       ACCESS read-only
       STATUS mandatory
       DESCRIPTION
            "Total number of import/export elements for this
            media domain in this physical library."
       ::= { mediaDomainEntry 4 }       

    numCleaningSlots  OBJECT-TYPE
       SYNTAX INTEGER 
       ACCESS read-write
       STATUS mandatory
       DESCRIPTION
            "Returns the number of storage slots reserved for 
            cleaning media of this domain.  When set, the 
            value is the total number of slots to reserve
            for cleaning media of this domain.  The library
            will reserve a set of storage segments such
            that total number of storage slots is greater 
            than or equal to numCleaningSlots."
       ::= { mediaDomainEntry 5 }
	--
	-- End media domain definitions
	--
		
	-- ***************************************************************** 
	-- 
	-- Physical Library Media Type Table 
	-- 
	-- ***************************************************************** 
    mediaTypeTable OBJECT-TYPE 
        SYNTAX SEQUENCE OF MediaTypeEntry 
        ACCESS not-accessible 
        STATUS mandatory 
        DESCRIPTION 
            "Table of media types."
        ::= { physicalLibrary 30 }

    mediaTypeEntry OBJECT-TYPE 
        SYNTAX MediaTypeEntry 
        ACCESS not-accessible 
        STATUS mandatory 
        DESCRIPTION 
            "" 
        INDEX { componentId , mediaDomainIndex , mediaTypeIndex  } 
        ::= { mediaTypeTable 1 } 

        MediaTypeEntry ::= 
            SEQUENCE {
            	mediaTypeIndex			INTEGER ,
            	mediaTypeName			DisplayString ,
            	numDriveElements		INTEGER  
           }
	--
	-- Begin media type definitions
	--
    mediaTypeIndex  OBJECT-TYPE
       SYNTAX INTEGER 
       ACCESS read-only
       STATUS mandatory
       DESCRIPTION
            ""
       ::= { mediaTypeEntry 1 }
       
    mediaTypeName  OBJECT-TYPE
       SYNTAX DisplayString
       ACCESS read-only
       STATUS mandatory
       DESCRIPTION
            ""
       ::= { mediaTypeEntry 2 }
       
    numDriveElements  OBJECT-TYPE
       SYNTAX INTEGER
       ACCESS read-only
       STATUS mandatory
       DESCRIPTION
            "Number of drives for this media type."
       ::= { mediaTypeEntry 3 }
                   
    --
	-- End media type definitions
	--
	-- ***************************************************************** 
	-- 
	-- Physical Library Frame Table
	--
	-- This is a list of all the frames in the library
	-- 
	-- ***************************************************************** 
    phFrameTable OBJECT-TYPE 
        SYNTAX SEQUENCE OF PhFrameEntry 
        ACCESS not-accessible 
        STATUS optional 
        DESCRIPTION 
            "** This table is optional **
            This is a list of all the frames in the library."
        ::= { physicalLibrary 41 }

    phFrameEntry OBJECT-TYPE 
        SYNTAX PhFrameEntry 
        ACCESS not-accessible 
        STATUS optional 
        DESCRIPTION 
            "** This entry object is optional **" 
        INDEX { componentId , phSegmentAisle , phSegmentFrame } 
        ::= { phFrameTable 1 } 

        PhFrameEntry ::= 
            SEQUENCE {    
            	phFrameType				AdicComponentType ,
            	phFrameSerialNumber		DisplayString ,
           		phFrameNumRacks			INTEGER
            }  
	--
	-- Begin Physical Library Frame definitions
	--
	
    phFrameType  OBJECT-TYPE
       SYNTAX AdicComponentType
       ACCESS read-write
       STATUS optional
       DESCRIPTION
            "** This object is optional **
            Physical type of frame.  Only controlModule(6) 
            and expansionModule(7) values are actually
            valid for the frame type."
       ::= { phFrameEntry 1 }

    phFrameSerialNumber  OBJECT-TYPE
       SYNTAX DisplayString
       ACCESS read-write
       STATUS optional
       DESCRIPTION
            "** This object is optional **
            Serial number of this frame, if available."
       ::= { phFrameEntry 2 }

    phFrameNumRacks OBJECT-TYPE
       SYNTAX INTEGER
       ACCESS read-write
       STATUS optional
       DESCRIPTION
            "** This object is optional **
            Number of racks in this frame."
       ::= { phFrameEntry 3 }
              
	-- ***************************************************************** 
	-- 
	-- Physical Library Segement Table
	--
	-- This is a list of all the segments in the library
	-- 
	-- ***************************************************************** 
    phSegmentTable OBJECT-TYPE 
        SYNTAX SEQUENCE OF PhSegmentEntry 
        ACCESS not-accessible 
        STATUS mandatory 
        DESCRIPTION 
            "This is a list of all the segments in the library."
        ::= { physicalLibrary 55 }

    phSegmentEntry OBJECT-TYPE 
        SYNTAX PhSegmentEntry 
        ACCESS not-accessible 
        STATUS mandatory 
        DESCRIPTION 
            "" 
        INDEX { componentId 	, phSegmentType  ,
        		phSegmentAisle 	, phSegmentFrame ,	phSegmentRack , 
        		phSegmentSection , phSegmentCol , phSegmentStartingRow } 
        ::= { phSegmentTable 1 } 

        PhSegmentEntry ::= 
            SEQUENCE {    
            	phSegmentAisle			INTEGER , -- Physical aisle coordinate of segment
            	phSegmentFrame			INTEGER , -- Physical frame coordinate of segment
           		phSegmentRack			INTEGER , -- Physical rack coordinate of segment
				phSegmentSection		INTEGER , -- Physical section coordinate of segment         		
           		phSegmentCol			INTEGER , -- Physical column coordinate of segment 
           		phSegmentStartingRow	INTEGER , -- Within a column, row number where this segment begins
           										  -- Added so that we can have more than one segment per column
            	phSegmentSize			INTEGER ,
            	phSegmentType			AdicSegmentType , -- Storage, I/E, or Drive segment
            	phSegmentMediaDomain	INTEGER , -- Element media domain of segment (media domain table index) 
            	phSegmentStatus			INTEGER ,
            	phSegmentCodStatus		INTEGER ,
            	phSegStartingAddress	INTEGER 
            }  
	--
	-- Begin Physical Library Segment definitions
	--
	
    phSegmentAisle  OBJECT-TYPE
       SYNTAX INTEGER 
       ACCESS read-only
       STATUS mandatory
       DESCRIPTION
            "Aisle coordinate value for this segment."
       ::= { phSegmentEntry 1 }

    phSegmentFrame  OBJECT-TYPE
       SYNTAX INTEGER 
       ACCESS read-only
       STATUS mandatory
       DESCRIPTION
            "Frame coordinate value for this segment."
       ::= { phSegmentEntry 2 }       
       
    phSegmentRack  OBJECT-TYPE
       SYNTAX INTEGER 
       ACCESS read-only
       STATUS mandatory
       DESCRIPTION
            "Rack coordinate value for this segment."
       ::= { phSegmentEntry 3 }
 
    phSegmentSection  OBJECT-TYPE
       SYNTAX INTEGER 
       ACCESS read-only
       STATUS mandatory
       DESCRIPTION
            "Section coordinate for this segment."
       ::= { phSegmentEntry 4 }

    phSegmentCol  OBJECT-TYPE
       SYNTAX INTEGER 
       ACCESS read-only
       STATUS mandatory
       DESCRIPTION
            "Column coordinate value for this segment."
       ::= { phSegmentEntry 5 }             

    phSegmentStartingRow  OBJECT-TYPE
       SYNTAX INTEGER 
       ACCESS read-only
       STATUS mandatory
       DESCRIPTION
            "Row coordinate of the first element in this segment.
            This is useful to divide a column into multiple 
            segments.  For instance, a segment which contains
            rows 1 - 10 would have phSegmentStartingRow = 1.  A
            segment which contains rows 11 - 20 in the same 
            column would have phSegmentStartingRow = 11."
       ::= { phSegmentEntry 6 }
       
    phSegmentSize  OBJECT-TYPE
       SYNTAX INTEGER
       ACCESS read-only
       STATUS mandatory
       DESCRIPTION
            "Number of elements in this segment."
       ::= { phSegmentEntry 7 }                        
       
    phSegmentType  OBJECT-TYPE
       SYNTAX AdicSegmentType
       ACCESS read-only
       STATUS mandatory
       DESCRIPTION
            "This segment's type (storage, drive, I/E, etc.)."
       ::= { phSegmentEntry 8 }     

    phSegmentMediaDomain  OBJECT-TYPE
       SYNTAX INTEGER
       ACCESS read-only
       STATUS mandatory
       DESCRIPTION
            "Element domain of this segment. 
            Points a row in the media domain table."
       ::= { phSegmentEntry 9 }             
       
    phSegmentStatus  OBJECT-TYPE
       SYNTAX INTEGER { installed(1) , notInstalled(2) , reservedForCleaning(3) } 
       ACCESS read-only
       STATUS mandatory
       DESCRIPTION
            "Status of this segment.  May be installed,
            not installed, or reserved for use by the
            automatic cleaning service."
       ::= { phSegmentEntry 10 }     

    phSegmentCodStatus  OBJECT-TYPE
       SYNTAX INTEGER { enabled(1) , disabled(2) , noCod(3) }
       ACCESS read-only
       STATUS mandatory
       DESCRIPTION
            "Capacity on Demand (COD) status for this
            segment.  noCod means that COD is not
            enabled for this library."
       ::= { phSegmentEntry 11 }       
       
    phSegStartingAddress  OBJECT-TYPE
       SYNTAX INTEGER 
       ACCESS read-only
       STATUS mandatory
       DESCRIPTION
            "SCSI media changer element address of the first 
            row in this segment.  Element addresses are 
            contiguous, so we can derive the address of
            each row in the segment from the address of 
            the first row."
       ::= { phSegmentEntry 12 }
       
	-- ***************************************************************** 
	-- 
	-- Physical Library Storage Segement Table
	--
	-- This is a list of all the storage segments in the library
	-- 
	-- ***************************************************************** 
    phStorageSegTable OBJECT-TYPE 
        SYNTAX SEQUENCE OF PhStorageSegEntry 
        ACCESS not-accessible 
        STATUS mandatory 
        DESCRIPTION 
            "This is a list of all the storage segments in the library, indexed by
	        their media domain and segment Index."
        ::= { physicalLibrary 60 }

    phStorageSegEntry OBJECT-TYPE 
        SYNTAX PhStorageSegEntry 
        ACCESS not-accessible 
        STATUS mandatory 
        DESCRIPTION 
            "" 
        INDEX { componentId , mediaDomainIndex , 
        		phSegmentAisle 	, phSegmentFrame ,	phSegmentRack , 
        		phSegmentSection , phSegmentCol , phSegmentStartingRow }        
        ::= { phStorageSegTable 1 } 

        PhStorageSegEntry ::= 
            SEQUENCE {
            	phStorageSegSize 	INTEGER    
            }  
	--
	-- Begin Physical Library Segment definitions
	--
	
    phStorageSegSize  OBJECT-TYPE
       SYNTAX INTEGER
       ACCESS read-only
       STATUS mandatory
       DESCRIPTION
            "Number of elements in this segment."
       ::= { phStorageSegEntry 1 }

	-- ***************************************************************** 
	-- 
	-- Physical Library I/E Segement Table
	--
	-- This is a list of all the storage segments in the library
	-- 
	-- ***************************************************************** 
    phIeSegTable OBJECT-TYPE 
        SYNTAX SEQUENCE OF PhIeSegEntry 
        ACCESS not-accessible 
        STATUS optional 
        DESCRIPTION 
            "** Some objects in this table are optional **
            This is a list of all the I/E segments in the library, indexed by
	        their media domain and segment index."
        ::= { physicalLibrary 70 }

    phIeSegEntry OBJECT-TYPE 
        SYNTAX PhIeSegEntry 
        ACCESS not-accessible 
        STATUS optional 
        DESCRIPTION 
            "** Some objects in this entry are optional **" 
        INDEX { componentId , mediaDomainIndex ,
        		phSegmentAisle 	, phSegmentFrame ,	phSegmentRack , 
        		phSegmentSection , phSegmentCol , phSegmentStartingRow }        
        		         
        ::= { phIeSegTable 1 } 

        PhIeSegEntry ::= 
            SEQUENCE {                                                       
            	phIeSegSize				INTEGER ,
            	phIeSegReserve			INTEGER ,
            	phIeSegReservedBy		INTEGER ,
				phIeSegOnlineStatus  	INTEGER ,
				phIeSegCommand			INTEGER            	
            }  
	--
	-- Begin Physical Library Segment definitions
	--	

    phIeSegSize  OBJECT-TYPE
       SYNTAX INTEGER
       ACCESS read-only
       STATUS optional
       DESCRIPTION
            "Number of elements in this segment."
       ::= { phIeSegEntry 1 }
       
    phIeSegReserve  OBJECT-TYPE
       SYNTAX INTEGER { reserve(1) , release(2) } 
       ACCESS read-write
       STATUS optional
       DESCRIPTION
            "** This object is optional **
            Mechanism to release and reserve this 
            I/E segment."
       ::= { phIeSegEntry 2 }     

    phIeSegReservedBy  OBJECT-TYPE
       SYNTAX INTEGER 
       ACCESS read-write
       STATUS optional
       DESCRIPTION
            "** This object is optional **
            Indicator of who reserved this I/E segment."
       ::= { phIeSegEntry 3 }

    phIeSegOnlineStatus  OBJECT-TYPE
       SYNTAX INTEGER { online(1) , offline(2) }
       ACCESS read-write
       STATUS optional
       DESCRIPTION
            "** This object is optional **
            Takes this I/E segment online/offline."
       ::= { phIeSegEntry 4 }      

	phIeSegCommand     OBJECT-TYPE
       SYNTAX INTEGER { import(1) }
       ACCESS read-write
       STATUS optional
       DESCRIPTION
            "** This object is optional **
            Issue a command to this I/E station."
       ::= { phIeSegEntry 5 }   

	-- ***************************************************************** 
	-- 
	-- Physical Library I/E Station Table
	--
	-- This is a list of all the I/E Stations in the library
	-- 
	-- ***************************************************************** 
    phIeStationTable OBJECT-TYPE 
        SYNTAX SEQUENCE OF PhIeStationEntry 
        ACCESS not-accessible 
        STATUS mandatory 
        DESCRIPTION 
            "This is a list of all the I/E stations in the library"
        ::= { physicalLibrary 75 }

    phIeStationEntry OBJECT-TYPE 
        SYNTAX PhIeStationEntry 
        ACCESS not-accessible 
        STATUS mandatory 
        DESCRIPTION 
            "" 
        INDEX { componentId , phSegmentAisle , phSegmentFrame ,	phSegmentRack , 
        		phIeStationNumber }        
        		         
        ::= { phIeStationTable 1 } 

        PhIeStationEntry ::= 
            SEQUENCE {                                                       
            	phIeStationNumber       INTEGER ,
            	phIeStationDoorStatus	AdicDoorStatus ,
                phIeStationREDId        AdicREDIdentifier            	
            }  
	--
	-- Begin Physical Library Segment definitions
	--	

    phIeStationNumber  OBJECT-TYPE
       SYNTAX INTEGER
       ACCESS read-only
       STATUS mandatory
       DESCRIPTION
            "Index of I/E station within a frame.
            If a frame has N I/E stations, the
            range of phIeStationNumber is
            1 through N."
       ::= { phIeStationEntry 1 }

    phIeStationDoorStatus  OBJECT-TYPE
       SYNTAX AdicDoorStatus
       ACCESS read-only
       STATUS mandatory
       DESCRIPTION
            "Is the station door open/closed,
            locked/unlocked ?"
       ::= { phIeStationEntry 2 }

    phIeStationREDId   OBJECT-TYPE 
       SYNTAX AdicREDIdentifier
       ACCESS read-only 
       STATUS mandatory 
       DESCRIPTION 
          "Runtime Error Detection identifier for this 
          import/export station."
       ::= { phIeStationEntry 3 }       
              
	-- ***************************************************************** 
	-- 
	-- Physical Library Drive Segement Table
	--
	-- This is a list of all the storage segments in the library
	-- 
	-- ***************************************************************** 
    phDriveSegTable OBJECT-TYPE 
        SYNTAX SEQUENCE OF PhDriveSegEntry 
        ACCESS not-accessible 
        STATUS mandatory 
        DESCRIPTION 
            "This is a list of all the drive segments in the library, indexed by
	        their media domain, media type and segment index."
        ::= { physicalLibrary 80 }

    phDriveSegEntry OBJECT-TYPE 
        SYNTAX PhDriveSegEntry 
        ACCESS not-accessible 
        STATUS mandatory 
        DESCRIPTION 
            "" 
        INDEX { componentId , mediaDomainIndex , mediaTypeIndex , 
        		phSegmentAisle 	, phSegmentFrame ,	phSegmentRack , 
        		phSegmentSection , phSegmentCol , phSegmentStartingRow }
        ::= { phDriveSegTable 1 } 

        PhDriveSegEntry ::= 
            SEQUENCE {    
            	phDriveSegSize				INTEGER ,
            	phDriveSegMediaType			INTEGER , -- Element media type of segment (media type table index) 
            	phDriveSegInterfaceType		AdicInterfaceType  -- Element data transfer interface type of segment            	           		
            }  
	--
	-- Begin Physical Library Segment definitions
	--
	
    phDriveSegSize  OBJECT-TYPE
       SYNTAX INTEGER
       ACCESS read-only
       STATUS mandatory
       DESCRIPTION
            "Number of drive elements in this segment."
       ::= { phDriveSegEntry 1 }    

    phDriveSegMediaType  OBJECT-TYPE
       SYNTAX INTEGER
       ACCESS read-only
       STATUS mandatory
       DESCRIPTION
            "Exact media type of this segment. 
            With phSegmentMediaDomain, points a 
            row in the media type table."
       ::= { phDriveSegEntry 2 }

    phDriveSegInterfaceType  OBJECT-TYPE
       SYNTAX AdicInterfaceType
       ACCESS read-only
       STATUS mandatory
       DESCRIPTION
            "Data interface type of this segment. "
       ::= { phDriveSegEntry 3 }       

	-- ***************************************************************** 
	-- 
	-- Physical Library Cleaning Segement Table
	--
	-- This is a list of all storage segments in the library reserved for 
	-- automatic cleaning media
	-- 
	-- ***************************************************************** 
    phCleaningSegTable OBJECT-TYPE 
        SYNTAX SEQUENCE OF PhCleaningSegEntry 
        ACCESS not-accessible 
        STATUS optional 
        DESCRIPTION 
            "** This table is optional **
            This is a list of all the storage segments in the library
	        which have been reserved for use by automatic cleaning services."
        ::= { physicalLibrary 85 }

    phCleaningSegEntry OBJECT-TYPE 
        SYNTAX PhCleaningSegEntry 
        ACCESS not-accessible 
        STATUS optional 
        DESCRIPTION 
            "** This entry object is optional **" 
        INDEX { componentId , mediaDomainIndex , 
        		phSegmentAisle 	, phSegmentFrame ,	phSegmentRack , 
        		phSegmentSection , phSegmentCol , phSegmentStartingRow }
        ::= { phCleaningSegTable 1 } 

        PhCleaningSegEntry ::= 
            SEQUENCE {    
            	phCleaningSegSize				INTEGER ,
            	phCleaningSegRowStatus			RowStatus
            }  
	--
	-- Begin Physical Library Segment definitions
	--
	
    phCleaningSegSize  OBJECT-TYPE
       SYNTAX INTEGER
       ACCESS read-only
       STATUS optional
       DESCRIPTION
            "** This object is optional **
            Number of elements in this segment."
       ::= { phCleaningSegEntry 1 }

    phCleaningSegRowStatus  OBJECT-TYPE
       SYNTAX RowStatus
       ACCESS read-write
       STATUS optional
       DESCRIPTION
            "** This object is optional **
            Management application use this object to 
            to reserve segment for cleaning or release 
            the segment for use as storage."
       ::= { phCleaningSegEntry 2 }
       
	-- ***************************************************************** 
	-- 
	-- Physical Library Storage Slot Table 
	-- 
	-- ***************************************************************** 
    phStorageSlotTable OBJECT-TYPE 
        SYNTAX SEQUENCE OF PhStorageSlotEntry 
        ACCESS not-accessible 
        STATUS optional 
        DESCRIPTION 
            "** This table is optional **"
        ::= { physicalLibrary 90 }

    phStorageSlotEntry OBJECT-TYPE 
        SYNTAX PhStorageSlotEntry 
        ACCESS not-accessible 
        STATUS optional 
        DESCRIPTION 
            "** This entry object is optional **" 
        INDEX { componentId , mediaDomainIndex , 
        		phSegmentAisle 	, phSegmentFrame ,	phSegmentRack , 
        		phSegmentSection , phSegmentCol , 	phStorageRow }  
        ::= { phStorageSlotTable 1 } 

        PhStorageSlotEntry ::= 
            SEQUENCE {
           		phStorageRow			INTEGER ,
           		phStorageElementAddr 	INTEGER 
            }
	--
	-- Begin Physical Storage Slot definitions
	--       
 
     phStorageRow OBJECT-TYPE
       SYNTAX INTEGER 
       ACCESS read-only
       STATUS optional
       DESCRIPTION
            "** This object is optional **
            Row coordinate value for this storage slot."
       ::= { phStorageSlotEntry 1 } 

     phStorageElementAddr OBJECT-TYPE
       SYNTAX INTEGER 
       ACCESS read-only
       STATUS optional
       DESCRIPTION
            "** This object is optional **
            SCSI Medium Changer Element Address for this storage slot."
       ::= { phStorageSlotEntry 2 }
	--
	-- End Physical Storage Slot definitions
	--

	-- ***************************************************************** 
	-- 
	-- Physical Library I/E Slot Table 
	-- 
	-- ***************************************************************** 
    phIeSlotTable OBJECT-TYPE 
        SYNTAX SEQUENCE OF PhIeSlotEntry 
        ACCESS not-accessible 
        STATUS optional 
        DESCRIPTION 
            "** This table is optional **"
        ::= { physicalLibrary 100 }

    phIeSlotEntry OBJECT-TYPE 
        SYNTAX PhIeSlotEntry 
        ACCESS not-accessible 
        STATUS optional 
        DESCRIPTION 
            "** This entry object is optional **" 
        INDEX { componentId , mediaDomainIndex 	,
        		phSegmentAisle 	, phSegmentFrame ,	phSegmentRack , 
        		phSegmentSection , phSegmentCol , phIeRow }  
        ::= { phIeSlotTable 1 } 

        PhIeSlotEntry ::= 
            SEQUENCE {
           		phIeRow				INTEGER ,
           		phIeElementAddr 	INTEGER ,
           		phIeMediaPresent	INTEGER ,
           		phIeMediaId			AdicBarCode
            }
	--
	-- Begin Physical I/E Slot definitions
	--       
 
     phIeRow OBJECT-TYPE
       SYNTAX INTEGER 
       ACCESS read-only
       STATUS optional
       DESCRIPTION
            "** This object is optional **
            Row coordinate value for this I/E slot"
       ::= { phIeSlotEntry 1 } 

     phIeElementAddr OBJECT-TYPE
       SYNTAX INTEGER 
       ACCESS read-only
       STATUS optional
       DESCRIPTION
            "** This object is optional **
            SCSI Medium Changer Element Address for this I/E slot."
       ::= { phIeSlotEntry 2 }

     phIeMediaPresent OBJECT-TYPE
       SYNTAX INTEGER { yes(1) , no(2) , error(3) } 
       ACCESS read-only
       STATUS optional
       DESCRIPTION
            "** This object is optional **
            Is a media cartridge present in this slot?  Values are:
            yes(1)     - system is certain that a cartridge is present.
            no(2)      - system is certain that a cartridge is not present.
            error(3)   - an error ocurred while determining if media is 
                         present.
            "
       ::= { phIeSlotEntry 3 }
       
     phIeMediaId OBJECT-TYPE
       SYNTAX AdicBarCode
       ACCESS read-only
       STATUS optional
       DESCRIPTION
            "** This object is optional **
            Media ID bar code of cartridge in this I/E
            slot, if present and available.  Returns
            zero length string if the bar code is not
            available for any reason."
       ::= { phIeSlotEntry 4 }       
	--
	-- End Physical I/E Slot definitions
	--

	-- ***************************************************************** 
	-- 
	-- Physical Library Drive Table 
	-- 
	-- ***************************************************************** 
    phDriveTable OBJECT-TYPE 
        SYNTAX SEQUENCE OF PhDriveEntry 
        ACCESS not-accessible 
        STATUS mandatory 
        DESCRIPTION 
            ""
        ::= { physicalLibrary 110 }

    phDriveEntry OBJECT-TYPE 
        SYNTAX PhDriveEntry 
        ACCESS not-accessible 
        STATUS mandatory 
        DESCRIPTION 
            "" 
        INDEX { componentId , mediaDomainIndex , mediaTypeIndex ,
        		phSegmentAisle 	, phSegmentFrame ,	phSegmentRack , 
        		phSegmentSection , phSegmentCol , 	phDriveRow }  
        ::= { phDriveTable 1 } 

        PhDriveEntry ::= 
            SEQUENCE {
           		phDriveRow				INTEGER ,
           		phDriveElementAddr 		INTEGER ,
           		phDriveScsiId			INTEGER ,
           		phDriveScsiLun			INTEGER ,
           		phDriveWwn				DisplayString ,
           		phDriveVendor			DisplayString ,
           		phDriveProduct			DisplayString ,
           		phDriveSerialNumber		DisplayString ,
           		phDriveNeedsCleaning	INTEGER ,
           		phDriveAutoCleaning		Boolean ,
           		phDriveInterfaceType	AdicInterfaceType ,
           		phDriveFcLoopId			INTEGER ,
           		phDriveFcLoopIdMode		INTEGER ,
           		phDriveFcHardId			INTEGER ,
           		phDriveStatus			INTEGER ,
           		phDriveCommand			INTEGER ,
           		phDriveFcPortId			INTEGER ,
           		phDriveCompressionOn	Boolean ,
           		phDriveWriteProtected	Boolean ,
           		phDriveNumLoads			INTEGER ,
           		phDriveNumCleans		INTEGER , 
           		phDrivePowerStatus 		INTEGER ,
           		phDriveReadErrors		INTEGER ,
           		phDriveWriteErrors		INTEGER ,
           		phDriveMbytesRead		INTEGER ,
           		phDriveMbytesWritten	INTEGER ,
           		phDriveFirmwareVersion	DisplayString ,
           		phDriveREDId            AdicREDIdentifier ,
           		phDriveOnlineStatus     AdicOnlineStatus ,
           		phDriveErrorCodeBytes   OCTET STRING ,
           		phDriveRasStatus        AdicStatusGroupState ,
           		phDriveWwPortName       DisplayString 
            }
	--
	-- Begin Physical Library Drive definitions
	--  
 
     phDriveRow OBJECT-TYPE
       SYNTAX INTEGER 
       ACCESS read-only
       STATUS mandatory
       DESCRIPTION
            "Row coordinate value for this drive element."
       ::= { phDriveEntry 1 } 

     phDriveElementAddr OBJECT-TYPE
       SYNTAX INTEGER 
       ACCESS read-only
       STATUS mandatory
       DESCRIPTION
            "SCSI Element Address for this drive element."
       ::= { phDriveEntry 2 }

    phDriveScsiId OBJECT-TYPE
       SYNTAX INTEGER 
       ACCESS read-write
       STATUS mandatory
       DESCRIPTION
            ""
       ::= { phDriveEntry 3 }

    phDriveScsiLun OBJECT-TYPE
       SYNTAX INTEGER 
       ACCESS read-write
       STATUS mandatory
       DESCRIPTION
            ""
       ::= { phDriveEntry 4 }

    phDriveWwn OBJECT-TYPE
       SYNTAX DisplayString 
       ACCESS read-only
       STATUS mandatory
       DESCRIPTION
            "World Wide Node Name for this drive."
       ::= { phDriveEntry 5 }

    phDriveVendor OBJECT-TYPE
       SYNTAX DisplayString
       ACCESS read-only
       STATUS mandatory
       DESCRIPTION
            "Name of the vendor of this drive."
       ::= { phDriveEntry 6 }

    phDriveProduct OBJECT-TYPE
       SYNTAX DisplayString
       ACCESS read-only
       STATUS mandatory
       DESCRIPTION
            "Product name of this drive."
       ::= { phDriveEntry 7 }

    phDriveSerialNumber OBJECT-TYPE
       SYNTAX DisplayString 
       ACCESS read-only
       STATUS mandatory
       DESCRIPTION
            ""
       ::= { phDriveEntry 8 }

    phDriveNeedsCleaning OBJECT-TYPE
       SYNTAX INTEGER { true(1) , false(2) , immediate(3) }
       ACCESS read-write
       STATUS mandatory
       DESCRIPTION
            ""
       ::= { phDriveEntry 9 }  

    phDriveAutoCleaning OBJECT-TYPE
       SYNTAX Boolean
       ACCESS read-write
       STATUS mandatory
       DESCRIPTION
            "Add or remove this drive from automatic
            cleaning list."
       ::= { phDriveEntry 10 }

    phDriveInterfaceType OBJECT-TYPE
       SYNTAX AdicInterfaceType
       ACCESS read-only
       STATUS mandatory
       DESCRIPTION
            "Data interface type (SCSI, Fibre Channel, etc.)."
       ::= { phDriveEntry 11 }

    phDriveFcLoopId OBJECT-TYPE
       SYNTAX INTEGER
       ACCESS read-only
       STATUS mandatory
       DESCRIPTION
            "Loop ID for Fibre Channel interface drives,
            undefined for other interface type drives."
       ::= { phDriveEntry 12 }

    phDriveFcLoopIdMode OBJECT-TYPE
       SYNTAX INTEGER { soft(1) , hard(2) } 
       ACCESS read-write
       STATUS mandatory
       DESCRIPTION
            "Loop ID Mode for Fibre Channel interface drives,
            undefined for other interface type drives.  
            Controls negotiation of the port ID on the 
            Fibre Channel connection."
       ::= { phDriveEntry 13 }

    phDriveFcHardId OBJECT-TYPE
       SYNTAX INTEGER
       ACCESS read-write
       STATUS mandatory
       DESCRIPTION
            "Preferred port ID Mode for Fibre Channel 
            interface drives, undefined for other interface 
            type drives.  Used only when port ID mode is 
            set to 'hard'."  
       ::= { phDriveEntry 14 }

    phDriveStatus OBJECT-TYPE
       SYNTAX INTEGER { loading(1) , loaded(2) , unloading(3) , empty(4) }
       ACCESS read-only
       STATUS mandatory
       DESCRIPTION
            ""
       ::= { phDriveEntry 15 }

    phDriveCommand OBJECT-TYPE
       SYNTAX INTEGER { online(1) , offline(2) , reset(3) , powerOn(4) , powerOff(5) , 
                        powerCycle(6) , driveBrickUpdate(7) }
       ACCESS read-write
       STATUS mandatory
       DESCRIPTION
            "Perform various operations on a drive:
            ***************************************
            online(1) - bring drive online
            offline(2) - take drive offline
            reset(3) - perform a warm reset
            powerOn(4) - perform power on
            powerOff(5) - peform power off
            powerCycle(6) - perform power cycle
            driveBrickUpdate(7) - download firmware to the drive brick"
       ::= { phDriveEntry 16 }
       
    phDriveFcPortId OBJECT-TYPE
       SYNTAX INTEGER
       ACCESS read-only
       STATUS mandatory
       DESCRIPTION
            "Port ID for fabric attached Fibre Channel drives,
            undefined for other interface type drives."
       ::= { phDriveEntry 17 } 

    phDriveCompressionOn OBJECT-TYPE
       SYNTAX Boolean
       ACCESS read-write
       STATUS mandatory
       DESCRIPTION
            "Is compression turned on for this drive?"
       ::= { phDriveEntry 18 }             

    phDriveWriteProtected OBJECT-TYPE
       SYNTAX Boolean
       ACCESS read-write
       STATUS mandatory
       DESCRIPTION
            "Is write protection turned on for this drive?"
       ::= { phDriveEntry 19 }             

    phDriveNumLoads OBJECT-TYPE
       SYNTAX INTEGER
       ACCESS read-only
       STATUS mandatory
       DESCRIPTION
            "Total number of loads for this drive.  Count 
            is for the entire lifetime of the drive."
       ::= { phDriveEntry 20 }  

    phDriveNumCleans OBJECT-TYPE
       SYNTAX INTEGER
       ACCESS read-only
       STATUS mandatory
       DESCRIPTION
            "Total number of cleaning operations peroformed
            on this drive.  Count is for the entire lifetime 
            of the drive."
       ::= { phDriveEntry 21 }

    phDrivePowerStatus OBJECT-TYPE
       SYNTAX INTEGER { poweredOn(1) , poweredOff(2) }
       ACCESS read-only
       STATUS mandatory
       DESCRIPTION
            "Is this drive powered on?"
       ::= { phDriveEntry 22 }  
       
    phDriveReadErrors OBJECT-TYPE
       SYNTAX INTEGER
       ACCESS read-only
       STATUS mandatory
       DESCRIPTION
            "Number of read errors for this drive.  Count 
            is for the entire lifetime of the drive."
       ::= { phDriveEntry 23 }  

    phDriveWriteErrors OBJECT-TYPE
       SYNTAX INTEGER
       ACCESS read-only
       STATUS mandatory
       DESCRIPTION
            "Number of write errors for this drive.  Count 
            is for the entire lifetime of the drive."
       ::= { phDriveEntry 24 }

    phDriveMbytesRead OBJECT-TYPE
       SYNTAX INTEGER
       ACCESS read-only
       STATUS mandatory
       DESCRIPTION
            "Number of megabytes of data read from this drive."
       ::= { phDriveEntry 25 }  

    phDriveMbytesWritten OBJECT-TYPE
       SYNTAX INTEGER
       ACCESS read-only
       STATUS mandatory
       DESCRIPTION
            "Number of megabytes of data written to this drive."
       ::= { phDriveEntry 26 }       

    phDriveFirmwareVersion OBJECT-TYPE
       SYNTAX DisplayString
       ACCESS read-only
       STATUS mandatory
       DESCRIPTION
            "Firmware version for this drive."
       ::= { phDriveEntry 27 } 	       

    phDriveREDId   OBJECT-TYPE 
       SYNTAX AdicREDIdentifier
       ACCESS read-only 
       STATUS mandatory 
       DESCRIPTION 
          "Runtime Error Detection identifier for this 
          tape drive."
       ::= { phDriveEntry 28 }

    phDriveOnlineStatus   OBJECT-TYPE 
       SYNTAX AdicOnlineStatus
       ACCESS read-only 
       STATUS mandatory 
       DESCRIPTION 
          "Returns either online(1) or offline(2).  The 
          shutdown(3) state is not applicable to this
          object.  To change the online state of the drive, 
          set the phDriveCommand object to online(1) or 
          offline(2)."
       ::= { phDriveEntry 29 }

    phDriveErrorCodeBytes   OBJECT-TYPE 
       SYNTAX OCTET STRING ( SIZE( 1 ) )
       ACCESS read-only 
       STATUS mandatory 
       DESCRIPTION 
          "String of bytes which contains error
          information about the drive.  The
          meaning of each byte is as follows: 
          ~~~~~~~~~~~~~~~~~~~~~~~~~~~~~~~~~~~~~~~
          byte 0: drive seven segment display code"
       ::= { phDriveEntry 30 }

    phDriveRasStatus   OBJECT-TYPE 
       SYNTAX AdicStatusGroupState
       ACCESS read-only 
       STATUS mandatory 
       DESCRIPTION 
          "RAS status for this individual drive."
       ::= { phDriveEntry 31 }                   
                       
    phDriveWwPortName   OBJECT-TYPE 
       SYNTAX DisplayString
       ACCESS read-only 
       STATUS mandatory 
       DESCRIPTION 
          "World Wide Port Name for this drive."
       ::= { phDriveEntry 32 }
       
    --
	-- End Physical Library Drive definitions
	--         
      
	-- ***************************************************************** 
	-- 
	-- Physical Library Drive Statistics Historical Data
	-- 
	-- ***************************************************************** 
    phDriveStatHistoryTable OBJECT-TYPE 
        SYNTAX SEQUENCE OF PhDriveStatHistoryEntry 
        ACCESS not-accessible 
        STATUS mandatory 
        DESCRIPTION 
            "This table contains historical data on drive 
            operations.  Each row in the table gives various
            statistical data for a single drive over a one hour
            period.  The table is indexed such that phIndex = 0
            is the current hour's data, phIndex = 1 is one hour
            ago, phIndex = 2 is two hours ago, etc."
        ::= { physicalLibrary 112 }

    phDriveStatHistoryEntry OBJECT-TYPE 
        SYNTAX PhDriveStatHistoryEntry 
        ACCESS not-accessible 
        STATUS mandatory 
        DESCRIPTION 
            "" 
        INDEX { componentId , mediaDomainIndex , mediaTypeIndex ,
        		phSegmentAisle 	, phSegmentFrame ,	phSegmentRack , 
        		phSegmentSection , phSegmentCol , 	phDriveRow , phHourIndex }  
        ::= { phDriveStatHistoryTable 1 } 

        PhDriveStatHistoryEntry ::= 
            SEQUENCE {
           		phHourIndex				INTEGER ,
           		phHourlyMBytesRead 		INTEGER ,
           		phHourlyMBytesWritten	INTEGER ,
           		phHourlyMounts          INTEGER
            }
	--
	-- Begin Drive Hourly Statistics
	--  
 
     phHourIndex OBJECT-TYPE
       SYNTAX INTEGER
       ACCESS read-only
       STATUS mandatory
       DESCRIPTION
            "Index into the historical data.  The integer value
            is the number in the past the data the data was collected.
            For example, phHourIndex = 0 means the current hour's 
            statistics, phHourIndex = 1 means one hour in the past,
            phHourIndex = 2 means two hours in the past."
       ::= { phDriveStatHistoryEntry 1 } 

     phHourlyMBytesRead OBJECT-TYPE
       SYNTAX INTEGER 
       ACCESS read-only
       STATUS mandatory
       DESCRIPTION
            "Number of megabytes read by this drive during the
            one hour period indicated by phHourIndex."
       ::= { phDriveStatHistoryEntry 2 }

     phHourlyMBytesWritten OBJECT-TYPE
       SYNTAX INTEGER 
       ACCESS read-only
       STATUS mandatory
       DESCRIPTION
            "Number of megabytes written by this drive during the
            one hour period indicated by phHourIndex."
       ::= { phDriveStatHistoryEntry 3 }

     phHourlyMounts OBJECT-TYPE
       SYNTAX INTEGER 
       ACCESS read-only
       STATUS mandatory
       DESCRIPTION
            "Number of mounts performed by this drive during the
            one hour period indicated by phHourIndex."
       ::= { phDriveStatHistoryEntry 4 }       

                                              
	-- ***************************************************************** 
	-- 
	-- Physical Library Drive Port Group
	--
	-- A group of tables containing variables pertaining to
	-- drive data ports (SCSI, FC, etc. )
	-- 
	-- ***************************************************************** 
	phDrivePorts    OBJECT IDENTIFIER    ::= { physicalLibrary 116 }

	-- ***************************************************************** 
	-- 
	-- Fibre Channel Port Table
	-- 
	-- ***************************************************************** 
		
    fcDrivePortTable OBJECT-TYPE 
        SYNTAX SEQUENCE OF FcDrivePortEntry 
        ACCESS not-accessible 
        STATUS mandatory 
        DESCRIPTION 
            "This table contains objects pertaining to 
            Fibre Channel port settings on native Fibre
            Channel drives."
        ::= { phDrivePorts 10 }

    fcDrivePortEntry OBJECT-TYPE 
        SYNTAX FcDrivePortEntry 
        ACCESS not-accessible 
        STATUS mandatory 
        DESCRIPTION 
            "A row object describing a Fibre Channel
            port." 
        INDEX { componentId , mediaDomainIndex , mediaTypeIndex ,
        		phSegmentAisle 	, phSegmentFrame ,	phSegmentRack , 
        		phSegmentSection , phSegmentCol , 	phDriveRow }  
        ::= { fcDrivePortTable 1 } 

        FcDrivePortEntry ::= 
            SEQUENCE {
                fcPortPreferredSpeed	AdicFcPortSpeed ,
                fcPortNegotiatedSpeed   AdicFcPortSpeed ,
           		fcPortPreferredType	    AdicFcPortType ,  
           		fcPortNegotiatedType	AdicFcPortType ,
           		fcPortTypeQualifier     INTEGER
            }
	--
	-- Begin Fibre Channel Port Attributes
	--  
 
     fcPortPreferredSpeed OBJECT-TYPE
       SYNTAX AdicFcPortSpeed
       ACCESS read-write
       STATUS mandatory
       DESCRIPTION
            "Preferred transmitter speed.  Except for
            auto(1), the numerical value of this object
            is equal to the port speed in megabits per
            second.
            *******************************************
            auto(1) - speed is auto-negotiated with no 
                      preferred speed
            megabits1000(1000) - 1000 megabits per second
            megabits2000(2000) - 2000 megabits per second"
       ::= { fcDrivePortEntry 1 }                                              

     fcPortNegotiatedSpeed OBJECT-TYPE
       SYNTAX AdicFcPortSpeed
       ACCESS read-only
       STATUS mandatory
       DESCRIPTION
            "Actual transmitter speed as negotiated
            on the FC network. The numerical value of 
            this object is equal to the port speed in 
            megabits per second.  Although auto(1) is
            defined in the AdicFcPortSpeed enumeration,
            the fcPortNegotiatedSpeed should never return
            this value.
            *******************************************
            auto(1) - This object should never auto(1)
            megabits1000(1000) - 1000 megabits per second
            megabits2000(2000) - 2000 megabits per second"
       ::= { fcDrivePortEntry 2 }

     fcPortPreferredType OBJECT-TYPE
       SYNTAX AdicFcPortType
       ACCESS read-write
       STATUS mandatory
       DESCRIPTION
            "Preferred port type, such as N_Port or NL_Port.
            auto(1) means no preference, auto-negotiate." 
       ::= { fcDrivePortEntry 3 }                                              

     fcPortNegotiatedType OBJECT-TYPE
       SYNTAX AdicFcPortType 
       ACCESS read-only
       STATUS mandatory
       DESCRIPTION
            "Actual port type as negotiated on the 
            FC network.  Should never return auto(1)."
       ::= { fcDrivePortEntry 4 }

     fcPortTypeQualifier OBJECT-TYPE
       SYNTAX INTEGER { public(1) , private(2) }
       ACCESS read-only
       STATUS mandatory
       DESCRIPTION
            "Is this a public or private port?"
       ::= { fcDrivePortEntry 5 }
    --
    -- End of Fibre Channel Port Attributes
    --       
    
	-- ***************************************************************** 
	-- 
	-- Physical Library Media Table 
	-- 
	-- ***************************************************************** 
    phMediaTable OBJECT-TYPE 
        SYNTAX SEQUENCE OF PhMediaEntry 
        ACCESS not-accessible 
        STATUS mandatory 
        DESCRIPTION 
            ""
        ::= { physicalLibrary 120 }

    phMediaEntry OBJECT-TYPE 
        SYNTAX PhMediaEntry 
        ACCESS not-accessible 
        STATUS mandatory 
        DESCRIPTION 
            "" 
        INDEX { componentId , phMediaBarCode } 
        ::= { phMediaTable 1 } 

        PhMediaEntry ::= 
            SEQUENCE {
           		phMediaBarCode				AdicBarCode ,
           		phMediaDomain				INTEGER ,
           		phMediaType					INTEGER ,
           		phMediaElementAddress		INTEGER ,
           		phMediaMounts				INTEGER ,
           		phMediaReadErrors			INTEGER ,
           		phMediaWriteErrors			INTEGER ,
           		phMediaCapacity				INTEGER ,
           		phMediaFreeSpace			INTEGER ,      
           		phMediaExported				Boolean ,
           		phMediaImportTimestamp		AdicDateAndTime ,
           		phMediaExportTimestamp		AdicDateAndTime
            }
	--
	-- Begin Physical Library Drive definitions
	--
    phMediaBarCode  OBJECT-TYPE
       SYNTAX AdicBarCode 
       ACCESS read-only
       STATUS mandatory
       DESCRIPTION
            ""
       ::= { phMediaEntry 1 }

    phMediaDomain OBJECT-TYPE
       SYNTAX INTEGER
       ACCESS read-only
       STATUS mandatory
       DESCRIPTION
            ""
       ::= { phMediaEntry 2 }

    phMediaType OBJECT-TYPE
       SYNTAX INTEGER
       ACCESS read-only
       STATUS mandatory
       DESCRIPTION
            ""
       ::= { phMediaEntry 3 }

    phMediaElementAddress OBJECT-TYPE
       SYNTAX INTEGER
       ACCESS read-only
       STATUS mandatory
       DESCRIPTION
            "Element address where this cartridge is physically
            located."
       ::= { phMediaEntry 4 }

    phMediaMounts OBJECT-TYPE
       SYNTAX INTEGER
       ACCESS read-only
       STATUS mandatory
       DESCRIPTION
            "Number of times this cartridge has been mounted."
       ::= { phMediaEntry 5 }

    phMediaReadErrors OBJECT-TYPE
       SYNTAX INTEGER
       ACCESS read-only
       STATUS mandatory
       DESCRIPTION
            "Number of errors when reading from this cartridge."
       ::= { phMediaEntry 6 }

    phMediaWriteErrors OBJECT-TYPE
       SYNTAX INTEGER
       ACCESS read-only
       STATUS mandatory
       DESCRIPTION
            "Number of errors when writing to this cartridge."
       ::= { phMediaEntry 7 }

    phMediaCapacity OBJECT-TYPE
       SYNTAX INTEGER
       ACCESS read-only
       STATUS mandatory
       DESCRIPTION
            "Capacity of this cartridge in megabytes.  Returns
            -1 if capacity is unknown."
       ::= { phMediaEntry 8 }

    phMediaFreeSpace OBJECT-TYPE
       SYNTAX INTEGER
       ACCESS read-only
       STATUS mandatory
       DESCRIPTION
            "Amount of free space on this cartridge in megabytes.  Returns
            -1 if free space is unknown."
       ::= { phMediaEntry 9 }       
       
    phMediaExported OBJECT-TYPE
       SYNTAX Boolean
       ACCESS read-only
       STATUS mandatory
       DESCRIPTION
            "Has this cartridge been exported from the library?"
       ::= { phMediaEntry 10 }

    phMediaImportTimestamp OBJECT-TYPE
       SYNTAX AdicDateAndTime
       ACCESS read-only
       STATUS mandatory
       DESCRIPTION
            "Timestamp when cartridge was imported.
            Compatible with the SMIv2 DateAndTime
            textual convention.  Encode is as follows:
            
             field  octets  contents                  range
             -----  ------  --------                  -----
               1      1-2   year                      0..65536
               2       3    month                     1..12
               3       4    day                       1..31
               4       5    hour                      0..23
               5       6    minutes                   0..59
               6       7    seconds                   0..60
                            (use 60 for leap-second)
               7       8    deci-seconds              0..9
               8       9    direction from UTC        '+' / '-'
               9      10    hours from UTC            0..11
              10      11    minutes from UTC          0..59

            For example, Tuesday May 26, 1992 at 1:30:15 PM EDT would be
            displayed as:

                             1992-5-26,13:30:15.0,-4:0

            Note that if only local time is known, then timezone
            information (fields 8-10) is not present."
       ::= { phMediaEntry 11 }

    phMediaExportTimestamp OBJECT-TYPE
       SYNTAX AdicDateAndTime
       ACCESS read-only
       STATUS mandatory
       DESCRIPTION
            "Timestamp when cartridge was exported.
            Compatible with the SMIv2 DateAndTime
            textual convention.  Encode is as follows:
            
             field  octets  contents                  range
             -----  ------  --------                  -----
               1      1-2   year                      0..65536
               2       3    month                     1..12
               3       4    day                       1..31
               4       5    hour                      0..23
               5       6    minutes                   0..59
               6       7    seconds                   0..60
                            (use 60 for leap-second)
               7       8    deci-seconds              0..9
               8       9    direction from UTC        '+' / '-'
               9      10    hours from UTC            0..11
              10      11    minutes from UTC          0..59

            For example, Tuesday May 26, 1992 at 1:30:15 PM EDT would be
            displayed as:

                             1992-5-26,13:30:15.0,-4:0

            Note that if only local time is known, then timezone
            information (fields 8-10) is not present."
       ::= { phMediaEntry 12 }
 	--
	-- End Physical Library Media definitions
	--	

	-- ***************************************************************** 
	-- 
	-- Physical Library Transport Element Table 
	-- 
	-- ***************************************************************** 
    phTransportTable OBJECT-TYPE 
        SYNTAX SEQUENCE OF PhTransportEntry 
        ACCESS not-accessible 
        STATUS optional
        DESCRIPTION 
            "** This table is optional **"
        ::= { physicalLibrary 130 }

    phTransportEntry OBJECT-TYPE 
        SYNTAX PhTransportEntry 
        ACCESS not-accessible 
        STATUS optional 
        DESCRIPTION 
            "** This entry object is optional **" 
        INDEX { componentId , phTransportElementAddress } 
        ::= { phTransportTable 1 } 

        PhTransportEntry ::= 
            SEQUENCE {
           		phTransportElementAddress		INTEGER ,
				phTransportNumRecoveredGets		INTEGER ,
				phTransportNumRecoveredPuts		INTEGER ,
				phTransportNumRecoveredScans	INTEGER ,
				phTransportNumPuts              INTEGER ,
                phTransportREDId                AdicREDIdentifier				
            }
	--
	-- Begin Physical Library Drive definitions
	--
    phTransportElementAddress  OBJECT-TYPE
       SYNTAX INTEGER 
       ACCESS read-only
       STATUS optional
       DESCRIPTION
            "** This object is optional **"
       ::= { phTransportEntry 1 }

    phTransportNumRecoveredGets  OBJECT-TYPE
       SYNTAX INTEGER 
       ACCESS read-only
       STATUS optional
       DESCRIPTION
            "** This object is optional **
            Number of recovered get operations for this
            transport element.  The count is for the entire
            lifetime of the library."
       ::= { phTransportEntry 2 }       

    phTransportNumRecoveredPuts  OBJECT-TYPE
       SYNTAX INTEGER 
       ACCESS read-only
       STATUS optional
       DESCRIPTION
            "** This object is optional **
            Number of recovered put operations for this
            transport element.  The count is for the entire
            lifetime of the library."            
       ::= { phTransportEntry 3 }

    phTransportNumRecoveredScans  OBJECT-TYPE
       SYNTAX INTEGER 
       ACCESS read-only
       STATUS optional
       DESCRIPTION
            "** This object is optional **
            Number of recovered scan operations for this
            transport element.  The count is for the entire
            lifetime of the library."            
       ::= { phTransportEntry 4 }

    phTransportNumPuts  OBJECT-TYPE
       SYNTAX INTEGER 
       ACCESS read-only
       STATUS optional
       DESCRIPTION
            "** This object is optional **
            Number put operations for this transport
            element.  The count is for the entire
            lifetime of the library."            
       ::= { phTransportEntry 5 }
       
    phTransportREDId   OBJECT-TYPE 
       SYNTAX AdicREDIdentifier
       ACCESS read-only 
       STATUS optional 
       DESCRIPTION 
          "** This object is optional **
          Runtime Error Detection identifier for this 
          tape drive."
       ::= { phTransportEntry 6 }
       
 	--
	-- End Physical Library Transport Element definitions
	--

	-- ***************************************************************** 
	-- 
	-- Physical Library Transport Element Domain Table 
	-- 
	-- ***************************************************************** 
    phTransportDomainTable OBJECT-TYPE 
        SYNTAX SEQUENCE OF PhTransportDomainEntry 
        ACCESS not-accessible 
        STATUS optional 
        DESCRIPTION 
            "** This table is optional **"
        ::= { physicalLibrary 132 }

    phTransportDomainEntry OBJECT-TYPE 
        SYNTAX PhTransportDomainEntry 
        ACCESS not-accessible 
        STATUS optional
        DESCRIPTION 
            "** This entry object is optional **" 
        INDEX { componentId , phTransportElementAddress , phTransportDomainIndex } 
        ::= { phTransportDomainTable 1 } 

        PhTransportDomainEntry ::= 
            SEQUENCE {
           		phTransportDomainIndex			INTEGER   -- points to entry in domain table
            }
	--
	-- Begin Physical Library Drive definitions
	--
    phTransportDomainIndex  OBJECT-TYPE
       SYNTAX INTEGER 
       ACCESS read-only
       STATUS optional
       DESCRIPTION
            "** This object is optional **"
       ::= { phTransportDomainEntry 1 } 
       
 	--
	-- End Physical Library Transport Element definitions
	--

	-- ***************************************************************** 
	-- 
	-- Physical Library Cleaning Media Table 
	-- 
	-- ***************************************************************** 
    phCleaningMediaTable OBJECT-TYPE 
        SYNTAX SEQUENCE OF PhCleaningMediaEntry 
        ACCESS not-accessible 
        STATUS optional 
        DESCRIPTION 
            "** This table is optional **
            This is a combination of data about slots reserved for 
            automatic cleaning and the cleaning cartridges themselves.
            Since the relationship between slots and cartridges is
            one-to-one, we can combine these data."
        ::= { physicalLibrary 140 }

    phCleaningMediaEntry OBJECT-TYPE 
        SYNTAX PhCleaningMediaEntry 
        ACCESS not-accessible 
        STATUS optional 
        DESCRIPTION 
            "** This entry object is optional **" 
        INDEX { componentId , mediaDomainIndex ,           
        		phSegmentAisle 	, phSegmentFrame ,	phSegmentRack , 
        		phSegmentSection , phSegmentCol , 	phCleaningMediaRow }  
        ::= { phCleaningMediaTable 1 } 

        PhCleaningMediaEntry ::= 
            SEQUENCE {      
            	phCleaningMediaRow					INTEGER ,            
            	phCleaningMediaStatus				INTEGER , 
            	phCleaningMediaTypeIndex			INTEGER ,            	
            	phCleaningMediaVendorId				DisplayString ,
            	phCleaningMediaBarcode				AdicBarCode ,
            	phCleaningMediaUseCount				INTEGER ,
            	phCleaningMediaMaxUses				INTEGER ,  -- this is really (per domain,type,vendor)
            	phCleaningMediaImportTimestamp		AdicDateAndTime
            }
	--
	-- Begin Physical Library Automatic Cleaning Media definitions
	--

    phCleaningMediaRow  OBJECT-TYPE
       SYNTAX INTEGER 
       ACCESS read-only
       STATUS optional
       DESCRIPTION
            "** This object is optional **"
       ::= { phCleaningMediaEntry 1 }      

    phCleaningMediaStatus  OBJECT-TYPE
       SYNTAX INTEGER { allocated(1) , unallocated(2) }
       ACCESS read-only
       STATUS optional
       DESCRIPTION
            "** This object is optional **
            Cleaning storage is allocated by segment; the value
            of phCleaningMediaStatus indicates if the slot is 
            being used to store a cartridge or not.            
            allocated(1) means this slot is home to cartridge.
            unallocated(2) means there is no cartridge associated with this slot."
       ::= { phCleaningMediaEntry 2 }      

    phCleaningMediaTypeIndex  OBJECT-TYPE
       SYNTAX INTEGER 
       ACCESS read-write
       STATUS optional
       DESCRIPTION
            "** This object is optional **
            Exact media type of this cleaning cartridge.
            Value points to a row in the Media Type table with 
            mediaTypeIndex = phCleaningMediaTypeIndex."
       ::= { phCleaningMediaEntry 3 }      

    phCleaningMediaVendorId  OBJECT-TYPE
       SYNTAX DisplayString 
       ACCESS read-write
       STATUS optional
       DESCRIPTION
            "** This object is optional **
            Vendor of drives that this cleaning cartridge
            is designed to clean.  Value points to a row
            in the Vendor table with 
            vendorIdIndex = phCleaningMediaVendorId."
       ::= { phCleaningMediaEntry 4 }      

    phCleaningMediaBarcode  OBJECT-TYPE
       SYNTAX AdicBarCode
       ACCESS read-write
       STATUS optional
       DESCRIPTION
            "** This object is optional **
            Barcode (if present)."
       ::= { phCleaningMediaEntry 5 }

    phCleaningMediaUseCount  OBJECT-TYPE
       SYNTAX INTEGER 
       ACCESS read-write
       STATUS optional
       DESCRIPTION
            "** This object is optional **
            Use count.  May be set to any value to accomodate 
            importing cartridges that have already been used."
       ::= { phCleaningMediaEntry 6 }   

    phCleaningMediaMaxUses  OBJECT-TYPE
       SYNTAX INTEGER 
       ACCESS read-write
       STATUS optional
       DESCRIPTION
            "** This object is optional **
            Maximum number of uses for this cartidge." -- this is really per (domain,type,vendor)
       ::= { phCleaningMediaEntry 7 }           

    phCleaningMediaImportTimestamp  OBJECT-TYPE
       SYNTAX AdicDateAndTime
       ACCESS read-only
       STATUS optional
       DESCRIPTION
            "** This object is optional **
            Timestamp when this cartridge was imported.
            Compatible with the SMIv2 DateAndTime
            textual convention.  Encode is as follows:
            
             field  octets  contents                  range
             -----  ------  --------                  -----
               1      1-2   year                      0..65536
               2       3    month                     1..12
               3       4    day                       1..31
               4       5    hour                      0..23
               5       6    minutes                   0..59
               6       7    seconds                   0..60
                            (use 60 for leap-second)
               7       8    deci-seconds              0..9
               8       9    direction from UTC        '+' / '-'
               9      10    hours from UTC            0..11
              10      11    minutes from UTC          0..59

            For example, Tuesday May 26, 1992 at 1:30:15 PM EDT would be
            displayed as:

                             1992-5-26,13:30:15.0,-4:0

            Note that if only local time is known, then timezone
            information (fields 8-10) is not present."
       ::= { phCleaningMediaEntry 8 }

 	--
	-- End Physical Library Automatic Cleaning definitions
	--

-- ***************************************************************** 
-- 
-- MCB Logical Library Group 
-- 
-- ***************************************************************** 

    loGeneralInfoTable OBJECT-TYPE 
        SYNTAX SEQUENCE OF LoGeneralInfoEntry 
        ACCESS not-accessible 
        STATUS mandatory 
        DESCRIPTION 
            "General information about the Logical Library Manager."
        ::= { logicalLibrary 10 }

    loGeneralInfoEntry OBJECT-TYPE 
        SYNTAX LoGeneralInfoEntry 
        ACCESS not-accessible 
        STATUS mandatory 
        DESCRIPTION 
            "" 
        INDEX { componentId  } 
        ::= { loGeneralInfoTable 1 } 

        LoGeneralInfoEntry ::= 
            SEQUENCE {
            	maxLogicalLibraries			INTEGER ,
            	numLogicalLibraries			INTEGER ,
            	masterOnlineStatus			INTEGER ,
            	numVendorIds				INTEGER 
           }
--
-- Begin logical library general info definitions
--                           
    maxLogicalLibraries  OBJECT-TYPE
       SYNTAX INTEGER 
       ACCESS read-only
       STATUS mandatory
       DESCRIPTION
            "Maximum number of logical libraries.  This includes
            all media types."
       ::= { loGeneralInfoEntry 1 }

    numLogicalLibraries  OBJECT-TYPE
       SYNTAX INTEGER 
       ACCESS read-only
       STATUS mandatory
       DESCRIPTION
            "Current number of logical libraries configured. 
            This includes all media types."
       ::= { loGeneralInfoEntry 2 }

    masterOnlineStatus  OBJECT-TYPE
       SYNTAX INTEGER { online(1) , offline(2) }
       ACCESS read-write
       STATUS mandatory
       DESCRIPTION
            ""
       ::= { loGeneralInfoEntry 3 } 

    numVendorIds  OBJECT-TYPE
       SYNTAX INTEGER
       ACCESS read-only
       STATUS mandatory
       DESCRIPTION
            ""
       ::= { loGeneralInfoEntry 4 }            
--
-- End logical library general info definitions
--                           

	-- ***************************************************************** 
	-- 
	-- Auto Partition Table
	-- 
	-- ***************************************************************** 
    autoPartitionTable OBJECT-TYPE 
        SYNTAX SEQUENCE OF AutoPartitionEntry 
        ACCESS not-accessible 
        STATUS mandatory 
        DESCRIPTION 
            "Variables pertaining to library auto partitioning."
        ::= { logicalLibrary 12 }

    autoPartitionEntry OBJECT-TYPE 
        SYNTAX AutoPartitionEntry 
        ACCESS not-accessible 
        STATUS mandatory 
        DESCRIPTION 
            "Autopartitioning is based on the media domain, media
            type, and drive data port interface type." 
        INDEX { componentId , mediaDomainIndex , mediaTypeIndex , phDriveInterfaceType } 
        ::= { autoPartitionTable 1 } 

        AutoPartitionEntry ::= 
            SEQUENCE {
            	numAutoPartition        INTEGER	, -- how many partitions to create upon auto-partition
            	autoPartitionCommand    INTEGER 
            }

    numAutoPartition  OBJECT-TYPE
       SYNTAX INTEGER
       ACCESS read-write
       STATUS mandatory
       DESCRIPTION
            "Number of partitions to create upon 
            automatic partitioning for a given
            media domain, media type and interface
            type."
       ::= { autoPartitionEntry 1 }

    autoPartitionCommand  OBJECT-TYPE
       SYNTAX INTEGER { autoPartition(1) }
       ACCESS read-write
       STATUS mandatory
       DESCRIPTION
            "Perform operation based on the media domain,
            media type, and interface type:
            autoPartition(1) - create the number of partitions
                               indicated by the numAutoPartition
                               object, with the library resouces
                               divided equally among the partitions."

       ::= { autoPartitionEntry 2 }    

--
-- End Auto Partitioning Table definitions
-- 
	-- ***************************************************************** 
	-- 
	-- Logical Library Vendor ID Table 
	-- 
	-- ***************************************************************** 
                             
    vendorIdTable OBJECT-TYPE 
        SYNTAX SEQUENCE OF VendorIdEntry 
        ACCESS not-accessible 
        STATUS mandatory 
        DESCRIPTION 
            "Table of possible vendors."
        ::= { logicalLibrary 15 }

    vendorIdEntry OBJECT-TYPE 
        SYNTAX VendorIdEntry 
        ACCESS not-accessible 
        STATUS mandatory 
        DESCRIPTION 
            "" 
        INDEX { componentId , vendorIdIndex  } 
        ::= { vendorIdTable 1 } 

        VendorIdEntry ::= 
            SEQUENCE {
            	vendorIdIndex		INTEGER,
            	vendorName			DisplayString ,
            	numProductIds		INTEGER            	
           }

	--
	-- Begin Vendor ID definitions
	--
    vendorIdIndex  OBJECT-TYPE
       SYNTAX INTEGER 
       ACCESS read-only
       STATUS mandatory
       DESCRIPTION
            ""
       ::= { vendorIdEntry 1 }

    vendorName  OBJECT-TYPE
       SYNTAX DisplayString
       ACCESS read-write
       STATUS mandatory
       DESCRIPTION
            ""
       ::= { vendorIdEntry 2 }

     numProductIds  OBJECT-TYPE
       SYNTAX INTEGER
       ACCESS read-only
       STATUS mandatory
       DESCRIPTION
            ""
       ::= { vendorIdEntry 3 }       
	--
	-- End Vendor ID definitions
	--

	-- ***************************************************************** 
	-- 
	-- Physical Library Product ID Table 
	-- 
	-- ***************************************************************** 
                             
    productIdTable OBJECT-TYPE 
        SYNTAX SEQUENCE OF ProductIdEntry 
        ACCESS not-accessible 
        STATUS mandatory 
        DESCRIPTION 
            "Table of possible product names and configuration
            constraints."
        ::= { logicalLibrary 17 }

    productIdEntry OBJECT-TYPE 
        SYNTAX ProductIdEntry 
        ACCESS not-accessible 
        STATUS mandatory 
        DESCRIPTION 
            "" 
        INDEX { componentId , vendorIdIndex, productIdIndex  } 
        ::= { productIdTable 1 } 

        ProductIdEntry ::= 
            SEQUENCE {
            	productIdIndex		INTEGER,
            	productIdName		DisplayString ,
            	productDrivesMin	INTEGER ,
            	productDrivesMax	INTEGER ,
            	productSlotsMin		INTEGER ,
            	productSlotsMax		INTEGER ,
            	productIeMin		INTEGER ,
            	productIeMax		INTEGER
           }

	--
	-- Begin Product ID definitions
	--
    productIdIndex  OBJECT-TYPE
       SYNTAX INTEGER 
       ACCESS read-only
       STATUS mandatory
       DESCRIPTION
            ""
       ::= { productIdEntry 1 }

    productIdName  OBJECT-TYPE
       SYNTAX DisplayString
       ACCESS read-write
       STATUS mandatory
       DESCRIPTION
            ""
       ::= { productIdEntry 2 }

    productDrivesMin  OBJECT-TYPE
       SYNTAX INTEGER
       ACCESS read-write
       STATUS mandatory
       DESCRIPTION
            ""
       ::= { productIdEntry 3 }

    productDrivesMax  OBJECT-TYPE
       SYNTAX INTEGER
       ACCESS read-write
       STATUS mandatory
       DESCRIPTION
            ""
       ::= { productIdEntry 4 }       

    productSlotsMin  OBJECT-TYPE
       SYNTAX INTEGER
       ACCESS read-write
       STATUS mandatory
       DESCRIPTION
            ""
       ::= { productIdEntry 5 }

    productSlotsMax  OBJECT-TYPE
       SYNTAX INTEGER
       ACCESS read-write
       STATUS mandatory
       DESCRIPTION
            ""
       ::= { productIdEntry 6 }

    productIeMin  OBJECT-TYPE
       SYNTAX INTEGER
       ACCESS read-write
       STATUS mandatory
       DESCRIPTION
            ""
       ::= { productIdEntry 7 }

    productIeMax  OBJECT-TYPE
       SYNTAX INTEGER
       ACCESS read-write
       STATUS mandatory
       DESCRIPTION
            ""
       ::= { productIdEntry 8 }
	--
	-- End Product ID definitions
	--                                

    logicalLibraryTable OBJECT-TYPE 
        SYNTAX SEQUENCE OF LogicalLibraryEntry 
        ACCESS not-accessible 
        STATUS mandatory 
        DESCRIPTION 
            ""
        ::= { logicalLibrary 20 }

    logicalLibraryEntry OBJECT-TYPE 
        SYNTAX LogicalLibraryEntry 
        ACCESS not-accessible 
        STATUS mandatory 
        DESCRIPTION 
            "" 
        INDEX { componentId , logicalLibraryIndex } 
        ::= { logicalLibraryTable 1 } 

        LogicalLibraryEntry ::= 
            SEQUENCE {
            	logicalLibraryIndex		INTEGER ,
            	command					INTEGER ,
            	name					DisplayString,
            	assignedLun				INTEGER ,
            	vendorId				DisplayString,
            	productId				DisplayString,
            	mediaDomain				INTEGER ,
            	mediaType				INTEGER ,
            	numSlots				INTEGER ,
            	numIE					INTEGER ,
            	numDrives				INTEGER ,
            	loStatus				INTEGER ,
            	automaticCleaning		AdicEnable ,
            	mediaTypeChecking		AdicEnable ,
            	serialNumber			DisplayString ,
            	loInterfaceType			AdicInterfaceType ,
            	loNumLibraries			INTEGER ,
            	loLtoTapeTags           INTEGER ,
            	loMediaTypeCheckingPolicy  INTEGER
            	
            }
--
-- Begin definitions
--
    logicalLibraryIndex  OBJECT-TYPE
       SYNTAX INTEGER 
       ACCESS read-only
       STATUS mandatory
       DESCRIPTION
            "Identifies the Logical Library to be
            managed."
       ::= { logicalLibraryEntry 1 }

    command  OBJECT-TYPE
       SYNTAX INTEGER { createSimple(1) , createExpert(2) , modify(3) , delete(4) }
       ACCESS read-write
       STATUS mandatory
       DESCRIPTION
            ""
       ::= { logicalLibraryEntry 2 }
                 
    name  OBJECT-TYPE
       SYNTAX DisplayString
       ACCESS read-write
       STATUS mandatory
       DESCRIPTION
            ""
       ::= { logicalLibraryEntry 3 }
 
     assignedLun OBJECT-TYPE
       SYNTAX INTEGER
       ACCESS read-only
       STATUS mandatory
       DESCRIPTION
            "Assigned LUN of this library's 
            (virtual) SCSI media changer. This
            can only be changed through the 
            SANMgr proxy MIB device map table."
       ::= { logicalLibraryEntry 4 }

    vendorId  OBJECT-TYPE
       SYNTAX DisplayString
       ACCESS read-write
       STATUS mandatory
       DESCRIPTION
            ""
       ::= { logicalLibraryEntry 5 }

    productId  OBJECT-TYPE
       SYNTAX DisplayString
       ACCESS read-write
       STATUS mandatory
       DESCRIPTION
            ""
       ::= { logicalLibraryEntry 6 }

    mediaDomain  OBJECT-TYPE
       SYNTAX INTEGER
       ACCESS read-write
       STATUS mandatory
       DESCRIPTION
            "Points to entry in the Physical Library 
            MediaDomainTable."
       ::= { logicalLibraryEntry 7 }

    mediaType  OBJECT-TYPE
       SYNTAX INTEGER
       ACCESS read-write
       STATUS mandatory
       DESCRIPTION
            "Points to entry in the Physical Library
            MediaTypeTable."
       ::= { logicalLibraryEntry 8 }
       
    numSlots  OBJECT-TYPE
       SYNTAX INTEGER
       ACCESS read-write
       STATUS mandatory
       DESCRIPTION
            ""
       ::= { logicalLibraryEntry 9 }
       
    numIE  OBJECT-TYPE
       SYNTAX INTEGER
       ACCESS read-write
       STATUS mandatory
       DESCRIPTION
            ""
       ::= { logicalLibraryEntry 10 }

    numDrives  OBJECT-TYPE
       SYNTAX INTEGER
       ACCESS read-write
       STATUS mandatory
       DESCRIPTION
            ""
       ::= { logicalLibraryEntry 11 }

    loStatus  OBJECT-TYPE
       SYNTAX INTEGER { online(1) , offline(2) }
       ACCESS read-write
       STATUS mandatory
       DESCRIPTION
            ""
       ::= { logicalLibraryEntry 12 }

    automaticCleaning  OBJECT-TYPE
       SYNTAX AdicEnable
       ACCESS read-write
       STATUS mandatory
       DESCRIPTION
            "Enables/Disables automatic cleaning for
            drives this logical library."
       ::= { logicalLibraryEntry 13 }       
 
    mediaTypeChecking  OBJECT-TYPE
       SYNTAX AdicEnable
       ACCESS read-write
       STATUS mandatory
       DESCRIPTION
            "Enables/Disables media type checking for
            this logical library."
       ::= { logicalLibraryEntry 14 }

    serialNumber  OBJECT-TYPE
       SYNTAX DisplayString
       ACCESS read-only
       STATUS mandatory
       DESCRIPTION
            "Serial Number of this logical library.  Assigned by
            MCB when logical library is created."
       ::= { logicalLibraryEntry 15 }

    loInterfaceType  OBJECT-TYPE
       SYNTAX AdicInterfaceType
       ACCESS read-write
       STATUS mandatory
       DESCRIPTION
            "Type of data interface for this logical library."
       ::= { logicalLibraryEntry 16 }
                                          
    loNumLibraries  OBJECT-TYPE
       SYNTAX INTEGER
       ACCESS read-write
       STATUS obsolete
       DESCRIPTION
            "Formerly used in auto partition operation.
            Made obsolete by autoPartition table."
       ::= { logicalLibraryEntry 17 }

    loLtoTapeTags OBJECT-TYPE
       SYNTAX INTEGER { prefix(1) , suffix(2) , disabled(3) }
       ACCESS read-write
       STATUS mandatory
       DESCRIPTION
            "Controls the inclusion of media type characters 
            in the media barcodes for this logical library.
            For example, the LTO media type characters are 
            'L1' for LTO-1 and 'L2' for LTO-2. This object 
            applies to logical libraries of all media domains,
            not just LTO (as the name suggests)."
       ::= { logicalLibraryEntry 18 }

    loMediaTypeCheckingPolicy OBJECT-TYPE
       SYNTAX INTEGER 
       ACCESS read-write
       STATUS mandatory
       DESCRIPTION
            "Allows the user to specify special handling of
            media type information in barcodes.  Values are:
            
            0 - media type checking disabled; media type as
                derived from barcode is irrelevant.
            911 - 'required'; barcode MUST be a valid ADIC
                barcode, the correct media type may be
                derived from the barcode using the ADIC 
                algorithm.
            Other - 'override'; the media type may not
                be derived from the barcode, use this value 
                instead.  The value map is the same as the
                mediaTypeIndex variable: the logical 
                library's mediaDomain variable specifies
                the media domain and loMediaTypeCheckingPolicy 
                specifies the media type that will be
                assumed for all media in this logical 
                library."
       ::= { logicalLibraryEntry 19 }
                                                               
	-- ***************************************************************** 
	-- 
	-- Logical Library Segement Table
	--
	-- This is a list of all the segments in the logical library
	-- 
	-- ***************************************************************** 
    loSegmentTable OBJECT-TYPE 
        SYNTAX SEQUENCE OF LoSegmentEntry 
        ACCESS not-accessible 
        STATUS mandatory 
        DESCRIPTION 
            "This is a list of all the segments in the library."
        ::= { logicalLibrary 25 }

    loSegmentEntry OBJECT-TYPE 
        SYNTAX LoSegmentEntry 
        ACCESS not-accessible 
        STATUS mandatory 
        DESCRIPTION 
            "" 
        INDEX { componentId 	, loSegmentType  ,
        		loSegmentAisle 	, loSegmentFrame ,	loSegmentRack , 
        		loSegmentSection , loSegmentCol , loSegmentStartingRow } 
        ::= { loSegmentTable 1 } 

        LoSegmentEntry ::= 
            SEQUENCE {    
            	loSegmentAisle				INTEGER , -- Physical aisle coordinate of segment
            	loSegmentFrame				INTEGER , -- Physical frame coordinate of segment
           		loSegmentRack				INTEGER , -- Physical rack coordinate of segment
				loSegmentSection			INTEGER , -- Physical section coordinate of segment         		
           		loSegmentCol				INTEGER , -- Physical column coordinate of segment 
           		loSegmentStartingRow		INTEGER , -- Physical row value where this segment begins
            	loSegmentSize				INTEGER ,
            	loSegmentType				AdicSegmentType ,
            	loSegmentMediaDomain		INTEGER ,
            	loSegmentBelongsTo			INTEGER ,
            	loSegmentCommand			INTEGER ,
            	loSegmentStatus				INTEGER ,
            	loSegmentStartingAddress	INTEGER -- SCSI element address of 1st element in this segment
            }  
	--
	-- Begin Physical Library Segment definitions
	--
	
    loSegmentAisle  OBJECT-TYPE
       SYNTAX INTEGER 
       ACCESS read-only
       STATUS mandatory
       DESCRIPTION
            "Aisle coordinate value for this segment."
       ::= { loSegmentEntry 1 }

    loSegmentFrame  OBJECT-TYPE
       SYNTAX INTEGER 
       ACCESS read-only
       STATUS mandatory
       DESCRIPTION
            "Frame coordinate value for this segment."
       ::= { loSegmentEntry 2 }       
       
    loSegmentRack  OBJECT-TYPE
       SYNTAX INTEGER 
       ACCESS read-only
       STATUS mandatory
       DESCRIPTION
            "Rack coordinate value for this segment."
       ::= { loSegmentEntry 3 }
 
    loSegmentSection  OBJECT-TYPE
       SYNTAX INTEGER 
       ACCESS read-only
       STATUS mandatory
       DESCRIPTION
            "Section coordinate for this segment."
       ::= { loSegmentEntry 4 }

    loSegmentCol  OBJECT-TYPE
       SYNTAX INTEGER 
       ACCESS read-only
       STATUS mandatory
       DESCRIPTION
            "Column coordinate value for this segment."
       ::= { loSegmentEntry 5 }             
 
     loSegmentStartingRow  OBJECT-TYPE
       SYNTAX INTEGER 
       ACCESS read-only
       STATUS mandatory
       DESCRIPTION
            "Row coordinate of the first element in this segment.
            This is useful to divide a column into multiple 
            segments.  For instance, a segment which contains
            rows 1 - 10 would have loSegmentStartingRow = 1.  A
            segment which contains rows 11 - 20 in the same 
            column would have loSegmentStartingRow = 11."
       ::= { loSegmentEntry 6 }
       
    loSegmentSize  OBJECT-TYPE
       SYNTAX INTEGER
       ACCESS read-only
       STATUS mandatory
       DESCRIPTION
            "Number of elements in this segment."
       ::= { loSegmentEntry 7 }                        
       
    loSegmentType  OBJECT-TYPE
       SYNTAX AdicSegmentType
       ACCESS read-only
       STATUS mandatory
       DESCRIPTION
            "Type segment (storage, I/E, drive)."
       ::= { loSegmentEntry 8 }

    loSegmentMediaDomain  OBJECT-TYPE
       SYNTAX INTEGER
       ACCESS read-only
       STATUS mandatory
       DESCRIPTION
            "Media domain for this segment.
            Points to a row in the media 
            domain table."
       ::= { loSegmentEntry 9 }

       
    loSegmentBelongsTo  OBJECT-TYPE
       SYNTAX INTEGER
       ACCESS read-write
       STATUS mandatory
       DESCRIPTION
            "logicalLibraryIndex to which this segment is 
            allocated.  This object has no meaning for 
            an I/E segment since I/E segments may be shared.
            For I/E segments, the list of logical libaraies
            which share the segment may be found in the 
            loSegmentAssignmentTable."
       ::= { loSegmentEntry 10 }                

    loSegmentCommand  OBJECT-TYPE
       SYNTAX INTEGER { allocate(1) , free(2) , reserveForCleaning(3) }
       ACCESS read-write
       STATUS mandatory
       DESCRIPTION
            "Operation to perform using objects in varbind list."
       ::= { loSegmentEntry 11 }       

    loSegmentStatus  OBJECT-TYPE
       SYNTAX INTEGER { allocated(1) , unallocated(2) }
       ACCESS read-only
       STATUS mandatory
       DESCRIPTION
            "Is this segment allocated to a logical library?"
       ::= { loSegmentEntry 12 }
                                     
    loSegmentStartingAddress  OBJECT-TYPE
       SYNTAX INTEGER 
       ACCESS read-only
       STATUS mandatory
       DESCRIPTION
            "Logical SCSI element address of the first 
            element (row) in this segment.  Element
            addresses are contiguous within a segment
            and unique within a logical library."       
       ::= { loSegmentEntry 13 }  

       
	-- ***************************************************************** 
	-- 
	-- Logical Library Segement BelongsTo Table
	--
	-- This is a list of all logical library to which each segment is 
	-- assigned.
	-- 
	-- ***************************************************************** 
    loSegmentBelongsToTable OBJECT-TYPE 
        SYNTAX SEQUENCE OF LoSegmentBelongsToEntry 
        ACCESS not-accessible 
        STATUS mandatory 
        DESCRIPTION 
            "This is a list of the logical libraries to
            which each segments belongs.  Storage and
            drive segments belong to a maximum of
            one logical library, but I/E segments
            may be shared among several logical libraries."
        ::= { logicalLibrary 27 }

    loSegmentBelongsToEntry OBJECT-TYPE 
        SYNTAX LoSegmentBelongsToEntry 
        ACCESS not-accessible 
        STATUS mandatory 
        DESCRIPTION 
            "" 
        INDEX { componentId 	, loSegmentType , 
        		loSegmentAisle 	, loSegmentFrame ,	loSegmentRack , 
        		loSegmentSection , loSegmentCol , loSegmentStartingRow ,
        		loSegmentAssignedTo } 
        ::= { loSegmentBelongsToTable 1 } 

        LoSegmentBelongsToEntry ::= 
            SEQUENCE {    
            	loSegmentAssignedTo		INTEGER 
            }  
	--
	-- Begin Physical Library Segment definitions
	--
	
    loSegmentAssignedTo  OBJECT-TYPE
       SYNTAX INTEGER
       ACCESS read-only
       STATUS mandatory
       DESCRIPTION
            "logicalLibraryIndex to which this segment belongs."
       ::= { loSegmentBelongsToEntry 1 }                
              
	-- ***************************************************************** 
	-- 
	-- Logical Library Storage Segement Table
	--
	-- This is a list of all the storage segments in the logical library
	-- 
	-- ***************************************************************** 
    loStorageSegTable OBJECT-TYPE 
        SYNTAX SEQUENCE OF LoStorageSegEntry 
        ACCESS not-accessible 
        STATUS mandatory 
        DESCRIPTION 
            "This is a list of all the storage segments in the library, indexed by
	        a flat segment index loStorageSegIndex."
        ::= { logicalLibrary 30 }

    loStorageSegEntry OBJECT-TYPE 
        SYNTAX LoStorageSegEntry 
        ACCESS not-accessible 
        STATUS mandatory 
        DESCRIPTION 
            "" 
        INDEX { componentId , logicalLibraryIndex , 
                loSegmentAisle 	, loSegmentFrame ,	loSegmentRack , 
        		loSegmentSection , loSegmentCol , loSegmentStartingRow }
        ::= { loStorageSegTable 1 } 

        LoStorageSegEntry ::= 
            SEQUENCE {
            	loStorageSegSize			INTEGER ,   -- Number of storage elements in this segment 
            	loStorageSegStartingAddress	INTEGER
            }  
	--
	-- Begin Physical Library Segment definitions
	--

    loStorageSegSize  OBJECT-TYPE
       SYNTAX INTEGER
       ACCESS read-only
       STATUS mandatory
       DESCRIPTION
            "Number of storage elements in this segment."
       ::= { loStorageSegEntry 1 }       

    loStorageSegStartingAddress  OBJECT-TYPE
       SYNTAX INTEGER
       ACCESS read-only
       STATUS mandatory
       DESCRIPTION
            "Logical SCSI element address of the first element
            (row) in this storage segment.  Element
            addresses are contiguous within a segment
            and unique within a logical library."
       ::= { loStorageSegEntry 2 }       

	-- ***************************************************************** 
	-- 
	-- Logical Library I/E Segement Table
	--
	-- This is a list of all the storage segments in the logical library
	-- 
	-- ***************************************************************** 
    loIeSegTable OBJECT-TYPE 
        SYNTAX SEQUENCE OF LoIeSegEntry 
        ACCESS not-accessible 
        STATUS mandatory 
        DESCRIPTION 
            "This is a list of all the I/E segments in the logical library, 
            indexed by a flat segment index."
        ::= { logicalLibrary 40 }

    loIeSegEntry OBJECT-TYPE 
        SYNTAX LoIeSegEntry 
        ACCESS not-accessible 
        STATUS mandatory 
        DESCRIPTION 
            "" 
        INDEX { componentId , logicalLibraryIndex ,
                loSegmentAisle 	, loSegmentFrame ,	loSegmentRack , 
        		loSegmentSection , loSegmentCol , loSegmentStartingRow }        

        ::= { loIeSegTable 1 } 

        LoIeSegEntry ::= 
            SEQUENCE {  
            	loIeSegSize				INTEGER ,
                loIeSegReserve 			INTEGER ,
                loIeSegReservedBy		INTEGER ,
                loIeSegStartingAddress	INTEGER            	
            }  
	--
	-- Begin Logical Library I/E Segment definitions
	--

    loIeSegSize  OBJECT-TYPE
       SYNTAX INTEGER
       ACCESS read-only
       STATUS mandatory
       DESCRIPTION
       		"Number of I/E elements in this segment."
       ::= { loIeSegEntry 1 }

    loIeSegReserve  OBJECT-TYPE
       SYNTAX INTEGER { reserve(1) , release(2) } 
       ACCESS read-write
       STATUS mandatory
       DESCRIPTION
            "Mechanism to release and reserve this 
            I/E segment."
       ::= { loIeSegEntry 2 }     

    loIeSegReservedBy  OBJECT-TYPE
       SYNTAX INTEGER 
       ACCESS read-write
       STATUS mandatory
       DESCRIPTION
            "Index of logical library for which this
            I/E segment has been reserved."
       ::= { loIeSegEntry 3 }

    loIeSegStartingAddress  OBJECT-TYPE
       SYNTAX INTEGER
       ACCESS read-only
       STATUS mandatory
       DESCRIPTION
            "Logical SCSI element address of the first 
            element (row) in this I/E segment.  Element
            addresses are contiguous within a segment
            and unique within a logical library."
       ::= { loIeSegEntry 4 }
       
	-- ***************************************************************** 
	-- 
	-- Physical Library Drive Segement Table
	--
	-- This is a list of all the storage segments in the library
	-- 
	-- ***************************************************************** 
    loDriveSegTable OBJECT-TYPE 
        SYNTAX SEQUENCE OF LoDriveSegEntry 
        ACCESS not-accessible 
        STATUS mandatory 
        DESCRIPTION 
            "This is a list of all the drive segments in the library, indexed by
	        their media domain, media type and segment index."
        ::= { logicalLibrary 50 }

    loDriveSegEntry OBJECT-TYPE 
        SYNTAX LoDriveSegEntry 
        ACCESS not-accessible 
        STATUS mandatory 
        DESCRIPTION 
            "" 
        INDEX { componentId , logicalLibraryIndex ,
                loSegmentAisle 	, loSegmentFrame ,	loSegmentRack , 
        		loSegmentSection , loSegmentCol , loSegmentStartingRow }        
        ::= { loDriveSegTable 1 } 

        LoDriveSegEntry ::= 
            SEQUENCE {
            	loDriveSegSize				INTEGER ,
            	loDriveSegStartingAddress	INTEGER ,
            	loDriveSegMediaType			INTEGER ,
            	loDriveSegInterfaceType		AdicInterfaceType            	
            }  
	--
	-- Begin Logical Library Segment definitions
	--

    loDriveSegSize  OBJECT-TYPE
       SYNTAX INTEGER
       ACCESS read-only
       STATUS mandatory
       DESCRIPTION
            "Number of elements in this segment."
       ::= { loDriveSegEntry 1 }

    loDriveSegStartingAddress  OBJECT-TYPE
       SYNTAX INTEGER
       ACCESS read-only
       STATUS mandatory
       DESCRIPTION
            "Logical SCSI element address of the first 
            element (row) in this drive segment.  Element
            addresses are contiguous within a segment
            and unique within a logical library."
       ::= { loDriveSegEntry 2 }

    loDriveSegMediaType  OBJECT-TYPE
       SYNTAX INTEGER
       ACCESS read-only
       STATUS mandatory
       DESCRIPTION
            "Exact media type of this segment. 
            With loSegmentMediaDomain, points a 
            row in the media type table."
       ::= { loDriveSegEntry 3 }

    loDriveSegInterfaceType  OBJECT-TYPE
       SYNTAX AdicInterfaceType
       ACCESS read-only
       STATUS mandatory
       DESCRIPTION
            "Data interface for this segment."
       ::= { loDriveSegEntry 4 }

       
	-- ***************************************************************** 
	-- 
	-- Logical Library Storage Slot Table 
	-- 
	-- ***************************************************************** 
    loStorageSlotTable OBJECT-TYPE 
        SYNTAX SEQUENCE OF LoStorageSlotEntry 
        ACCESS not-accessible 
        STATUS mandatory 
        DESCRIPTION 
            ""
        ::= { logicalLibrary 60 }

    loStorageSlotEntry OBJECT-TYPE 
        SYNTAX LoStorageSlotEntry 
        ACCESS not-accessible 
        STATUS mandatory 
        DESCRIPTION 
            "" 
        INDEX { componentId , logicalLibraryIndex , 
                loSegmentAisle 	, 	loSegmentFrame ,	loSegmentRack , 
        		loSegmentSection ,	loSegmentCol , 		loStorageRow }
        ::= { loStorageSlotTable 1 } 

        LoStorageSlotEntry ::= 
            SEQUENCE {
           		loStorageRow			INTEGER 
            }
	--
	-- Begin Logical Storage Slot definitions
	--       
     loStorageRow OBJECT-TYPE
       SYNTAX INTEGER 
       ACCESS read-only
       STATUS mandatory
       DESCRIPTION
            "Row coordinate value for this storage slot."
       ::= { loStorageSlotEntry 1 } 
	--
	-- End Logical Storage Slot definitions
	--

	-- ***************************************************************** 
	-- 
	-- Logical Library I/E Slot Table 
	-- 
	-- ***************************************************************** 
    loIeSlotTable OBJECT-TYPE 
        SYNTAX SEQUENCE OF LoIeSlotEntry 
        ACCESS not-accessible 
        STATUS mandatory 
        DESCRIPTION 
            ""
        ::= { logicalLibrary 70 }

    loIeSlotEntry OBJECT-TYPE 
        SYNTAX LoIeSlotEntry 
        ACCESS not-accessible 
        STATUS mandatory 
        DESCRIPTION 
            "" 
        INDEX { componentId , logicalLibraryIndex , 
                loSegmentAisle ,	loSegmentFrame ,	loSegmentRack , 
        		loSegmentSection ,	loSegmentCol , 		loIeRow }  
        ::= { loIeSlotTable 1 } 

        LoIeSlotEntry ::= 
            SEQUENCE {
           		loIeRow			INTEGER 
            }
	--
	-- Begin Logical I/E Slot definitions
	--       
     loIeRow OBJECT-TYPE
       SYNTAX INTEGER 
       ACCESS read-only
       STATUS mandatory
       DESCRIPTION
            "Row coordinate value for this storage slot."
       ::= { loIeSlotEntry 1 } 
	--
	-- End Logical I/E Slot definitions
	--

	-- ***************************************************************** 
	-- 
	-- Logical Library Drive Table 
	-- 
	-- ***************************************************************** 
    loDriveTable OBJECT-TYPE 
        SYNTAX SEQUENCE OF LoDriveEntry 
        ACCESS not-accessible 
        STATUS mandatory 
        DESCRIPTION 
            ""
        ::= { logicalLibrary 80 }

    loDriveEntry OBJECT-TYPE 
        SYNTAX LoDriveEntry 
        ACCESS not-accessible 
        STATUS mandatory 
        DESCRIPTION 
            "" 
        INDEX { componentId , logicalLibraryIndex , 
                loSegmentAisle 	, 	loSegmentFrame ,	loSegmentRack , 
        		loSegmentSection ,	loSegmentCol , 		loDriveRow }
        ::= { loDriveTable 1 } 

        LoDriveEntry ::= 
            SEQUENCE {
           		loDriveRow				INTEGER             	
            }
	--
	-- Begin Logical Library Drive definitions
	--
 
     loDriveRow OBJECT-TYPE
       SYNTAX INTEGER 
       ACCESS read-only
       STATUS mandatory
       DESCRIPTION
            "Row coordinate value for where this drive
            element is physically located."
       ::= { loDriveEntry 1 }
       
 	--
	-- End Logical Library Drive definitions
	--

    loStatisticsTable OBJECT-TYPE 
        SYNTAX SEQUENCE OF LoStatisticsEntry 
        ACCESS not-accessible 
        STATUS optional 
        DESCRIPTION 
            "** This table is optional **
            Table of statistics for each logical library.
            Error counts, recovery counts, etc. ."
        ::= { logicalLibrary 90 }

    loStatisticsEntry OBJECT-TYPE 
        SYNTAX LoStatisticsEntry 
        ACCESS not-accessible 
        STATUS optional 
        DESCRIPTION 
            "** This entry object is optional **" 
        INDEX { componentId , logicalLibraryIndex } 
        ::= { loStatisticsTable 1 } 

        LoStatisticsEntry ::= 
            SEQUENCE {
            	loNumRecoveredGets		INTEGER ,
            	loNumRecoveredPuts		INTEGER ,
            	loNumRecoveredScans		INTEGER ,
                loStatsNumPuts          INTEGER ,
                loStatsNumPutRetries    INTEGER ,
                loStatsNumGetRetries    INTEGER ,
                loStatsNumScanRetries   INTEGER
            }
--
-- Begin loStatistics definitions
--
    loNumRecoveredGets  OBJECT-TYPE
       SYNTAX INTEGER 
       ACCESS read-only
       STATUS optional
       DESCRIPTION
            "** This object is optional **
            Number of recovered get operations for this
            logical library.  The count is for the entire
            lifetime of the logical library."
       ::= { loStatisticsEntry 1 }

    loNumRecoveredPuts  OBJECT-TYPE
       SYNTAX INTEGER 
       ACCESS read-only
       STATUS optional
       DESCRIPTION
            "** This object is optional **
            Number of recovered putt operations for this
            logical library.  The count is for the entire
            lifetime of the logical library."
       ::= { loStatisticsEntry 2 }

    loNumRecoveredScans  OBJECT-TYPE
       SYNTAX INTEGER 
       ACCESS read-only
       STATUS optional
       DESCRIPTION
            "** This object is optional **
            Number of recovered scan operations for this
            logical library.  The count is for the entire
            lifetime of the logical library."
       ::= { loStatisticsEntry 3 }

    loStatsNumPuts  OBJECT-TYPE
       SYNTAX INTEGER 
       ACCESS read-only
       STATUS optional
       DESCRIPTION
            "** This object is optional **
            Number of put operations performed for this
            logical library.  The count is for the entire
            lifetime of the logical library."
       ::= { loStatisticsEntry 4 }

    loStatsNumPutRetries  OBJECT-TYPE
       SYNTAX INTEGER 
       ACCESS read-only
       STATUS optional
       DESCRIPTION
            "** This object is optional **
            Number of retried put operations performed for this
            logical library.  The count is for the entire
            lifetime of the logical library."
       ::= { loStatisticsEntry 5 }

    loStatsNumGetRetries  OBJECT-TYPE
       SYNTAX INTEGER 
       ACCESS read-only
       STATUS optional
       DESCRIPTION
            "** This object is optional **
            Number of retried get operations performed for this
            logical library.  The count is for the entire
            lifetime of the logical library."
       ::= { loStatisticsEntry 6 }       

    loStatsNumScanRetries  OBJECT-TYPE
       SYNTAX INTEGER 
       ACCESS read-only
       STATUS optional
       DESCRIPTION
            "** This object is optional **
            Number of retried scan operations performed for this
            logical library.  The count is for the entire
            lifetime of the logical library."
       ::= { loStatisticsEntry 7 }
       
--
-- End loStatistics definitions
--

-- ***************************************************************** 
-- 
-- MCB RAS Group 
-- 
-- *****************************************************************  

	-- ***************************************************************** 
	-- 
	-- System Status Table 
	-- 
	-- ***************************************************************** 

    rasSystemStatusTable OBJECT-TYPE 
        SYNTAX SEQUENCE OF RasSystemStatusEntry 
        ACCESS not-accessible 
        STATUS mandatory 
        DESCRIPTION 
            "Contains status information for various system
            status groups."
        ::= { ras 10 }

    rasSystemStatusEntry OBJECT-TYPE 
        SYNTAX RasSystemStatusEntry 
        ACCESS not-accessible 
        STATUS mandatory 
        DESCRIPTION 
            "Information for a particular system status group.
            The componentId index refers to the MCB through 
            which the management application accesses the RAS 
            manager.  The rasStatusGroupIndex specifies the
            system status group for which the entry contains 
            information." 
        INDEX { componentId , rasStatusGroupIndex  } 
        ::= { rasSystemStatusTable 1 } 

        RasSystemStatusEntry ::= 
            SEQUENCE {
            	rasStatusGroupIndex				AdicStatusGroup ,
            	rasStatusGroupStatus 			AdicStatusGroupState ,
            	rasStatusGroupPreviousStatus 	AdicStatusGroupState ,            	
            	rasStatusGroupTextSummary		DisplayString ,
            	rasStatusGroupTotalTickets 		INTEGER ,
            	rasStatusGroupOpenTickets 		INTEGER ,        
            	rasStatusGroupActionsPending	INTEGER ,
            	rasStatusGroupLastChange		AdicDateAndTime
           }
	--
	-- Begin RAS System Status Table definitions
	--
    rasStatusGroupIndex  OBJECT-TYPE
       SYNTAX AdicStatusGroup
       ACCESS read-only
       STATUS mandatory
       DESCRIPTION
            "Identifies the system status group for which
            this row object contains information."
       ::= { rasSystemStatusEntry 1 }

    rasStatusGroupStatus  OBJECT-TYPE
       SYNTAX AdicStatusGroupState 
       ACCESS read-only
       STATUS mandatory
       DESCRIPTION
            "The status (or condition) of this system status group.
            Use of the 'indeterminate' state: 'indeterminate' is 
            primarily for use in the rasStatusGroupPreviousStatus
            object, where there may not be any previous state 
            information."
       ::= { rasSystemStatusEntry 2 }

    rasStatusGroupPreviousStatus  OBJECT-TYPE
       SYNTAX AdicStatusGroupState
       ACCESS read-only
       STATUS mandatory
       DESCRIPTION
            "After a state change, this object gives the 
            previous state of the system status group.
            If there is no previous state information 
            available, such as when resetting the system,
            the previous state is 'indeterminate'."
       ::= { rasSystemStatusEntry 3 }
       
    rasStatusGroupTextSummary  OBJECT-TYPE
       SYNTAX DisplayString
       ACCESS read-only
       STATUS mandatory
       DESCRIPTION
            "A brief message describing the state of this
            system status group.  If the rasStatusGroupStatus
            is other than 'good', this object should return
            the reason why this is so."
       ::= { rasSystemStatusEntry 4 } 

    rasStatusGroupTotalTickets  OBJECT-TYPE
       SYNTAX INTEGER
       ACCESS read-only
       STATUS mandatory
       DESCRIPTION
            "The total number of RAS tickets created 
            against this system status group."
       ::= { rasSystemStatusEntry 5 }
       
    rasStatusGroupOpenTickets  OBJECT-TYPE
       SYNTAX INTEGER
       ACCESS read-only
       STATUS mandatory
       DESCRIPTION
            "The number of RAS tickets currently open 
            against this system status group."
       ::= { rasSystemStatusEntry 6 }

    rasStatusGroupActionsPending  OBJECT-TYPE
       SYNTAX INTEGER
       ACCESS read-only
       STATUS mandatory
       DESCRIPTION
            "The number of actions pending 
            against this system status group."
       ::= { rasSystemStatusEntry 7 }

    rasStatusGroupLastChange  OBJECT-TYPE
       SYNTAX AdicDateAndTime
       ACCESS read-only
       STATUS mandatory
       DESCRIPTION
            "Timestamp of the last time the status changed." 
       ::= { rasSystemStatusEntry 8 }  

	-- ***************************************************************** 
	-- 
	-- RAS Ticket Table 
	-- 
	-- ***************************************************************** 

    rasTicketTable OBJECT-TYPE 
        SYNTAX SEQUENCE OF RasTicketEntry 
        ACCESS not-accessible 
        STATUS mandatory 
        DESCRIPTION 
            "Contains one row for each ticket in the
            database."
        ::= { ras 20 }

    rasTicketEntry OBJECT-TYPE 
        SYNTAX RasTicketEntry 
        ACCESS not-accessible 
        STATUS mandatory 
        DESCRIPTION 
            "Each entry contains information for a 
            single RAS ticket.  The componentId index 
            refers to the MCB through which the management 
            application accesses the RAS manager.  The 
            rasTicketId specifies the ticket instance."
        INDEX { componentId , rasTicketId  } 
        ::= { rasTicketTable 1 } 

        RasTicketEntry ::= 
            SEQUENCE {
            	rasTicketId				Gauge ,
            	rasTicketRowStatus		RowStatus ,
            	rasTicketState 			AdicRasTicketState ,
            	rasTicketQualifier		INTEGER , 
            	rasTicketPriority		INTEGER ,
            	rasTicketDescription	DisplayString , 
            	rasTicketStatusGroup	AdicStatusGroup , 
            	rasTicketGroupStatus	AdicStatusGroupState ,
            	rasTicketClosedBy		INTEGER ,
            	rasTicketVerifiedBy		INTEGER ,
            	rasTicketComments		DisplayString ,
            	rasTicketSerialNumber	AdicFruSerialNumber ,
            	rasTicketTimeOpened     AdicDateAndTime ,
            	rasTicketTimeClosed     AdicDateAndTime ,
            	rasTicketCount          INTEGER ,
            	rasTicketKeyReport      INTEGER
           }                                            
	--
	-- Begin RAS Ticket Table definitions
	--
    rasTicketId  OBJECT-TYPE
       SYNTAX Gauge 
       ACCESS read-only
       STATUS mandatory
       DESCRIPTION
            "Unique identifier for this ticket. The RAS 
            system defines the ticket ID as an unsigned
            32 bit integer, so it is declared here as a 
            Guage32."
       ::= { rasTicketEntry 1 }

    rasTicketRowStatus  OBJECT-TYPE
       SYNTAX RowStatus
       ACCESS read-write
       STATUS mandatory
       DESCRIPTION
            "Controls creation and deletion of rows
            in this table.  Creation of RAS tickets
            via SNMP is currently not permitted, so
            writing a value of createAndGo(4) or 
            createAndWait(5) does not create a new
            row; it may return error indication."
       ::= { rasTicketEntry 2 }

    rasTicketState  OBJECT-TYPE
       SYNTAX AdicRasTicketState 
       ACCESS read-write
       STATUS mandatory
       DESCRIPTION
            ""
       ::= { rasTicketEntry 3 }

    rasTicketQualifier  OBJECT-TYPE
       SYNTAX INTEGER { none(1), resolved(2), cannotDuplicate(3), asDesigned(4), manualOverride(5) }
       ACCESS read-write
       STATUS mandatory
       DESCRIPTION
            ""
       ::= { rasTicketEntry 4 }

    rasTicketPriority  OBJECT-TYPE
       SYNTAX INTEGER
       ACCESS read-write
       STATUS mandatory
       DESCRIPTION
            ""
       ::= { rasTicketEntry 5 }

    rasTicketDescription  OBJECT-TYPE
       SYNTAX DisplayString
       ACCESS read-write
       STATUS mandatory
       DESCRIPTION
            ""
       ::= { rasTicketEntry 6 }

    rasTicketStatusGroup  OBJECT-TYPE
       SYNTAX AdicStatusGroup
       ACCESS read-only
       STATUS mandatory
       DESCRIPTION
            "System status group to which this ticket
            belongs."
       ::= { rasTicketEntry 7 }

    rasTicketGroupStatus  OBJECT-TYPE
       SYNTAX AdicStatusGroupState
       ACCESS read-only
       STATUS mandatory
       DESCRIPTION
            "Status determination that this ticket indicates
            against its system status group."
       ::= { rasTicketEntry 8 }
              
    rasTicketClosedBy  OBJECT-TYPE
       SYNTAX INTEGER
       ACCESS read-write
       STATUS mandatory
       DESCRIPTION
            ""
       ::= { rasTicketEntry 9 }

    rasTicketVerifiedBy  OBJECT-TYPE
       SYNTAX INTEGER
       ACCESS read-write
       STATUS mandatory
       DESCRIPTION
            ""
       ::= { rasTicketEntry 10 }

    rasTicketComments  OBJECT-TYPE
       SYNTAX DisplayString
       ACCESS read-write
       STATUS mandatory
       DESCRIPTION
            ""
       ::= { rasTicketEntry 11 }

    rasTicketSerialNumber  OBJECT-TYPE
       SYNTAX AdicFruSerialNumber
       ACCESS read-only
       STATUS mandatory
       DESCRIPTION
            ""
       ::= { rasTicketEntry 12 }

    rasTicketTimeOpened  OBJECT-TYPE
       SYNTAX AdicDateAndTime
       ACCESS read-only
       STATUS mandatory
       DESCRIPTION
            "Date and time when ticket was opened."
       ::= { rasTicketEntry 13 }

    rasTicketTimeClosed  OBJECT-TYPE
       SYNTAX AdicDateAndTime
       ACCESS read-only
       STATUS mandatory
       DESCRIPTION
            "Date and time when ticket was closed."
       ::= { rasTicketEntry 14 }

    rasTicketCount  OBJECT-TYPE
       SYNTAX INTEGER
       ACCESS read-only
       STATUS mandatory
       DESCRIPTION
            "Number of times an attempt was made to open
            a duplicate ticket."
       ::= { rasTicketEntry 15 }

    rasTicketKeyReport  OBJECT-TYPE
       SYNTAX INTEGER
       ACCESS read-only
       STATUS mandatory
       DESCRIPTION
            "Contains 0 or a valid rasReportId value.  
            Indicates which report is currently responsible 
            for the severity of the ticket."
       ::= { rasTicketEntry 16 }
       
	-- ***************************************************************** 
	-- 
	-- RAS Report Table 
	-- 
	-- ***************************************************************** 

    rasReportTable OBJECT-TYPE 
        SYNTAX SEQUENCE OF RasReportEntry 
        ACCESS not-accessible 
        STATUS mandatory 
        DESCRIPTION 
            "Contains one row for each ticket/report
            combination in the database.  The table 
            is indexed off the RAS Ticket Table, it
            may contain many RAS Report entries for
            a single RAS Ticket."
        ::= { ras 30 }

    rasReportEntry OBJECT-TYPE 
        SYNTAX RasReportEntry 
        ACCESS not-accessible 
        STATUS mandatory 
        DESCRIPTION 
            "Each entry contains information for a 
            single RAS Report." 
        INDEX { componentId , rasTicketId, rasReportId  } 
        ::= { rasReportTable 1 } 

        RasReportEntry ::= 
            SEQUENCE {
            	rasReportId					Gauge ,
            	rasReportRowStatus			RowStatus ,
				rasReportTimestamp			AdicDateAndTime ,
				rasReportStatusGroup		AdicStatusGroup ,
				rasReportOrcData			OCTET STRING ,
    			rasReportGroupStatus  		AdicStatusGroupState ,
    			rasReportDescription		DisplayString ,
    			rasReportOrcDescription     DisplayString ,
    			rasReportRepeatCounter      INTEGER ,
                rasReportSerialNumber       AdicFruSerialNumber ,
                rasReportHeadReport         INTEGER   			
           }                                            
	--
	-- Begin RAS Ticket Table definitions
	--
    rasReportId  OBJECT-TYPE
       SYNTAX Gauge 
       ACCESS read-only
       STATUS mandatory
       DESCRIPTION
            "Identifies the RAS Report for which this
            this row object contains information.  The RAS 
            system defines the report ID as an unsigned
            32 bit integer, so it is declared here as a 
            Guage32."
       ::= { rasReportEntry 1 }

    rasReportRowStatus  OBJECT-TYPE
       SYNTAX RowStatus
       ACCESS read-write
       STATUS mandatory
       DESCRIPTION
            "Controls creation and deletion of rows
            in the RAS Report table."
       ::= { rasReportEntry 2 }

    rasReportTimestamp  OBJECT-TYPE
       SYNTAX AdicDateAndTime
       ACCESS read-only
       STATUS mandatory
       DESCRIPTION
            "Time when this event was generated."
       ::= { rasReportEntry 3 }

    rasReportStatusGroup  OBJECT-TYPE
       SYNTAX AdicStatusGroup
       ACCESS read-write
       STATUS mandatory
       DESCRIPTION
            "The subsystem that is reporting
            the event."
       ::= { rasReportEntry 4 }

    rasReportOrcData  OBJECT-TYPE
       SYNTAX OCTET STRING ( SIZE( 16 ) )
       ACCESS read-write
       STATUS mandatory
       DESCRIPTION
            "Event payload generated by the reporting
            subsystem."
       ::= { rasReportEntry 5 }

    rasReportGroupStatus  OBJECT-TYPE
       SYNTAX AdicStatusGroupState
       ACCESS read-write
       STATUS mandatory
       DESCRIPTION
            "Status determination that this report indicates
            against the specific FRU."
       ::= { rasReportEntry 6 }

    rasReportDescription  OBJECT-TYPE
       SYNTAX DisplayString
       ACCESS read-write
       STATUS mandatory
       DESCRIPTION
            ""
       ::= { rasReportEntry 7 }  
       
    rasReportOrcDescription  OBJECT-TYPE
       SYNTAX DisplayString
       ACCESS read-only
       STATUS mandatory
       DESCRIPTION
            "Description of the operation result code."
       ::= { rasReportEntry 8 }

    rasReportRepeatCounter  OBJECT-TYPE
       SYNTAX INTEGER
       ACCESS read-only
       STATUS mandatory
       DESCRIPTION
            "Number of times an identical report has been 
            generated."
       ::= { rasReportEntry 9 }        

    rasReportSerialNumber  OBJECT-TYPE
       SYNTAX AdicFruSerialNumber
       ACCESS read-only
       STATUS mandatory
       DESCRIPTION
            ""
       ::= { rasReportEntry 10 }       
                         
    rasReportHeadReport  OBJECT-TYPE
       SYNTAX INTEGER
       ACCESS read-only
       STATUS mandatory
       DESCRIPTION
            "The head report field allows reports 
            to be sorted according to FRU branch."
       ::= { rasReportEntry 11 }
       
	-- ***************************************************************** 
	-- 
	-- RAS FRU Statistics Table 
	-- 
	-- ***************************************************************** 

    rasFruStatTable OBJECT-TYPE 
        SYNTAX SEQUENCE OF RasFruStatEntry 
        ACCESS not-accessible 
        STATUS mandatory 
        DESCRIPTION 
            "Each row dsecribes the history and RAS
            statistics for a single FRU."
        ::= { ras 50 }

    rasFruStatEntry OBJECT-TYPE 
        SYNTAX RasFruStatEntry 
        ACCESS not-accessible 
        STATUS mandatory 
        DESCRIPTION 
            "Each entry contains information for a 
            single FRU." 
        INDEX { componentId , rasFruStatIndex  } 
        ::= { rasFruStatTable 1 } 

        RasFruStatEntry ::= 
            SEQUENCE {
                rasFruStatIndex             INTEGER ,
            	rasFruInstanceId			Gauge ,
            	rasFruStatStatusGroup		AdicStatusGroup ,
            	rasFruStatFruCategory		INTEGER ,
            	rasFruStatFruId				INTEGER ,
            	rasFruStatFirstReportTime	AdicDateAndTime ,
            	rasFruStatLastReportTime	AdicDateAndTime ,
            	rasFruStatTotalTickets		INTEGER ,
            	rasFruStatOpenTickets		INTEGER ,
            	rasFruStatSerialNumber      AdicFruSerialNumber ,
            	rasFruStatState             INTEGER            	
           }                                            
	--
	-- Begin RAS FRU Statistics Table definitions
	--         

    rasFruStatIndex  OBJECT-TYPE
       SYNTAX INTEGER 
       ACCESS read-only
       STATUS mandatory
       DESCRIPTION
            "Flat index for the FRU statistics table."
       ::= { rasFruStatEntry 1 }
       	
    rasFruInstanceId  OBJECT-TYPE
       SYNTAX Gauge 
       ACCESS read-only
       STATUS mandatory
       DESCRIPTION
            "Uniquely identifies the FRU instance."
       ::= { rasFruStatEntry 2 }

    rasFruStatStatusGroup  OBJECT-TYPE
       SYNTAX AdicStatusGroup 
       ACCESS read-only
       STATUS mandatory
       DESCRIPTION
            "Status group to which this FRU belongs."
       ::= { rasFruStatEntry 3 }    

    rasFruStatFruCategory  OBJECT-TYPE
       SYNTAX INTEGER { firmware(1), pcba(2), fan(3), accessor(4), picker(5),
       					power(6), cable(7), mailbox(8), drive(9), media(10),
       					label(11) }
       ACCESS read-only
       STATUS mandatory
       DESCRIPTION
            "Category to which this FRU belongs."
       ::= { rasFruStatEntry 4 }

    rasFruStatFruId  OBJECT-TYPE
       SYNTAX INTEGER 
       ACCESS read-only
       STATUS mandatory
       DESCRIPTION
            "FRU identifier."
       ::= { rasFruStatEntry 5 }

    rasFruStatFirstReportTime  OBJECT-TYPE
       SYNTAX AdicDateAndTime
       ACCESS read-only
       STATUS mandatory
       DESCRIPTION
            "Time when the first RAS report was generated
            for this FRU."
       ::= { rasFruStatEntry 6 }

    rasFruStatLastReportTime  OBJECT-TYPE
       SYNTAX AdicDateAndTime
       ACCESS read-only
       STATUS mandatory
       DESCRIPTION
            "Time when the most recent RAS report was generated
            for this FRU."
       ::= { rasFruStatEntry 7 }

    rasFruStatTotalTickets  OBJECT-TYPE
       SYNTAX INTEGER
       ACCESS read-only
       STATUS mandatory
       DESCRIPTION
            "Total number of RAS tickets created against 
            this FRU, both open and closed tickets."
       ::= { rasFruStatEntry 8 }
       
    rasFruStatOpenTickets  OBJECT-TYPE
       SYNTAX INTEGER
       ACCESS read-only
       STATUS mandatory
       DESCRIPTION
            "Number of RAS tickets currently open 
            against this FRU."
       ::= { rasFruStatEntry 9 } 

    rasFruStatSerialNumber  OBJECT-TYPE
       SYNTAX AdicFruSerialNumber
       ACCESS read-only
       STATUS mandatory
       DESCRIPTION
            "The unique serial number of the FRU."
       ::= { rasFruStatEntry 10 }       

    rasFruStatState  OBJECT-TYPE
       SYNTAX INTEGER { current(1) , old(2) }
       ACCESS read-only
       STATUS mandatory
       DESCRIPTION
            "State = current(1) indicates that
            the FRU is currently installed.
            State = old(2) indicates that the
            FRU has been removed and the data
            is historic."
       ::= { rasFruStatEntry 11 }  

	-- ***************************************************************** 
	-- 
	-- RAS Ticket Filter Table 
	-- 
	-- ***************************************************************** 

    rasTicketFilterTable OBJECT-TYPE 
        SYNTAX SEQUENCE OF RasTicketFilterEntry 
        ACCESS not-accessible 
        STATUS mandatory 
        DESCRIPTION 
            "Contains filter settings for ticket table
            walking.  Only those rows which match the
            filter criteria will appear in the RAS
            ticket table when traversed using GetNext 
            or GetBulk."
        ::= { ras 60 }

    rasTicketFilterEntry OBJECT-TYPE 
        SYNTAX RasTicketFilterEntry 
        ACCESS not-accessible 
        STATUS mandatory 
        DESCRIPTION 
            "" 
        INDEX { componentId } 
        ::= { rasTicketFilterTable 1 } 

        RasTicketFilterEntry ::= 
            SEQUENCE {
            	rasTicketFilterStatusGroup      AdicStatusGroup ,
            	rasTicketFilterState            AdicRasTicketState ,
            	rasTicketFilterSeverity         AdicRasTicketSeverity
           }
	--
	-- Begin RAS Ticket Filter Table definitions
	--
    rasTicketFilterStatusGroup  OBJECT-TYPE
       SYNTAX AdicStatusGroup
       ACCESS read-write
       STATUS mandatory
       DESCRIPTION
            "Identifies the system status group for which
            tickets will be returned."
       ::= { rasTicketFilterEntry 1 }

    rasTicketFilterState  OBJECT-TYPE
       SYNTAX AdicRasTicketState
       ACCESS read-write
       STATUS mandatory
       DESCRIPTION
            "Identifies the ticket state (open, closed, etc.) for which
            tickets will be returned."
       ::= { rasTicketFilterEntry 2 } 

    rasTicketFilterSeverity  OBJECT-TYPE
       SYNTAX AdicRasTicketSeverity
       ACCESS read-write
       STATUS mandatory
       DESCRIPTION
            "Identifies the ticket severity for which
            tickets will be returned.
            =========================================
            high: Tickets/reports with status 'failed' only.
            medium: Tickets/reports with status 'failed' or 'warning'.
            low: All tickets/reports."
       ::= { rasTicketFilterEntry 3 }
       
	--
	-- End RAS Ticket Filter Table definitions
	--
       
    -- 
    -- ADIC Management MIB Trap Definitions
    -- 
	-- Group traps according to trap "specific" number as follows:
	--
	--   1 -  99 Power and Cooling Traps
	-- 200 - 299 Logical Library Traps
	-- 300 - 399 Connectivity Traps
	-- 400 - 499 RAS
	-- 500 - 599 System Level Traps	
	--
    
    --
	-- 100 - 199 Physical Library Traps
    --
    physLibraryActivity TRAP-TYPE 
        ENTERPRISE management  
        VARIABLES 
        {
           componentId ,
           trapSequenceNumber ,           
           trapSeverity ,
           trapSummaryText
        }
        DESCRIPTION 
            "" 
        ::= 100

    physLibraryOnlineStatusChange TRAP-TYPE 
        ENTERPRISE management  
        VARIABLES 
        {
           componentId ,
           trapSequenceNumber ,           
           trapSeverity ,
           trapSummaryText ,
           onlineStatus           
        }
        DESCRIPTION 
            "" 
        ::= 101
        
    physLibraryDoorStatusChange TRAP-TYPE 
        ENTERPRISE management  
        VARIABLES 
        {
           componentId ,
           trapSequenceNumber ,           
           trapSeverity , 
           trapSummaryText ,
           physLibraryDoorStatus                      
        }
        DESCRIPTION 
            "" 
        ::= 102        

    ieStationDoorStatusChange TRAP-TYPE 
        ENTERPRISE management  
        VARIABLES 
        {
           componentId ,
           trapSequenceNumber ,           
           trapSeverity , 
           trapSummaryText ,
           phSegmentAisle , 
           phSegmentFrame ,	
           phSegmentRack , 
           phIeStationNumber ,
           phIeStationDoorStatus                      
        }
        DESCRIPTION 
            "" 
        ::= 103    

    moveMediaComplete TRAP-TYPE 
        ENTERPRISE management  
        VARIABLES 
        {
           componentId ,
           trapSequenceNumber , 
           trapSeverity ,
           phStorageElementAddr , -- source element address
           phStorageElementAddr   -- destination element address
        }
        DESCRIPTION 
            "A piece of media has been move from one
            location to another.
            componentId - identifies MCB 
            trapSequenceNumber - generic sequence number
            trapSeverity - should be informational(5)
            phStorageElementAddr - source element address
            phStorageElementAddr - destination element address" 
        ::= 104

    tapeDriveAdded TRAP-TYPE 
        ENTERPRISE management  
        VARIABLES 
        {
           componentId ,
           trapSequenceNumber , 
           trapSeverity ,
           phDriveRow -- Row component of drive's physical location
        }
        DESCRIPTION 
            "A tape drive was added to the library.
            This trap is issued when a tape drive previously unknown
            to the library becomes known.
            componentId - identifies MCB 
            trapSequenceNumber - generic sequence number
            trapSeverity - should be informational(5)
            phDriveRow - row component of the drive's physical location
               in the library." 
        ::= 105        

    tapeDriveRemoved TRAP-TYPE 
        ENTERPRISE management  
        VARIABLES 
        {
           componentId ,
           trapSequenceNumber , 
           trapSeverity ,
           phDriveRow -- Row component of drive's physical location
        }
        DESCRIPTION 
            "A tape drive was removed from the library.
            This trap is issued when a tape drive is removed from
            library's configuration.
            componentId - identifies MCB 
            trapSequenceNumber - generic sequence number
            trapSeverity - should be informational(5)
            phDriveRow - row component of the drive's physical location
               in the library." 
        ::= 106

    mediaMounted TRAP-TYPE 
        ENTERPRISE management  
        VARIABLES 
        {
           componentId ,
           trapSequenceNumber , 
           trapSeverity ,
           phDriveRow -- Row component of drive's physical location
        }
        DESCRIPTION 
            "Media was mounted in the tape drive indicated in the trap
            payload.
            This trap is issued upon every mount operation.
            componentId - identifies MCB 
            trapSequenceNumber - generic sequence number
            trapSeverity - should be informational(5)
            phDriveRow - row component of the drive's physical location
               in the library." 
        ::= 107

    mediaDismounted TRAP-TYPE 
        ENTERPRISE management  
        VARIABLES 
        {
           componentId ,
           trapSequenceNumber , 
           trapSeverity ,
           phDriveRow , -- Row component of drive's physical location
           phDriveMbytesRead , -- over lifetime of drive   
           phDriveMbytesWritten -- over lifetime of drive
        }
        DESCRIPTION 
            "Media was dismounted in the tape drive indicated in the trap
            payload.
            This trap is issued upon every dismount operation.
            componentId - identifies MCB 
            trapSequenceNumber - generic sequence number
            trapSeverity - should be informational(5)
            phDriveRow - row component of the drive's physical location
               in the library.
            phDriveMbytesRead - over lifetime of drive
            phDriveMbytesWritten - over lifetime of drive" 
        ::= 108

    ieStationInventoryPerformed TRAP-TYPE 
        ENTERPRISE management  
        VARIABLES 
        {
           componentId ,
           trapSequenceNumber ,           
           trapSeverity , -- informational(5)
           phIeElementAddr , -- starting element address
           phIeElementAddr   -- ending element address           
        }
        DESCRIPTION 
            "An inventory operation has been performed
            on an I/E station." 
        ::= 109

   rcuReady TRAP-TYPE
        ENTERPRISE management  
        VARIABLES
        {
           componentId , -- component ID of MCB
           trapSequenceNumber ,
           trapSeverity , -- informational(5)
           trapSummaryText , -- "RCU is ready"
           componentId -- component ID of RCU
        }
        DESCRIPTION 
            "The RCU indicated in the payload has
            transitioned from the NotReady state
            to the Ready state." 
        ::= 110

   rcuNotReady TRAP-TYPE
        ENTERPRISE management  
        VARIABLES
        {
           componentId , -- component ID of MCB
           trapSequenceNumber ,
           trapSeverity , -- informational(5)
           trapSummaryText , -- "RCU is not ready"
           componentId -- component ID of RCU
        }
        DESCRIPTION 
            "The RCU indicated in the payload has
            transitioned from the NotReady state
            to the Ready state."
        ::= 111

    driveActivityUpdate TRAP-TYPE
        ENTERPRISE management  
        VARIABLES
        {
           componentId , -- component ID of MCB
           trapSequenceNumber ,
           trapSeverity , -- informational(5)
           trapSummaryText , -- "" (empty string)
           phHourlyMBytesRead , 
           phHourlyMBytesWritten ,
           phHourlyMounts 
        }
        DESCRIPTION 
            "Drive activity integrated over a fixed
            time period.  Currently, the time period 
            is one hour.  NOTE: the drive is identified 
            by the instance OID contained in the 
            phHourlyMBytesRead, phHourlyMBytesWritten, 
            and phHourlyWritten varbinds."
        ::= 112  

    driveBrickFwUpdateSuccess TRAP-TYPE 
        ENTERPRISE management  
        VARIABLES 
        {
           componentId ,
           trapSequenceNumber , 
           trapSeverity ,
           trapSummaryText ,           
           phDriveSerialNumber ,
           phDriveFirmwareVersion
        }
        DESCRIPTION 
            "Drive brick's firmware was successfully updated.            
            componentId - identifies MCB 
            trapSequenceNumber - generic sequence number
            trapSeverity - should be informational(5)        
            trapSummaryText - brief message about the update 
            phDriveSerialNumber - the drive serial number. The
                                  OID of the varbind encoded in
                                  the trap payload must be the 
                                  full OID, column OID plus indices.
            phDriveFirmwareVersion - the drive firmware version 
                                  identifier. The OID of the varbind
                                  encoded in the trap payload must be 
                                  the full OID, column OID plus indices."
        ::= 113

    driveBrickFwUpdateFailure TRAP-TYPE 
        ENTERPRISE management  
        VARIABLES 
        {
           componentId ,
           trapSequenceNumber , 
           trapSeverity ,
           trapSummaryText ,           
           phDriveSerialNumber ,
           phDriveFirmwareVersion
        }
        DESCRIPTION 
            "Attempt to update drive brick's firmware has failed.            
            componentId - identifies MCB 
            trapSequenceNumber - generic sequence number
            trapSeverity - should be informational(5)        
            trapSummaryText - brief message about the update
            phDriveSerialNumber - the drive serial number. The
                                  OID of the varbind encoded in
                                  the trap payload must be the 
                                  full OID, column OID plus indices.
            phDriveFirmwareVersion - the drive firmware version 
                                  identifier. The OID of the varbind
                                  encoded in the trap payload must be 
                                  the full OID, column OID plus indices."
        ::= 114

    physLibraryConfigurationChange TRAP-TYPE 
        ENTERPRISE management  
        VARIABLES 
        {
           componentId ,
           trapSequenceNumber ,           
           trapSeverity ,
           trapSummaryText 
        }
        DESCRIPTION 
            "The physical configuration of the library has 
            been changed, possibly invalidating the data
            in the management application's model.  For
            example, an LTO magazine swapped for a DLT 
            magazine.  The management application should
            repopulate its data model." 
        ::= 115
                         
    physLibraryRESChange TRAP-TYPE 
        ENTERPRISE management  
        VARIABLES 
        {
           componentId , -- component ID of MCB
           trapSequenceNumber ,           
           trapSeverity , -- informational(5)
           trapSummaryText ,
           phStorageElementAddr , -- starting element address
           phStorageElementAddr   -- ending element address           
        }
        DESCRIPTION 
            "The physical library managers issues this trap
            when it detects that the Read Element Status data 
            has changed.  This generally occurs after an 
            inventory.  The range of elements specified 
            by the last two varbinds may represent storage
            drive, or I/E elements."
        ::= 116          

    driveBrickFwUpdateStart TRAP-TYPE 
        ENTERPRISE management  
        VARIABLES 
        {
           componentId ,
           trapSequenceNumber , 
           trapSeverity ,
           trapSummaryText ,           
           phDriveSerialNumber
        }
        DESCRIPTION 
            "Drive brick firmware update has started.            
            componentId - identifies MCB 
            trapSequenceNumber - generic sequence number
            trapSeverity - should be informational(5)        
            trapSummaryText - brief message about the update 
            phDriveSerialNumber - the drive serial number. The
                                  OID of the varbind encoded in
                                  the trap payload must be the 
                                  full OID, column OID plus indices."
        ::= 117        
        
    --
	-- 200 - 299 Logical Library Traps
    --
    logicalLibraryActivity TRAP-TYPE 
        ENTERPRISE management  
        VARIABLES 
        {
           componentId , 
           trapSequenceNumber ,           
           trapSeverity , 
           trapSummaryText ,
           logicalLibraryIndex 
        }
        DESCRIPTION 
            "" 
        ::= 200

    logicalLibraryCreated TRAP-TYPE 
        ENTERPRISE management  
        VARIABLES 
        {
           componentId ,
           trapSequenceNumber ,
           trapSeverity , 
           trapSummaryText , 
           logicalLibraryIndex 
        }
        DESCRIPTION 
            "" 
        ::= 201

    logicalLibraryModified TRAP-TYPE 
        ENTERPRISE management  
        VARIABLES 
        {
           componentId , 
           trapSequenceNumber ,
           trapSeverity , 
           trapSummaryText ,
           logicalLibraryIndex 
        }
        DESCRIPTION 
            "" 
        ::= 202

    logicalLibraryDeleted TRAP-TYPE 
        ENTERPRISE management  
        VARIABLES 
        {
           componentId , 
           trapSequenceNumber ,
           trapSeverity , 
           trapSummaryText ,
           logicalLibraryIndex 
        }
        DESCRIPTION 
            "" 
        ::= 203

    logicalLibraryOnlineStatusChange TRAP-TYPE 
        ENTERPRISE management  
        VARIABLES 
        {
           componentId , 
           trapSequenceNumber ,
           trapSeverity ,   
           trapSummaryText ,
           logicalLibraryIndex ,
           loStatus
        }
        DESCRIPTION 
            "" 
        ::= 204


    --
	-- 300 - 399 Connectivity Traps
    --

    --
	-- 400 - 499 RAS Traps
    --
    connectivityGroupStatusChange TRAP-TYPE 
        ENTERPRISE management  
        VARIABLES 
        {
           componentId ,
           trapSequenceNumber ,
           trapSeverity , 
           trapSummaryText ,
           rasStatusGroupIndex ,
           rasStatusGroupStatus ,
           rasTicketId ,
           rasReportId           
        }
        DESCRIPTION 
            "The overall state of the connectivity system
            status group has changed.  The present state of
            the connectivity status group is given by the
            value of the rasStatusGroupStatus object in the 
            trap payload." 
        ::= 400

    controlGroupStatusChange TRAP-TYPE 
        ENTERPRISE management  
        VARIABLES 
        {
           componentId ,
           trapSequenceNumber ,
           trapSeverity , 
           trapSummaryText ,
           rasStatusGroupIndex ,
           rasStatusGroupStatus ,
           rasTicketId ,
           rasReportId
        }
        DESCRIPTION 
            "The overall state of the control system
            status group has changed.  The present state of
            the control status group is given by the value of
            the rasStatusGroupStatus object in the trap 
            payload."
        ::= 401
        
    coolingGroupStatusChange TRAP-TYPE 
        ENTERPRISE management  
        VARIABLES 
        {
           componentId ,
           trapSequenceNumber ,
           trapSeverity , 
           trapSummaryText ,
           rasStatusGroupIndex ,
           rasStatusGroupStatus ,
           rasTicketId ,
           rasReportId           
        }
        DESCRIPTION 
            "The overall state of the cooling system
            status group has changed.  The present state of
            the cooling status group is given by the value of
            the rasStatusGroupStatus object in the trap 
            payload."
        ::= 402

    drivesAndMediaGroupStatusChange TRAP-TYPE 
        ENTERPRISE management  
        VARIABLES 
        {
           componentId ,
           trapSequenceNumber ,
           trapSeverity , 
           trapSummaryText ,
           rasStatusGroupIndex ,
           rasStatusGroupStatus ,
           rasTicketId ,
           rasReportId           
        }
        DESCRIPTION 
            "The overall state of the drives and media system
            status group has changed.  The present state of
            the drives and media status group is given by the 
            value of the rasStatusGroupStatus object in the trap 
            payload."
        ::= 403

    powerGroupStatusChange TRAP-TYPE 
        ENTERPRISE management  
        VARIABLES 
        {
           componentId ,
           trapSequenceNumber ,
           trapSeverity , 
           trapSummaryText ,
           rasStatusGroupIndex ,
           rasStatusGroupStatus ,
           rasTicketId ,
           rasReportId
        }
        DESCRIPTION 
            "The overall state of the power system status
            group has changed.  The present state of the
            power status group is given by the value of
            the rasStatusGroupStatus object in the trap 
            payload."
        ::= 404

    roboticsGroupStatusChange TRAP-TYPE 
        ENTERPRISE management  
        VARIABLES 
        {
           componentId ,
           trapSequenceNumber ,
           trapSeverity , 
           trapSummaryText ,
           rasStatusGroupIndex ,
           rasStatusGroupStatus ,
           rasTicketId ,
           rasReportId
        }
        DESCRIPTION 
            "The overall state of the robotics system status
            group has changed.  The present state of the
            robotics status group is given by the value of
            the rasStatusGroupStatus object in the trap 
            payload."
        ::= 405
                 
    rasEventNotification TRAP-TYPE 
        ENTERPRISE management  
        VARIABLES 
        {
           componentId ,
           trapSequenceNumber ,
           trapSeverity , 
           trapSummaryText ,
           rasStatusGroupIndex ,
           rasStatusGroupStatus ,
           rasTicketId ,
           rasReportId ,
           trapIntendedUsage
        }
        DESCRIPTION 
            "A RAS event has occurred, possibly requiring
            action by the management application."
        ::= 406
        
    --
	-- 500 - 599 System Traps
    --
    logRetrievalComplete TRAP-TYPE 
        ENTERPRISE management  
        VARIABLES 
        {
           componentId ,
           trapSequenceNumber ,
           trapSeverity , 
           trapSummaryText 
        }
        DESCRIPTION 
            "Indicates that the system has retrieved
            all remote log files as part of the capture 
            snapshot procedure."
        ::= 500

	END
