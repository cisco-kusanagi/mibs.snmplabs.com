--			Ascend mibuser MIB
--
--			Ascend Communications, Inc
--			1275 Harbor Bay Pkwy
--			Alameda, CA 94502
--			+1 510 769 6001
--			info@ascend.com
--
-- Copyright (c) 1993-1999 Ascend Communications, Inc.
-- All rights reserved.
--
-- Do not edit this file directly.
-- It is generated automatically by mibgen for use with
-- TAOS version 10.0.1 or newer.
--

ASCEND-MIBUSER-MIB DEFINITIONS ::= BEGIN

    IMPORTS

        configuration
            FROM ASCEND-MIB
	IpAddress
	    FROM RFC1155-SMI
	OBJECT-TYPE
	    FROM RFC-1212;

	-- If any of the MIB compilers have problems with the DisplayString
	-- or PhysAddress, uncomment the next two lines.

    DisplayString	::=	OCTET STRING
    -- PhysAddress	::=	OCTET STRING

    mibuserProfile  OBJECT IDENTIFIER ::= { configuration 134}

	-- The mibuserProfile table
	--
	-- This table contains parameters for the mibuserProfile profile
	--

    mibuserProfileTable	OBJECT-TYPE
	SYNTAX		SEQUENCE OF MibuserProfileEntry
	ACCESS		not-accessible
	STATUS		mandatory
	DESCRIPTION	"A list of mibuserProfile profile entries."
	::= { mibuserProfile 1 }

    mibuserProfileEntry	OBJECT-TYPE
	SYNTAX		MibuserProfileEntry
	ACCESS		not-accessible
	STATUS		mandatory
	DESCRIPTION	"A mibuserProfile entry containing objects that
			 maps to the parameters of mibuserProfile profile."
	INDEX		{ userProfile-Name }
	::= { mibuserProfileTable 1 }

    MibuserProfileEntry ::=
	SEQUENCE {
	    userProfile-Name
		DisplayString,
	    userProfile-Password
		DisplayString,
	    userProfile-ActiveEnabled
		INTEGER,
	    userProfile-AllowTermserv
		INTEGER,
	    userProfile-AllowSystem
		INTEGER,
	    userProfile-AllowDiagnostic
		INTEGER,
	    userProfile-AllowUpdate
		INTEGER,
	    userProfile-AllowPassword
		INTEGER,
	    userProfile-AllowCode
		INTEGER,
	    userProfile-IdleLogout
		INTEGER,
	    userProfile-Prompt
		DisplayString,
	    userProfile-DefaultStatus
		INTEGER,
	    userProfile-TopStatus
		INTEGER,
	    userProfile-BottomStatus
		INTEGER,
	    userProfile-LeftStatus
		INTEGER,
	    userProfile-ScreenWidth
		INTEGER,
	    userProfile-ScreenLength
		INTEGER,
	    userProfile-StatusLength
		INTEGER,
	    userProfile-UseScrollRegions
		INTEGER,
	    userProfile-LogDisplayLevel
		INTEGER,
	    userProfile-Action-o
		INTEGER
	}

    userProfile-Name	OBJECT-TYPE
	SYNTAX	DisplayString
	ACCESS	read-only
	STATUS	mandatory
	DESCRIPTION	"The name of the host that is asking for validation."
	::= { mibuserProfileEntry 1 }

    userProfile-Password	OBJECT-TYPE
	SYNTAX	DisplayString
	ACCESS	read-write
	STATUS	mandatory
	DESCRIPTION	"The password of the host that is asking for validation."
	::= { mibuserProfileEntry 2 }

    userProfile-ActiveEnabled	OBJECT-TYPE
	SYNTAX	INTEGER {
		    no (1),
		    yes (2)
		}
	ACCESS	read-write
	STATUS	mandatory
	DESCRIPTION	"TRUE if this user account is enabled for use."
	::= { mibuserProfileEntry 3 }

    userProfile-AllowTermserv	OBJECT-TYPE
	SYNTAX	INTEGER {
		    no (1),
		    yes (2)
		}
	ACCESS	read-write
	STATUS	mandatory
	DESCRIPTION	"TRUE if this user may use teminal server commands."
	::= { mibuserProfileEntry 4 }

    userProfile-AllowSystem	OBJECT-TYPE
	SYNTAX	INTEGER {
		    no (1),
		    yes (2)
		}
	ACCESS	read-write
	STATUS	mandatory
	DESCRIPTION	"TRUE if this user may use system commands."
	::= { mibuserProfileEntry 5 }

    userProfile-AllowDiagnostic	OBJECT-TYPE
	SYNTAX	INTEGER {
		    no (1),
		    yes (2)
		}
	ACCESS	read-write
	STATUS	mandatory
	DESCRIPTION	"TRUE if this user may use diagnostic commands."
	::= { mibuserProfileEntry 6 }

    userProfile-AllowUpdate	OBJECT-TYPE
	SYNTAX	INTEGER {
		    no (1),
		    yes (2)
		}
	ACCESS	read-write
	STATUS	mandatory
	DESCRIPTION	"TRUE if this user may use update commands."
	::= { mibuserProfileEntry 7 }

    userProfile-AllowPassword	OBJECT-TYPE
	SYNTAX	INTEGER {
		    no (1),
		    yes (2)
		}
	ACCESS	read-write
	STATUS	mandatory
	DESCRIPTION	"TRUE if this user may user may view password fields."
	::= { mibuserProfileEntry 8 }

    userProfile-AllowCode	OBJECT-TYPE
	SYNTAX	INTEGER {
		    no (1),
		    yes (2)
		}
	ACCESS	read-write
	STATUS	mandatory
	DESCRIPTION	"TRUE if this user may upload code the the unit."
	::= { mibuserProfileEntry 9 }

    userProfile-IdleLogout	OBJECT-TYPE
	SYNTAX	INTEGER
	ACCESS	read-write
	STATUS	mandatory
	DESCRIPTION	"When non-zero, the user will be logged out after this many minutes with no keyboard activity."
	::= { mibuserProfileEntry 10 }

    userProfile-Prompt	OBJECT-TYPE
	SYNTAX	DisplayString
	ACCESS	read-write
	STATUS	mandatory
	DESCRIPTION	"The prompt displayed to the user. The value '*' is substituted with the user's name."
	::= { mibuserProfileEntry 11 }

    userProfile-DefaultStatus	OBJECT-TYPE
	SYNTAX	INTEGER {
		    no (1),
		    yes (2)
		}
	ACCESS	read-write
	STATUS	mandatory
	DESCRIPTION	"When TRUE, the status screen is displayed by default."
	::= { mibuserProfileEntry 12 }

    userProfile-TopStatus	OBJECT-TYPE
	SYNTAX	INTEGER {
		    generalInfo (1),
		    logWindow (2),
		    lineStatus (3),
		    atmvccStatus (4)
		}
	ACCESS	read-write
	STATUS	mandatory
	DESCRIPTION	"The default content of the upper configurable status window."
	::= { mibuserProfileEntry 13 }

    userProfile-BottomStatus	OBJECT-TYPE
	SYNTAX	INTEGER {
		    generalInfo (1),
		    logWindow (2),
		    lineStatus (3),
		    atmvccStatus (4)
		}
	ACCESS	read-write
	STATUS	mandatory
	DESCRIPTION	"The default content of the lower configurable status window."
	::= { mibuserProfileEntry 14 }

    userProfile-LeftStatus	OBJECT-TYPE
	SYNTAX	INTEGER {
		    sessionList (1),
		    connectionList (2),
		    callstatsList (3)
		}
	ACCESS	read-write
	STATUS	mandatory
	DESCRIPTION	"The default content of the left configurable status window."
	::= { mibuserProfileEntry 15 }

    userProfile-ScreenWidth	OBJECT-TYPE
	SYNTAX	INTEGER
	ACCESS	read-write
	STATUS	mandatory
	DESCRIPTION	"The total width of the user's terminal window (default = 80 chars)."
	::= { mibuserProfileEntry 16 }

    userProfile-ScreenLength	OBJECT-TYPE
	SYNTAX	INTEGER
	ACCESS	read-write
	STATUS	mandatory
	DESCRIPTION	"The total height of the user's terminal window (default = 24 lines)."
	::= { mibuserProfileEntry 17 }

    userProfile-StatusLength	OBJECT-TYPE
	SYNTAX	INTEGER
	ACCESS	read-write
	STATUS	mandatory
	DESCRIPTION	"The number of lines of screen-length used by status (default = 18 lines, counting dividers)."
	::= { mibuserProfileEntry 18 }

    userProfile-UseScrollRegions	OBJECT-TYPE
	SYNTAX	INTEGER {
		    no (1),
		    yes (2)
		}
	ACCESS	read-write
	STATUS	mandatory
	DESCRIPTION	"If TRUE, VT100 scroll region commands will be used to reduce screen redraws when the status screen is being displayed."
	::= { mibuserProfileEntry 19 }

    userProfile-LogDisplayLevel	OBJECT-TYPE
	SYNTAX	INTEGER {
		    none (1),
		    emergency (2),
		    alert (3),
		    critical (4),
		    error (5),
		    warning (6),
		    notice (7),
		    info (8),
		    debug (9)
		}
	ACCESS	read-write
	STATUS	mandatory
	DESCRIPTION	"Determines the level of log message to display immediately to the user."
	::= { mibuserProfileEntry 20 }

    userProfile-Action-o	OBJECT-TYPE
	SYNTAX	INTEGER {
		    noAction (1),
		    createProfile (2),
		    deleteProfile (3)
		}
	ACCESS	read-write
	STATUS	mandatory
	DESCRIPTION	""
	::= { mibuserProfileEntry 21 }

END
