SALIX-M4-MIB DEFINITIONS ::= BEGIN

IMPORTS

   MODULE-IDENTITY, 
   OBJECT-TYPE,
   NOTIFICATION-TYPE,
   IpAddress                                 FROM SNMPv2-SMI

   MODULE-COMPLIANCE, OBJECT-GROUP           FROM SNMPv2-CONF
   
   TEXTUAL-CONVENTION, DisplayString,
   RowStatus, TruthValue                     FROM SNMPv2-TC
         
   atmfM4TcAdaptorEntry, 
   atmfM4EquipHolderEntry,
   atmfM4PlugInUnitEntry, 
   atmfM4CellProtoHistIndex,
   atmfM4TrapAlarmSeverity                   FROM ATM-FORUM-M4-MIB
         
   hrSWInstalledIndex                        FROM HOST-RESOURCES-MIB         
   entPhysicalIndex, PhysicalIndex           FROM ENTITY-MIB  
         
   SalixPlugInUnitType                       FROM SALIX-PRODUCT-PLUGIN-MIB    

   salixGeneric                              FROM SALIX-MIB;

salixM4MIB MODULE-IDENTITY
     LAST-UPDATED "9810130000Z"
     ORGANIZATION "SALIX Technologies"
     CONTACT-INFO "904 Wind River Lane
                   Suite 101
                   Gaithersburg, MD  20878
                   (301)-417-0017"
     DESCRIPTION  "The MIB describing SALIX specific extensions
                   to the M4-MIB"
     ::= { salixGeneric 5 }

   salixM4MIBObjects OBJECT IDENTIFIER ::= { salixM4MIB 1 }
   salixM4MIBTraps   OBJECT IDENTIFIER ::= { salixM4MIB 2 }
   salixM4MIBCompliance OBJECT IDENTIFIER ::= { salixM4MIB 3 }
   salixM4MIBTrapPrefix OBJECT IDENTIFIER ::= { salixM4MIB 0 }

-- HNE ATM M4 Objects (ATM-FORUM-M4-MIB Extensions)

  -- HNE Equipment Holder

  salixAtmfM4EquipHolderTable OBJECT-TYPE
       SYNTAX     SEQUENCE OF    SalixAtmfM4EquipHolderEntry
       MAX-ACCESS not-accessible
       STATUS     current
       DESCRIPTION
            "The HNE equipment holder table.  This table augments the
             atmfM4EquipHolderTable defined in the ATM-FORUM-M4-MIB."
       ::= { salixM4MIBObjects 2 }

  salixAtmfM4EquipHolderEntry OBJECT-TYPE
       SYNTAX     SalixAtmfM4EquipHolderEntry
       MAX-ACCESS not-accessible
       STATUS     current
       DESCRIPTION
            "An entry in the HNE equipment holder table. An entry
             contains HNE specific equipment holder information not found
             in the ATM-FORUM-M4-MIB."
       AUGMENTS { atmfM4EquipHolderEntry }
       ::= { salixAtmfM4EquipHolderTable 1 }

  SalixAtmfM4EquipHolderEntry ::= SEQUENCE {
            salixAtmfM4EquipHolderDownloadState          INTEGER,
            salixAtmfM4EquipHolderDownloadStatusMessage  OCTET STRING
       }

  salixAtmfM4EquipHolderDownloadState OBJECT-TYPE
       SYNTAX     INTEGER { none(1),
                            inProgress(2),
                            success(3),
                            aborted(4),
                            failed(5)
                          }
       MAX-ACCESS read-only
       STATUS     current
       DESCRIPTION
            "The software download state of the plug-in unit contained
             in the equipment holder. This status is only valid if the
             equipment holder is a slot.  If the equipment holder is not
             a slot then the status will be none(1).

             none(1)       - download not started or not supported
             inProgress(2) - download in progress
             success(3)    - download to plug-in unit successful
             aborted(4)    - download aborted
             failed(5)     - download failed"
         DEFVAL { none }
         ::= { salixAtmfM4EquipHolderEntry 1 }
         
  salixAtmfM4EquipHolderDownloadStatusMessage OBJECT-TYPE
       SYNTAX     OCTET STRING(SIZE (256))
       MAX-ACCESS read-only
       STATUS     current
       DESCRIPTION
            "Status message that describes the current state of the
             download as indicated by the 
             'salixAtmfM4EquipHolderDownloadState' attribute."
       ::= { salixAtmfM4EquipHolderEntry 2 }
         

  -- HNE Plug-in Unit (Augment the ATM-FORUM-M4-MIB)

  salixAtmfM4PlugInUnitTable OBJECT-TYPE
       SYNTAX     SEQUENCE OF    SalixAtmfM4PlugInUnitEntry
       MAX-ACCESS not-accessible
       STATUS     current
       DESCRIPTION
            "The HNE plug-in unit table.  This table augments the
             atmfM4PlugInUnitTable defined in the ATM-FORUM-M4-MIB."
       ::= { salixM4MIBObjects 3 }

  salixAtmfM4PlugInUnitEntry OBJECT-TYPE
       SYNTAX     SalixAtmfM4PlugInUnitEntry
       MAX-ACCESS not-accessible
       STATUS     current
       DESCRIPTION
            "An entry in the HNE plug-in unit table. An entry contains HNE
             specific plug-in information not found in the ATM-FORUM-M4-MIB."
       AUGMENTS { atmfM4PlugInUnitEntry }
       ::= { salixAtmfM4PlugInUnitTable 1 }

  SalixAtmfM4PlugInUnitEntry ::= SEQUENCE {
            salixAtmfM4PlugInUnitSerialNumber            DisplayString,
            salixAtmfM4PlugInUnitType                    SalixPlugInUnitType,
            salixAtmfM4PlugInUnitReset                   INTEGER,
            salixAtmfM4PlugInUnitHwRevision              DisplayString,
            salixAtmfM4PlugInUnitLedStatus               INTEGER,
            salixAtmfM4PlugInUnitRedundancyConfig        INTEGER,
            salixAtmfM4PlugInUnitRedundancyPartnerModule PhysicalIndex,
            salixAtmfM4PlugInUnitRedundancyPairStatus    INTEGER,
            salixAtmfM4PlugInUnitRedundancyStatusMessage OCTET STRING
       }

  salixAtmfM4PlugInUnitSerialNumber OBJECT-TYPE
       SYNTAX     DisplayString (SIZE (0..12))
       MAX-ACCESS read-only
       STATUS     current
       DESCRIPTION
            "The serial number of the plug-in unit."
       ::= { salixAtmfM4PlugInUnitEntry 1 }

  salixAtmfM4PlugInUnitType OBJECT-TYPE
       SYNTAX     SalixPlugInUnitType
       MAX-ACCESS read-only
       STATUS     current
       DESCRIPTION
            "The type of plug-in unit loaded in the slot."
       ::= { salixAtmfM4PlugInUnitEntry 2 }

  salixAtmfM4PlugInUnitReset OBJECT-TYPE
       SYNTAX     INTEGER { none(0), cold(1), warm(2) }
       MAX-ACCESS read-write
       STATUS     current
       DESCRIPTION
            "The type of reset to issue to the plug-in unit.  The
             following types of plug-in units can be reset, 'mpu',
             'dpu', 'smu', 'liu' and 'hsf'.

             Writing a cold(1) or warm(2) value to this object will
             initiate a reset of the plug-in unit.  The reset value
             will remain until the reset completes.  When completed
             the reset value will be changed to none(0). The following
             are valid reset values:

             cold(1) - cold reset initiated
             warm(2) - warm reset initiated"
       ::= { salixAtmfM4PlugInUnitEntry 3 }

  salixAtmfM4PlugInUnitHwRevision OBJECT-TYPE
       SYNTAX     DisplayString (SIZE (0..12))
       MAX-ACCESS read-only
       STATUS     current
       DESCRIPTION
            "The hardware revision of the plug-in unit."
       ::= { salixAtmfM4PlugInUnitEntry 4 }

  salixAtmfM4PlugInUnitLedStatus OBJECT-TYPE
       SYNTAX  INTEGER (1..63)
       MAX-ACCESS read-only
       STATUS     current
       DESCRIPTION
            "The status of the LEDs on the plug-in unit.  
             The various bit positions are:             
             1     OK LED is on
             2     OK LED is flashing
             4     Active LED is on
             8     Active LED is flashing
            16     Failed LED is on
            32     Failed LED is flashing"
       ::= { salixAtmfM4PlugInUnitEntry 5 }

  salixAtmfM4PlugInUnitRedundancyConfig OBJECT-TYPE
       SYNTAX     INTEGER { working(1),
                            protect(2),
                            none(3)
                          }                          
       MAX-ACCESS read-write
       STATUS     current
       DESCRIPTION
         "When retrieved, this attribute represents the current
          redundancy configuration of the specified Plug-In Unit.  A value 
          of 'none' indicates that the specified Plug-In Unit has no
          redundant module.  A status of either 'working' or 'protect'
          indicates that the specified Plug-In Unit is either the
          working or protect Plug-In Unit in a redundancy relationship.

          When used with the 'salixAtmfM4PlugInUnitRedundancyPartnerModule'
          attribute of the 'salixAtfM4PlugInUnitTable', it can be
          determined which Plug-In Units are in redudancy relationship
          and also the plug-in units role in that relationship (if
          they are in a relationship at all).

          In addition to using these attributes to get information on
          redundant modules, these attributes can also be used to
          create redundancy relationships.  By setting the
          'salixAtmfM4PlugInUnitRedundancyPartnerModule' to a valid PhysicalIndex
          and also setting the 'salixAtmfM4PlugInUnitRedundancyConfig' on either of
          the plug-in units to 'working' or 'protect' (as the desired
          configuration for that plug-in unit), a redundancy pair is
          created.  Redundancy relationships can be destroyed by
          setting the 'salixAtmfM4PlugInUnitRedundancyConfig' of either of the
          modules to 'none'.

          If a new value of either 'working' or 'protect' is written
          to the 'salixAtmfM4PlugInUnitRedundancyConfig' attribute, a switchover
          occurs in the system (i.e. the 'working' becomes the
          'protect' while the 'protect' becomes the 'working).

          NOTE: It is only necessary to set the information on one of
          the plug-in unit entries.  The information will be
          automatically set in the other entry by the system."
       DEFVAL { none }
       ::= { salixAtmfM4PlugInUnitEntry 6 }


  salixAtmfM4PlugInUnitRedundancyPartnerModule OBJECT-TYPE
       SYNTAX     PhysicalIndex
       MAX-ACCESS read-write
       STATUS     current
       DESCRIPTION
         "When retrieved, this attributes represents the current
          partner module of a pair of plugins that are in redundancy
          relationship.  This attribute is only valid when the
          'salixAtmfM4PlugInUnitRedundancyConfig' attribute is set to
          either 'working' or 'protect'.

          Writing to this object can either create a redundancy pair
          (if one doesn't already exist) or can cause a manual
          changeover of the working module (if there is a new value
          written).

          NOTE: It is only necessary to set the information on one of
          plug-in units entries.  The information will be
          automatically set in the other entry by the system."
       ::= { salixAtmfM4PlugInUnitEntry 7 }


  salixAtmfM4PlugInUnitRedundancyPairStatus OBJECT-TYPE
       SYNTAX     INTEGER { none(1), created(2), configured(3), active(4) }
       MAX-ACCESS read-only
       STATUS     current
       DESCRIPTION
         "This attribute reflects the status of the redundant 
          plug-in unit pair:
             none(1)       -  indicates that a 1:1 redundant pair does not exist
                              with this plug-in unit.
                           
             created(2)    -  indicates that a 1:1 redundant pair was created between
                              this plug-in unit and the plug-in unit identified
                              by the 'salixAtmfM4PlugInUnitRedundancyPartnerModule'.

             configured(3)    indicates that the working module identified by this
                              1:1 redundant pair is operational.
                              
             active(4)     -  indicates that 1:1 redundancy is active. This
                              state is entered if both redundant plug-in units
                              are physically installed with administrative and
                              operational status as 'up'."
                           
       ::= { salixAtmfM4PlugInUnitEntry 8 }

  salixAtmfM4PlugInUnitRedundancyStatusMessage OBJECT-TYPE
       SYNTAX     OCTET STRING(SIZE (256))
       MAX-ACCESS read-only
       STATUS     current
       DESCRIPTION
            "Status message that describes the current state of the
             redundant plug-in unit pair."
       ::= { salixAtmfM4PlugInUnitEntry 9 }


  -- Definitions for Notifications 
 
  SalixAtmfM4SwitchoverReasons ::= TEXTUAL-CONVENTION
       STATUS       current
       DESCRIPTION
            "Definitions that identify reasons for a switchover to occur
             between two plug-in units in a redundancy pair."
       SYNTAX       INTEGER {  administrative(1),
                               pluginRemoved(2),                               
                               failure(3)
                            }
                                                                 
  salixAtmfM4TrapSwitchoverReason OBJECT-TYPE
       SYNTAX       SalixAtmfM4SwitchoverReasons
       MAX-ACCESS   accessible-for-notify
       STATUS       current
       DESCRIPTION
            "This object identifies the reason for the switchover
             that occurred between two plug-in units in a redundant
             pair."
          ::= { salixM4MIBObjects 4 }
          

  -- State change notification traps
   
  salixAtmfM4HwSwDownloadSuccess NOTIFICATION-TYPE
       OBJECTS   { entPhysicalIndex,
                   hrSWInstalledIndex,
                   atmfM4TrapAlarmSeverity }
       STATUS    current
       DESCRIPTION
            "Indicates that software was successfully downloaded to
             the physical entity identified by the entPhysicalIndex.
             For a successful download to a 'salixSysSwDownloadEntry'
             the physical entity will identify an instance of a
             'salixAtmfM4PlugInUnitEntry' that represents the physical
             device that received the download.  The 'hrSWInstalledIndex'
             represents the instance of the 'salixSysSwDownloadEntry' 
             or download destination on the physical entity.

             For a successful download to a 'salixAtmfM4EquipHolderEntry'
             the physical entity will identify an instance of a
             'salixAtmfM4EquipHolderEntry' that represents the physical
             device that received the download.  The 'hrSWInstalledIndex'
             represents the instance of the 'salixSysHrSWInstalledEntry' 
             or source of the download."
       ::= { salixM4MIBTrapPrefix 1 }        
                                                                
   
   salixAtmfM4PlugInUnitRedundancyPairCreated   NOTIFICATION-TYPE
       OBJECTS   { salixAtmfM4PlugInUnitRedundancyConfig,
                   salixAtmfM4PlugInUnitRedundancyConfig
                 }
       STATUS    current
       DESCRIPTION
            "Indicates that a 1:1 redundancy pair was created between 
             two plug-in units.  The salixAtmfM4PlugInUnitRedundancyConfig'
             objects identify the 'working' and 'protect' plug-in units
             configured as the redundant pair."             
       ::= { salixM4MIBTrapPrefix 2 }

   salixAtmfM4PlugInUnitRedundancyPairDestroyed NOTIFICATION-TYPE
       OBJECTS   { salixAtmfM4PlugInUnitRedundancyConfig,
                   salixAtmfM4PlugInUnitRedundancyConfig
                 }
       STATUS    current
       DESCRIPTION
            "Indicates that the 1:1 redundancy pair between the two
             plug-in units identified by the 
             salixAtmfM4PlugInUnitRedundancyConfig objects was
             destroyed."
       ::= { salixM4MIBTrapPrefix 3 }

   salixAtmfM4PlugInUnitRedundancyPairSwitchover  NOTIFICATION-TYPE
       OBJECTS   { salixAtmfM4PlugInUnitRedundancyConfig,
                   salixAtmfM4PlugInUnitRedundancyConfig,
                   salixAtmfM4TrapSwitchoverReason
                 }
       STATUS    current
       DESCRIPTION
            "Indicates a switch from the working plug-in unit of the 
             redundant pair to the protect partner plug-in unit. The
             'salixAtmfM4PlugInUnitRedundancyConfig' objects reflect
             the redundancy configuration of the plug-in units after
             the switchover.  The reason for the switchover is 
             identified by the 'salixAtmfM4TrapSwitchoverReason' object."
       ::= { salixM4MIBTrapPrefix 4 }
     
   salixAtmfM4PlugInUnitRedundancyPairStatusChange  NOTIFICATION-TYPE
       OBJECTS   { salixAtmfM4PlugInUnitRedundancyConfig,
                   salixAtmfM4PlugInUnitRedundancyConfig,
                   salixAtmfM4PlugInUnitRedundancyPairStatus }
       STATUS    current
       DESCRIPTION
            "Indicates a change in status of the redundant plug-in unit
            pair.  The 'salixAtmfM4PlugInUnitRedundancyConfig' objects
            reflect the current redundancy configuration of the plug-in 
            units.  The 'salixAtmfM4PlugInUnitRedundancyPairStatus' object
            identifies the current status of the redundant plug-in unit
            pair."             
       ::= { salixM4MIBTrapPrefix 5 }
     
-- Conformance Statements

salixM4Groups      OBJECT IDENTIFIER  ::= { salixM4MIBCompliance 1 }
salixM4Compliances OBJECT IDENTIFIER  ::= { salixM4MIBCompliance 2 }

   salixM4Group OBJECT-GROUP
      OBJECTS {
         salixAtmfM4EquipHolderDownloadState,
         salixAtmfM4EquipHolderDownloadStatusMessage
      }
      STATUS         current
      DESCRIPTION    "Salix M4 Objects Group"
      ::= { salixM4Groups 1}


-- Compliance Statements

salixM4Compliance MODULE-COMPLIANCE
     STATUS       current
     DESCRIPTION
                  "The basic implementation requirements for the SALIX-M4-MIB."
     MODULE       -- This module
     MANDATORY-GROUPS { salixM4Group }
     ::= { salixM4Compliances 1 }

END
