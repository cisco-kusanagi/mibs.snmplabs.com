IPV4REDUNDANCY-MIB

   --FORCE-INCLUDE <mib.h>
   --FORCE-INCLUDE <snmpdefs.h>
   --FORCE-INCLUDE <snmpstat.h>
   --FORCE-INCLUDE "mibproto.h"
 
   DEFINITIONS ::= BEGIN

  IMPORTS
    MODULE-IDENTITY, OBJECT-TYPE, Integer32,IpAddress
      FROM SNMPv2-SMI
    RowStatus,  DisplayString
      FROM SNMPv2-TC
    apIpv4Redundancy
      FROM APENT-MIB;

    ipv4RedundancyMib MODULE-IDENTITY
     LAST-UPDATED "9711242000Z" -- Mon November 24 20:00:00 EST 1997
     ORGANIZATION "ArrowPoint Communications Inc."
     CONTACT-INFO
     "Postal:               ArrowPoint Communications Inc.
                            50 Nagog Park
                            Acton, Massachusetts 01720
     Tel:                   +1 978-206-3000  option 1
     E-Mail:                support@arrowpoint.com"
  DESCRIPTION
    "This MIB module describes the ArrowPoint enterprise
     MIB support for IPv4 Redundancy"
     ::= { apIpv4Redundancy 1}


--arrowpoint
-- apmgmt
--  ipv4Ext
--   apIpv4Redundancy
--     apIpv4RedundancyVRConfigTable
--     apIpv4RedundancyVIPConfigTable
--     apIpv4RedundancyIntConfigTable

--  virtual router configurtion

apIpv4RedundancyVRConfigTable OBJECT-TYPE
  SYNTAX      SEQUENCE OF ApIpv4RedundancyVRConfigEntry
  MAX-ACCESS  not-accessible
  STATUS      current
  DESCRIPTION
    "Virtual router entries table"
  ::= {apIpv4Redundancy 2}

apIpv4RedundancyVRConfigEntry OBJECT-TYPE
  SYNTAX      ApIpv4RedundancyVRConfigEntry
  MAX-ACCESS  not-accessible
  STATUS      current
  DESCRIPTION
    "Virtual router entry"
  INDEX  {apIpv4RedundancyVRIntAddr,apIpv4RedundancyVRID}
  ::= {apIpv4RedundancyVRConfigTable 1}

ApIpv4RedundancyVRConfigEntry ::=
  SEQUENCE {
       apIpv4RedundancyVRIntAddr       IpAddress,
       apIpv4RedundancyVRID            Integer32,
       apIpv4RedundancyConfigPriority  Integer32,
       apIpv4RedundancyAdPriority      Integer32,
       apIpv4RedundancyName            DisplayString,
       apIpv4RedundancyVRPreempt       INTEGER,
       apIpv4RedundancyVRState         INTEGER,
       apIpv4RedundancyVRMasterIP      IpAddress,
       apIpv4RedundancyVRLastChange    DisplayString,
       apIpv4RedundancyVRStateChanges  Integer32,
       apIpv4RedundancyVRStatus        RowStatus
     }


apIpv4RedundancyVRIntAddr OBJECT-TYPE
  SYNTAX      IpAddress
  MAX-ACCESS  read-create
  STATUS      current
  DESCRIPTION
    "Virtual router's IP interface address."
  ::= {apIpv4RedundancyVRConfigEntry 2}

apIpv4RedundancyVRID OBJECT-TYPE
  SYNTAX      Integer32(1..255)
  MAX-ACCESS  read-create
  STATUS      current
  DESCRIPTION
    "Virtual router's identifier."
  ::= {apIpv4RedundancyVRConfigEntry 1}

apIpv4RedundancyConfigPriority OBJECT-TYPE
  SYNTAX      Integer32
  MAX-ACCESS  read-create
  STATUS      current
  DESCRIPTION
    "Virtual router's configured priority. "
  ::= {apIpv4RedundancyVRConfigEntry 3}

apIpv4RedundancyAdPriority OBJECT-TYPE
  SYNTAX      Integer32
  MAX-ACCESS  read-only
  STATUS      current
  DESCRIPTION
    "Virtual router's advertised priority. "
  ::= {apIpv4RedundancyVRConfigEntry 4}

apIpv4RedundancyName OBJECT-TYPE
  SYNTAX      DisplayString (SIZE(0..31))
  MAX-ACCESS  read-create
  STATUS      current
  DESCRIPTION
    "Virtual router's critical service Name."
  ::= {apIpv4RedundancyVRConfigEntry 5}

-- The Default is different then the VRRP RFC but that is by design.
apIpv4RedundancyVRPreempt OBJECT-TYPE
  SYNTAX INTEGER {
    false(0),
    true(1)
  }
  MAX-ACCESS  read-create
  STATUS      current
  DESCRIPTION
    "Virtual router's preempt state."
  DEFVAL{0}
  ::= {apIpv4RedundancyVRConfigEntry 6}

apIpv4RedundancyVRState OBJECT-TYPE
  SYNTAX INTEGER{
    ifDown(0),
    noService(1),
    backup(2),
    master(3),
    idle(4)
  }
  MAX-ACCESS  read-only
  STATUS      current
  DESCRIPTION
    "Virtual router's state."
  DEFVAL{0}
  ::= {apIpv4RedundancyVRConfigEntry 7}

apIpv4RedundancyVRMasterIP OBJECT-TYPE
  SYNTAX      IpAddress
  MAX-ACCESS  read-only
  STATUS      current
  DESCRIPTION
    "Master virtual router's IP address."
--  DEFVAL{'00000000'H} 0.0.0.0
  ::= {apIpv4RedundancyVRConfigEntry 8}

apIpv4RedundancyVRLastChange OBJECT-TYPE
  SYNTAX      DisplayString(SIZE(0..19))
  MAX-ACCESS  read-only
  STATUS      current
  DESCRIPTION
    "Time at virtual router's last state change."
  ::= {apIpv4RedundancyVRConfigEntry 9}

apIpv4RedundancyVRStateChanges OBJECT-TYPE
  SYNTAX      Integer32
  MAX-ACCESS  read-only
  STATUS      current
  DESCRIPTION
    "Count of virtual router's state changes."
  ::= {apIpv4RedundancyVRConfigEntry 10}   

apIpv4RedundancyVRStatus OBJECT-TYPE
  SYNTAX      RowStatus
  MAX-ACCESS  read-create
  STATUS      current
  DESCRIPTION
    "Row status."
  ::=  {apIpv4RedundancyVRConfigEntry 11}

apIpv4RedundancyIntConfigTable OBJECT-TYPE
  SYNTAX      SEQUENCE OF ApIpv4RedundancyIntConfigEntry
  MAX-ACCESS  not-accessible
  STATUS      current
  DESCRIPTION
    "Redundant interface address entries table."
  ::= {apIpv4Redundancy 3}

apIpv4RedundancyIntConfigEntry OBJECT-TYPE
  SYNTAX      ApIpv4RedundancyIntConfigEntry
  MAX-ACCESS  not-accessible
  STATUS      current
  DESCRIPTION
    "Redundant interface address entry."
  INDEX  {apIpv4RedundancyIntAddress, apIpv4RedundancyIntVipAddress,apIpv4RedundancyIntVRID}
  ::= {apIpv4RedundancyIntConfigTable 1}

ApIpv4RedundancyIntConfigEntry ::=
  SEQUENCE {
       apIpv4RedundancyIntAddress       IpAddress,
       apIpv4RedundancyIntVipAddress    IpAddress,
       apIpv4RedundancyIntVRID          Integer32,
       apIpv4RedundancyIntState         INTEGER,
       apIpv4RedundancyIntMasterIP      IpAddress,
       apIpv4RedundancyIntLastChange    DisplayString,
       apIpv4RedundancyIntStateChanges  Integer32,
       apIpv4RedundancyIntStatus        RowStatus
    }

apIpv4RedundancyIntAddress OBJECT-TYPE
  SYNTAX      IpAddress
  MAX-ACCESS  read-create
  STATUS      current
  DESCRIPTION
    "Redundant interface address."
  ::= {apIpv4RedundancyIntConfigEntry 1}

apIpv4RedundancyIntVipAddress OBJECT-TYPE
  SYNTAX      IpAddress
  MAX-ACCESS  read-create
  STATUS      current
  DESCRIPTION
    "Redundant VIP address."
  ::= {apIpv4RedundancyIntConfigEntry 2}

apIpv4RedundancyIntVRID OBJECT-TYPE
  SYNTAX      Integer32(1..255)
  MAX-ACCESS  read-create
  STATUS      current
  DESCRIPTION
    "Virtual router Identifier."
  ::= {apIpv4RedundancyIntConfigEntry 3}

apIpv4RedundancyIntState OBJECT-TYPE
  SYNTAX INTEGER {
    noVirtualRouter(1),
    backup(2),
    backupshared(3),
    master(4)
  }
  MAX-ACCESS   read-only
  STATUS       current
  DESCRIPTION
    "Virtual router state."
  DEFVAL{1}
  ::= {apIpv4RedundancyIntConfigEntry 4} 
  
apIpv4RedundancyIntMasterIP OBJECT-TYPE
  SYNTAX      IpAddress
  MAX-ACCESS  read-only
  STATUS      current
  DESCRIPTION
    "Master virtual router IP address."
--  DEFVAL{'00000000'H} 0.0.0.0
  ::= {apIpv4RedundancyIntConfigEntry 5}

apIpv4RedundancyIntLastChange OBJECT-TYPE
  SYNTAX      DisplayString(SIZE(0..19))
  MAX-ACCESS  read-only
  STATUS      current
  DESCRIPTION
    "Time at virtual router's last state change."
  ::= {apIpv4RedundancyIntConfigEntry 6}

apIpv4RedundancyIntStateChanges OBJECT-TYPE
  SYNTAX      Integer32
  MAX-ACCESS  read-only
  STATUS      current
  DESCRIPTION
    "Count of virtual router's state changes."
  ::= {apIpv4RedundancyIntConfigEntry 7}                
  
apIpv4RedundancyIntStatus OBJECT-TYPE
  SYNTAX      RowStatus
  MAX-ACCESS  read-create
  STATUS      current
  DESCRIPTION
    "Row status."
  ::=  {apIpv4RedundancyIntConfigEntry 8}
      
apIpv4RedundancyVIPConfigTable OBJECT-TYPE
  SYNTAX      SEQUENCE OF ApIpv4RedundancyVIPConfigEntry
  MAX-ACCESS  not-accessible
  STATUS      current
  DESCRIPTION
    "Redundant VIP address entries table."
  ::= {apIpv4Redundancy 4}

apIpv4RedundancyVIPConfigEntry OBJECT-TYPE
  SYNTAX      ApIpv4RedundancyVIPConfigEntry
  MAX-ACCESS  not-accessible
  STATUS      current
  DESCRIPTION
    "Redundant VIP address entry."
  INDEX  {apIpv4RedundancyVIPIntAddress,apIpv4RedundancyVIPAddress,apIpv4RedundancyVIPVRID}
  ::= {apIpv4RedundancyVIPConfigTable 1}

ApIpv4RedundancyVIPConfigEntry ::=
  SEQUENCE {
       apIpv4RedundancyVIPIntAddress    IpAddress,
       apIpv4RedundancyVIPAddress       IpAddress,
       apIpv4RedundancyVIPVRID          Integer32,
       apIpv4RedundancyVIPRange         Integer32,
       apIpv4RedundancyVIPSharedVIP     INTEGER,
       apIpv4RedundancyVIPState          INTEGER,
       apIpv4RedundancyVIPMasterIP      IpAddress,
       apIpv4RedundancyVIPLastChange    DisplayString,
       apIpv4RedundancyVIPStateChanges  Integer32,
       apIpv4RedundancyVIPStatus         RowStatus
    }


apIpv4RedundancyVIPIntAddress OBJECT-TYPE
  SYNTAX      IpAddress
  MAX-ACCESS  read-create
  STATUS      current
  DESCRIPTION
    "Redundant VIP address' interface."
  ::= {apIpv4RedundancyVIPConfigEntry 1}

apIpv4RedundancyVIPAddress OBJECT-TYPE
  SYNTAX      IpAddress
  MAX-ACCESS  read-create
  STATUS      current
  DESCRIPTION
    "Redundant VIP address."
  ::= {apIpv4RedundancyVIPConfigEntry 2}


apIpv4RedundancyVIPVRID OBJECT-TYPE
  SYNTAX      Integer32(1..255)
  MAX-ACCESS  read-create
  STATUS      current
  DESCRIPTION
    "Virtual router identifier."
  ::= {apIpv4RedundancyVIPConfigEntry 3}

apIpv4RedundancyVIPRange OBJECT-TYPE
  SYNTAX        Integer32(0..65535)
  MAX-ACCESS    read-create
  STATUS        current
  DESCRIPTION
    "Redundant VIP address' address range."
  ::= {apIpv4RedundancyVIPConfigEntry 4}

apIpv4RedundancyVIPSharedVIP OBJECT-TYPE
  SYNTAX INTEGER {
    false(0),
    true(1)        
  }
  MAX-ACCESS  read-create
  STATUS      current
  DESCRIPTION
    "Shared VIP."
  ::= {apIpv4RedundancyVIPConfigEntry 5} 

apIpv4RedundancyVIPState OBJECT-TYPE
  SYNTAX INTEGER {
    noVirtualRouter(1),
    backup(2),
    backupshared(3),
    master(4)
  }
  MAX-ACCESS  read-only
  STATUS      current
  DESCRIPTION
    "Virtual router's state."
  DEFVAL{1}
  ::= {apIpv4RedundancyVIPConfigEntry 6} 
  
apIpv4RedundancyVIPMasterIP OBJECT-TYPE
  SYNTAX      IpAddress
  MAX-ACCESS  read-only
  STATUS      current
  DESCRIPTION
    "Master virtual router's IP address."
--  DEFVAL{'00000000'H} 0.0.0.0
  ::= {apIpv4RedundancyVIPConfigEntry 7}

apIpv4RedundancyVIPLastChange OBJECT-TYPE
  SYNTAX      DisplayString(SIZE(0..19))
  MAX-ACCESS  read-only
  STATUS      current
  DESCRIPTION
    "Time at virtual router's last state change."
  ::= {apIpv4RedundancyVIPConfigEntry 8}

apIpv4RedundancyVIPStateChanges OBJECT-TYPE
  SYNTAX      Integer32
  MAX-ACCESS  read-only
  STATUS      current
  DESCRIPTION
    "Count of virtual router's state changes."
  ::= {apIpv4RedundancyVIPConfigEntry 9}

apIpv4RedundancyVIPStatus OBJECT-TYPE
  SYNTAX      RowStatus
  MAX-ACCESS  read-create
  STATUS      current
  DESCRIPTION
    "Row status."
  ::=  {apIpv4RedundancyVIPConfigEntry 10}

apIpv4RedundancyServConfigTable OBJECT-TYPE
  SYNTAX      SEQUENCE OF ApIpv4RedundancyServConfigEntry
  MAX-ACCESS  not-accessible
  STATUS      current
  DESCRIPTION
    "Virtual router entries table"
  ::= {apIpv4Redundancy 6}

apIpv4RedundancyServConfigEntry OBJECT-TYPE
  SYNTAX      ApIpv4RedundancyServConfigEntry
  MAX-ACCESS  not-accessible
  STATUS      current
  DESCRIPTION
    "Virtual router entry"
  INDEX  {apIpv4RedundancyServIntAddr,apIpv4RedundancyServVRID,apIpv4RedundancyServName}
  ::= {apIpv4RedundancyServConfigTable 1}

ApIpv4RedundancyServConfigEntry ::=
  SEQUENCE {     
  	   apIpv4RedundancyServIntAddr		IpAddress,
  	   apIpv4RedundancyServVRID         Integer32,
       apIpv4RedundancyServName			DisplayString,   
       apIpv4RedundancyServType			INTEGER,
       apIpv4RedundancyServStatus       RowStatus
       }
 
apIpv4RedundancyServIntAddr OBJECT-TYPE
  SYNTAX		IpAddress
  MAX-ACCESS	read-create
  STATUS		current
  DESCRIPTION
  	"Interface Address that the VRID of this server belongs to."
  ::= {apIpv4RedundancyServConfigEntry 1}
  
apIpv4RedundancyServVRID OBJECT-TYPE
  SYNTAX	Integer32(1..255)
  MAX-ACCESS	read-create
  STATUS		current
  DESCRIPTION
  	"VRID the this server belongs to."
  ::= {apIpv4RedundancyServConfigEntry 2}
  
apIpv4RedundancyServName OBJECT-TYPE
  SYNTAX		DisplayString(SIZE(0..31))
  MAX-ACCESS	read-create
  STATUS		current
  DESCRIPTION
  	"The Name of the service."
  ::= {apIpv4RedundancyServConfigEntry 3}
  
apIpv4RedundancyServType OBJECT-TYPE
  SYNTAX	    INTEGER    {
						unknown(0),
 					    uplink(1),
  					    normal(2),
  					    script(3)
   					    }
  MAX-ACCESS	read-only
  STATUS		current
  DESCRIPTION
  	"Type of service."
  ::= {apIpv4RedundancyServConfigEntry 4}
  
apIpv4RedundancyServStatus OBJECT-TYPE
  SYNTAX      RowStatus
  MAX-ACCESS  read-create
  STATUS      current
  DESCRIPTION
    "Row status."
  ::=  {apIpv4RedundancyServConfigEntry 5}

apIpv4RedundancyEnabled OBJECT-TYPE
  SYNTAX	INTEGER {
				false(0),
				true(1)
			}
  MAX-ACCESS	read-only
  STATUS		current
  DESCRIPTION
	"Is VIP Redundancy configured on this box."
  ::= {apIpv4Redundancy 7}
END
