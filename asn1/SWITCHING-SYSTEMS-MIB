--	Switching System Management Information Base
--	Version 1.0.0
--	August 25, 1997

--	3Com Corporation
--	80 Central Street
--	Boxborough, MA 01719 
--	(508) 264-1400

--------------------------------------------------------------------------------------------------------
--	Change History:
--  9/29/97 - iwolf     Relabel S2 to Switching Systems
--  9/27/97 - iwolf     Create swSysBridgeVlanMode in swSysBridgeTable
--  9/27/97 - iwolf     Define additional swSysSystemType values for CB9400,
--                      SS3900 and SS9300
--  8/25/97 - jscano    Originally created
--
--------------------------------------------------------------------------------------------------------

SWITCHING-SYSTEMS-MIB DEFINITIONS ::= BEGIN

IMPORTS
	enterprises, Counter, Gauge, IpAddress FROM RFC1155-SMI
	DisplayString                          FROM RFC1213-MIB
	OBJECT-TYPE                            FROM RFC-1212
	TRAP-TYPE                              FROM RFC-1215
	RowStatus	FROM SNMPv2-TC;


-- Textual conventions

-- RowStatus as defined in SNMPv2
-- Refer to rfc1443.txt for concise definition
-- This is a place holder until lp.mib if fully compliant with SNMPv2

-- RowStatus	::= INTEGER ( 1..6 )

		-- the following two values are states:
		-- these values may be read or written
		-- active(1),
		-- notInService(2),
		-- the following value is a state:
		-- this value may be read, but not written
		-- notReady(3),
		-- the following three values are
		-- actions: these values may be written,
		-- but are never read
		-- createAndGo(4),
		-- createAndWait(5),
		--destroy(6)

-- Switching Systems Storage Type

SwSysStorageType ::= INTEGER (1..3)
		--storageTypeUnknown(1), (not settable)
   		--storageNonVolatileMemory(2),
    	--storageFlashMemory(3)

-- Switching Systems Address Type

SwSysAddressType ::= INTEGER ( 1..2 )
   		--addrTypeUnknown(1), (not settable)
   		--addrIp(2)

-- Switching Systems Resource Type

SwSysResourceType ::= INTEGER ( 1..3 )
   		--resourceTypeUnknown(1), (not settable)
   		--resourceSystem(2)
	 	--resourceBridge(3)


-- Switching Systems Resource Bit Mask
--
-- This type represents a variable length bit mask 
-- encoded as an octet string in which the bits are 
-- numbered from left-to-right.
--
-- Example: For an octet string with a length of 4:
--
--                Byte 0    Byte 1    Byte 2    Byte 3
-- Bits:         76543210  76543210  76543210  76543210
-- 
-- Bit String Indices:
--
--           Byte         Bit         Index
--           ====         ====        =====
--            0            7            1
--            0            6            2
--            0            5            3
--            .            .            .
--            .            .            .
--            1            7            9
--            1            6            10
--            1            5            11
--            .            .            .
--            .            .            .
--            4            7            25
--            4            6            26
--            4            5            27
--            .            .            .
--            .            .            .

SwSysResourceBitMask ::= OCTET STRING (SIZE(4))


IpxNetworkNumber ::= OCTET STRING (SIZE(4))

ATNetworkNumber ::=
	-- 2 octets of net number
	-- in network byte order
	OCTET STRING (SIZE (2))

ATName ::=
	-- 0 to 32 octets of AppleTalk
	-- ASCII [Inside AppleTalk]
	OCTET STRING (SIZE (0..32))

DdpNodeAddress ::= 
    -- 2 octets of net number
    -- in network byte order,
    -- 1 octet of node number
	OCTET STRING (SIZE (3))

MacAddress ::=
	-- a 6 octet address in
	-- the "canonical" order
	-- defined by IEEE 802.1a, i.e., as if it were transmitted least
	-- significant bit first
	OCTET STRING (SIZE (6))


--
-- Object identifiers
--
	
synernetics					OBJECT IDENTIFIER ::= { enterprises 114 }

switchingSystems			OBJECT IDENTIFIER ::= { synernetics 1 } 
switchingSystemsProducts	OBJECT IDENTIFIER ::= { synernetics 2 }

corebuilderProductsI		OBJECT IDENTIFIER ::= { switchingSystems 3}
switchingSystemsMib			OBJECT IDENTIFIER ::= { switchingSystems 4}
corebuilderSystemsMib		OBJECT IDENTIFIER ::= { switchingSystems 5}
superstackSystemsMib		OBJECT IDENTIFIER ::= { switchingSystems 6}
switchingSystemsFddiMib		OBJECT IDENTIFIER ::= { switchingSystems 10}

corebuilderProductsII		OBJECT IDENTIFIER ::= { switchingSystemsProducts 1}
superstackProducts			OBJECT IDENTIFIER ::= { switchingSystemsProducts 2}


-- switchingSystemsMib groups.
 
swSysSystem             OBJECT IDENTIFIER ::= { switchingSystemsMib 1 }
swSysSlot               OBJECT IDENTIFIER ::= { switchingSystemsMib 2 }
swSysControlPanel       OBJECT IDENTIFIER ::= { switchingSystemsMib 3 }
swSysPowerSupply        OBJECT IDENTIFIER ::= { switchingSystemsMib 4 }
swSysSnmp               OBJECT IDENTIFIER ::= { switchingSystemsMib 5 }
swSysAgent              OBJECT IDENTIFIER ::= { switchingSystemsMib 6 }
swSysInterface          OBJECT IDENTIFIER ::= { switchingSystemsMib 7 }
swSysEthernetPort		OBJECT IDENTIFIER ::= { switchingSystemsMib 8 }
swSysSmt				OBJECT IDENTIFIER ::= { switchingSystemsMib 9 }
swSysBridge				OBJECT IDENTIFIER ::= { switchingSystemsMib 10 }
swSysIpRouter			OBJECT IDENTIFIER ::= { switchingSystemsMib 11 }
swSysNetworkMonitor		OBJECT IDENTIFIER ::= { switchingSystemsMib 12 }
swSysTokenRingPort		OBJECT IDENTIFIER ::= { switchingSystemsMib 13 }
swSysFtGroup			OBJECT IDENTIFIER ::= { switchingSystemsMib 14 }
swSysIpGroup            OBJECT IDENTIFIER ::= { switchingSystemsMib 15 }
swSysIpxGroup           OBJECT IDENTIFIER ::= { switchingSystemsMib 16 }
swSysAppleTalkGroup     OBJECT IDENTIFIER ::= { switchingSystemsMib 17 }
swSysModuleCardGroup    OBJECT IDENTIFIER ::= { switchingSystemsMib 18 }
swSysDiagnosticsGroup   OBJECT IDENTIFIER ::= { switchingSystemsMib 19 }



-- The Switching Systems MIB system group.  Implementation of this
-- group is mandatory for agents which manage system resources.

swSysSystemId OBJECT-TYPE
	SYNTAX	INTEGER 
	ACCESS	read-only
	STATUS	mandatory
	DESCRIPTION
	"The unique identifier assigned to this system during
	manufacturing."
	::= { swSysSystem 1 }

swSysSystemType OBJECT-TYPE
	SYNTAX	INTEGER {
		other(1),
		lanplex6000(2),
		lanplex2000(3),
		coreBuilder3500(4),
		coreBuilder9400(5),
		superStack3900(6),
		superStack9300(7)
			}
	ACCESS	read-only
	STATUS	mandatory
	DESCRIPTION
	"The type of system."
	::= { swSysSystem 2 }

swSysSystemName OBJECT-TYPE
	SYNTAX	DisplayString (SIZE (0..31))
	ACCESS	read-write
	STATUS	mandatory
	DESCRIPTION
			"The text string describing this system."
	::= { swSysSystem 3 }

swSysSystemManufacturer OBJECT-TYPE
	SYNTAX	DisplayString (SIZE (0..127))
	ACCESS	read-only
	STATUS	mandatory
	DESCRIPTION
	"The text string describing the manufacturer of this
	system."
	::= { swSysSystem 4 }

swSysSystemHardwareRevision OBJECT-TYPE
	SYNTAX	OCTET STRING (SIZE (2)) 
	ACCESS	read-only
	STATUS	mandatory
	DESCRIPTION
	"The revision level of the system, contained in two
	octets.  The first octet indicates the artwork revision,
	and the second octet indicates the rework level."
	::= { swSysSystem 5 }

swSysSystemMemorySize OBJECT-TYPE
	SYNTAX	INTEGER 
	ACCESS	read-only
	STATUS	mandatory
	DESCRIPTION
	"The amount of memory (RAM), in bytes, present on the
	system processor board." 
	::= { swSysSystem 6 }

swSysSystemFlashMemorySize OBJECT-TYPE
	SYNTAX	INTEGER 
	ACCESS	read-only
	STATUS	mandatory
	DESCRIPTION
	"The amount of flash memory, in bytes, present on the
	system processor board."
	::= { swSysSystem 7 }

swSysSystemNvMemorySize OBJECT-TYPE
	SYNTAX	INTEGER 
	ACCESS	read-only
	STATUS	mandatory
	DESCRIPTION
	"The amount of non-volatile memory, in bytes, present
	on the system processor board." 
::= { swSysSystem 8 }

swSysSystemSoftwareRevision OBJECT-TYPE
	SYNTAX	OCTET STRING (SIZE (4)) 
	ACCESS	read-only
	STATUS	mandatory
	DESCRIPTION
	"The revision number of the Switching Systems software.
	Each byte indicates the following:
	byte 0: major release number.
	byte 1: minor release number.
	byte 2: update number.
	byte 3:
	bits 7-6: release type.
	bits 5-0: supplemental identifier."
::= { swSysSystem 9 }

swSysSystemBuildTime OBJECT-TYPE
	SYNTAX	DisplayString (SIZE (0..127))
	ACCESS	read-only
	STATUS	mandatory
	DESCRIPTION
	"The build time of the system software."
	::= { swSysSystem 10 }

swSysSystemSnmpRevision OBJECT-TYPE
	SYNTAX	INTEGER
	ACCESS	read-only
	STATUS	mandatory
	DESCRIPTION
	"The revision number of the SNMP agent implementation."
	::= { swSysSystem 11 }

swSysSystemRequestedSnmpMode OBJECT-TYPE
	SYNTAX	INTEGER {
		singleAgentMode(1),
		multiAgentMode(2)
			}
	ACCESS	read-write
	STATUS	mandatory
	DESCRIPTION
	"This object describes the requested SNMP mode for the
	system.  The value of this object indicates the mode that
	will become effective following a reboot of the system.
	Note that only a subset of the above values may be valid
	for some systems."
	::= { swSysSystem 12 }

swSysSystemCurrentSnmpMode OBJECT-TYPE
	SYNTAX	INTEGER {
		singleAgentMode(1),
		multiAgentMode(2)
			}
	ACCESS	read-only
	STATUS	mandatory
	DESCRIPTION
	"This object describes the currently active SNMP mode for
	the system.  Note that only a subset of the above values
	may be valid for some systems."
	::= { swSysSystem 13 }

swSysSystemAction OBJECT-TYPE
	SYNTAX	INTEGER {
		other(1),
		reset(2),
		nvReset(3)
			}
	ACCESS	read-write
	STATUS	mandatory
	DESCRIPTION
	"This object, when read, always returns the value other(1). 

	Setting this object to the value reset(2) causes a reset 
	of the system.  

	Setting this object to the value nvReset(3) causes the
	system's non-volatile configuration to be reset to the 
	default values.

	The value other(1) is not a vaild value for set operations."
	::= { swSysSystem 14 }

swSysSystemOvertemperature OBJECT-TYPE
	SYNTAX	INTEGER {
		true(1),
		false(2),
		notSupported(3)
			}
	ACCESS	read-only
	STATUS	mandatory
	DESCRIPTION
	"This object indicates the current overtemperature
	status for the system.  If the system does not support
	overtemperature detection, this object returns
	notSupported."
	::= { swSysSystem 15 }

swSysSystemFanFailure OBJECT-TYPE
	SYNTAX	INTEGER {
		true(1),
		false(2),
		notSupported(3)
		}
	ACCESS	read-only
	STATUS	mandatory
	DESCRIPTION
	"This object indicates the current fan status for the
	system.  If the system does not support fan failure
	detection, this object returns notSupported."
	::= { swSysSystem 16 }

swSysSystemProtocolMask OBJECT-TYPE
	SYNTAX	INTEGER 
	ACCESS	read-only
	STATUS	mandatory
	DESCRIPTION
	"This object is a bit mask that indicates which protocols
	 exist in the software image currently loaded in memory.  
	 The value of this OBJECT is a sum.  It initially takes
	 on the value 0, then for each protocol bit as defined
	 below, 2 raised to the value of the (bit position - 1)
	 is added to the sum.

	 The following bits are defined:

		IP_ROUTING	0x00000001
		IPX_ROUTING 0x00000002
		DDP_ROUTING 0x00000004

	 A value of 0x00000000 indicates the
	 standard switching software."
::= { swSysSystem 17 }

swSysSystemConsoleAccess OBJECT-TYPE
	SYNTAX  INTEGER {
		enabled  (1),	--  Console Access is permitted (unlocked)   
		disabled (2)	--  Console Access is prohibited  (locked)
	}
	ACCESS  read-write
	STATUS  mandatory
	DESCRIPTION
	"This object determines whether another device
	can remotely access the system console via Telnet,
	Rlogin, or modem port.

	An existing remote session will not be terminated
	when this value is modified."
::= { swSysSystem 18 }

swSysSystemConsoleReadPwd OBJECT-TYPE
	SYNTAX  DisplayString (SIZE (0..31)) 
	ACCESS  read-write
	STATUS  mandatory
	DESCRIPTION
	"This object is the console read-access password."
::= { swSysSystem 19 }

swSysSystemConsoleWritePwd OBJECT-TYPE
	SYNTAX  DisplayString (SIZE (0..31)) 
	ACCESS  read-write
	STATUS  mandatory
	DESCRIPTION
	"This object is the console write-access password. The
	read-write community string is required for access to this
	object."
::= { swSysSystem 20 }

swSysSystemConsoleAdminPwd OBJECT-TYPE
	SYNTAX  DisplayString (SIZE (0..31)) 
	ACCESS  read-write
	STATUS  mandatory
	DESCRIPTION
	"This object is the console admin-access password. The
	read-write community string is required for access to this
	object."
::= { swSysSystem 21 }


swSysSystemDateTime OBJECT-TYPE
	SYNTAX  DisplayString
	ACCESS  read-write
	STATUS  mandatory
	DESCRIPTION
		"The current date and time as reflected by the 
		system clock in the format mm/dd/yy hh:mm:ss xM."
::= { swSysSystem 22 }

swSysSystemDSTime OBJECT-TYPE
	SYNTAX  INTEGER (-120..120)
	ACCESS  read-write
	STATUS  mandatory
	DESCRIPTION
		"This parameter specifies the displacement, in
		minutes, from non-daylight savings time.  The
		swSysDSTime object, along with the swSysTimeZone
		object, allows the system to support Universal
		time for network communications spanning different
		time zones."
::= { swSysSystem 23 }

swSysSystemTimeZone OBJECT-TYPE
	SYNTAX  INTEGER (-720..720)
	ACCESS  read-write
	STATUS  mandatory
	DESCRIPTION
		"This parameter specifies, in minutes,
		displacement of the system west of Greenwich.
		A negative number for this parameter indicates how
		many minutes displacement east of Greenwich
		the site is located.  A positive number
		indicates the number of minutes west of Greenwich."
::= { swSysSystem 24 }

swSysSystemCurrentFddiStationMode OBJECT-TYPE
	SYNTAX  INTEGER {
		singleStationMode(1),
		multiStationMode(2)
		}
	ACCESS  read-only
	STATUS  mandatory
	DESCRIPTION
		"This object describes the current FDDI station 
		mode for systems that support multi-station mode."
::= { swSysSystem 25 }

swSysSystemRequestedFddiStationMode OBJECT-TYPE
	SYNTAX  INTEGER {
		singleStationMode(1),
		multiStationMode(2)
		}
	ACCESS  read-write
	STATUS  mandatory
	DESCRIPTION
		"This object describes the requested FDDI station 
		mode for systems that support multi-station mode.
		The requested mode will become current during
		the next system reboot."
::= { swSysSystem 26 }

swSysSystemLog OBJECT IDENTIFIER ::= { swSysSystem 27 }

swSysSystemLogEntryCurrentCount OBJECT-TYPE
	SYNTAX INTEGER
	ACCESS read-only
	STATUS mandatory
	DESCRIPTION
		"The number of entries currently recorded in the system log."
::= { swSysSystemLog 1 }

swSysSystemLogMaxSize OBJECT-TYPE
	SYNTAX INTEGER
	ACCESS read-only
	STATUS mandatory
	DESCRIPTION
		"The maximum number of events that can be recorded in the system log."
	::= { swSysSystemLog 2 }

swSysSystemLogSeverityThreshold OBJECT-TYPE
	SYNTAX INTEGER
	{	informational(1),
		warning(2),
		error(3),
		fatal(4)
	}
	ACCESS read-write
	STATUS mandatory
	DESCRIPTION
		"This object determines the miminum serverety level of events recorded in the
		system log.  For example, if the swSysSysteLogSeverityThreshold is set to errors(3)
		than only events which have serverity levels of error(3) or higher will
		be recorded."
::= { swSysSystemLog 3 }

swSysSystemLogTable OBJECT-TYPE
	SYNTAX SEQUENCE OF SwSysSystemLogEntry
	ACCESS not-accessible
	STATUS mandatory
	DESCRIPTION
		"This table provides information on recorded system events."
::= { swSysSystemLog 4 }

swSysSystemLogEntry OBJECT-TYPE
	SYNTAX SwSysSystemLogEntry
	ACCESS not-accessible
	STATUS mandatory
	DESCRIPTION
		"A system log entry."
	INDEX { swSysSystemLogIndex }
::= { swSysSystemLogTable 1 }

SwSysSystemLogEntry ::=	SEQUENCE {
	swSysSystemLogIndex 		INTEGER,
	swSysSystemLogSeverityLevel 	INTEGER,
	swSysSystemLogDateTime 		DisplayString,
	swSysSystemLogFacility 		INTEGER,
	swSysSystemLogMessage 		DisplayString 
}

swSysSystemLogIndex OBJECT-TYPE
	SYNTAX INTEGER
	ACCESS read-only
	STATUS mandatory
	DESCRIPTION
	"The index of the log entry relative to this entry."
::= { swSysSystemLogEntry 1 }

swSysSystemLogSeverityLevel OBJECT-TYPE
	SYNTAX INTEGER {
		information(1),
		warning(2),
		error(3),
		fatal(4)
	}
	ACCESS read-only
	STATUS mandatory
	DESCRIPTION
		"Indicates the severity level of the log entry."
::= { swSysSystemLogEntry 2 }

swSysSystemLogDateTime OBJECT-TYPE
	SYNTAX DisplayString 
	ACCESS read-only
	STATUS mandatory
	DESCRIPTION
		"Indicates the date and time of the log event and is formatted
		as follows: MM:DD:YY  HH:MM:SS."
	::= { swSysSystemLogEntry 3 }


swSysSystemLogFacility OBJECT-TYPE
	SYNTAX INTEGER
	{
		exception(1),
		operatingSystem(2),
		assertion(3),
		spanningTree(4),
		fcmlmm(5),
		lmmfddi(6),
		lmmboard(7),
		esm(8),
		trsm(9),
		efsm(10),
		fsm(11),
		hsi(12)
	}
	ACCESS read-only
	STATUS mandatory
	DESCRIPTION
		"The facility which entered the event in the log.  fcmlmm(6) represents
		those events which may be common to the Lanplex Management Module
		(LMM) and the FDDI Concentrator Module (FCM).  lmmfddi(6) represents
		those events specific to the FDDI portion of the LMM and lmmboard 
		represents general events logged by the LMM." 
::= { swSysSystemLogEntry 4 }

swSysSystemLogMessage OBJECT-TYPE
	SYNTAX DisplayString
	ACCESS read-only
	STATUS mandatory
	DESCRIPTION
		"The recorded log message."
::= { swSysSystemLogEntry 5 }

swSysSystemBaseMACAddress OBJECT-TYPE
	SYNTAX  MacAddress
	ACCESS  read-only
	STATUS  mandatory
	DESCRIPTION
		"The base MAC address for the system."
::= { swSysSystem 28 }

swSysSystemMACAddressCount OBJECT-TYPE
	SYNTAX  INTEGER
	ACCESS  read-only
	STATUS  mandatory
	DESCRIPTION
		"The number of MAC addresses allocated to this system."
::= { swSysSystem 29 }

swSysSystemChassisSerialNumber OBJECT-TYPE
	SYNTAX  DisplayString (SIZE(12))
	ACCESS  read-only
	STATUS  mandatory
	DESCRIPTION
		"The serial number of the chassis."
::= { swSysSystem 30 }

swSysSystemFPMemorySize OBJECT-TYPE
	SYNTAX	INTEGER
	ACCESS	read-only
	STATUS	mandatory
	DESCRIPTION
		"The amount of frame processor memory (RAM), in bytes."
::= { swSysSystem 31}

swSysSystemBufferSize OBJECT-TYPE
	SYNTAX	INTEGER
	ACCESS	read-only
	STATUS	mandatory
	DESCRIPTION
		"The amount of buffer memory, in bytes."
::= { swSysSystem 32}


-- The Switching Systems MIB slot group.  Implementation of this
-- group is mandatory for agents which manage system resources
-- for systems with independently manageable slots.

swSysSlotCount OBJECT-TYPE
	SYNTAX  INTEGER
	ACCESS  read-only
	STATUS  mandatory
	DESCRIPTION
	"The count of slots in the chassis."
::= { swSysSlot 1 }

-- The Switching Systems MIB slot table.

swSysSlotTable OBJECT-TYPE
	SYNTAX  SEQUENCE OF SwSysSlotEntry
	ACCESS  not-accessible
	STATUS  mandatory
	DESCRIPTION
			"A list of slot entries.  A single entry exists in this
			list for each slot in the chassis."
::= { swSysSlot 2 }

swSysSlotEntry OBJECT-TYPE
	SYNTAX  SwSysSlotEntry
	ACCESS  not-accessible
	STATUS  mandatory
	DESCRIPTION
			"A slot entry contains information about a particular
			slot."
	INDEX   { swSysSlotIndex }
::= { swSysSlotTable 1 }

SwSysSlotEntry ::=
	SEQUENCE {
		swSysSlotIndex
			INTEGER,
		swSysSlotBoardType
			INTEGER,
		swSysSlotBoardRevision
			OCTET STRING,
		swSysSlotBoardStatus
			INTEGER,
		swSysSlotBoardName
			DisplayString,
		swSysSlotBoardNameAbbrev
			DisplayString,
		swSysSlotEthernetPortCount
			INTEGER,
		swSysSlotFddiMacCount
			INTEGER,
		swSysSlotFddiPortCount
			INTEGER,
		swSysSlotOvertemperature
			INTEGER,
		swSysSlotTokenRingPortCount
			INTEGER,
		swSysSlotBoardRevStr
			DisplayString,
                swSysSlotConverterBad
                    INTEGER
    }

swSysSlotIndex OBJECT-TYPE
	SYNTAX  INTEGER
	ACCESS  read-only
	STATUS  mandatory
	DESCRIPTION
			"The index of the slot identified by this entry."
::= { swSysSlotEntry 1 }

swSysSlotBoardType OBJECT-TYPE
	SYNTAX  INTEGER {
				other(1),
				emptyLocation(2),
				esmBoard(7),
				fcmBoard(8),
				lmmBoard(9),
				efsmBoard(10),
				trsmBoard(11),
				tmmBoard(12),
				fsmBoard(13),
				fesmBoard(14)
			}
	ACCESS  read-only
	STATUS  mandatory
	DESCRIPTION
			"The type of board residing in the slot identified by
			this entry."
::= { swSysSlotEntry 2 }

swSysSlotBoardRevision OBJECT-TYPE
	SYNTAX  OCTET STRING (SIZE (0..1))
	ACCESS  read-only
	STATUS  mandatory
	DESCRIPTION
			"The revision number of the board in the slot identified
			by this entry.  If the slot is empty, or the revision is
			unknown this object returns a zero length string."
::= { swSysSlotEntry 3 }

swSysSlotBoardStatus OBJECT-TYPE
	SYNTAX  INTEGER {
				notPresent(1),
				testing(2),
				offline(3),
				online(4)
			}
	ACCESS  read-only
	STATUS  mandatory
	DESCRIPTION
			"The status of the board in the slot identified by this
                    entry."
::= { swSysSlotEntry 4 }

swSysSlotBoardName OBJECT-TYPE
	SYNTAX  DisplayString (SIZE (0..255))
	ACCESS  read-only
	STATUS  mandatory
	DESCRIPTION
			"The text string describing the board in the slot
			identified by this entry."
::= { swSysSlotEntry 5 }

swSysSlotBoardNameAbbrev OBJECT-TYPE
	SYNTAX  DisplayString (SIZE (0..31))
	ACCESS  read-only
	STATUS  mandatory
	DESCRIPTION
			"The abbreviation used to describe the board in the slot
			identified by this entry."
::= { swSysSlotEntry 6 }

swSysSlotEthernetPortCount OBJECT-TYPE
	SYNTAX  INTEGER
	ACCESS  read-only
	STATUS  mandatory
	DESCRIPTION
			"The count of ethernet ports in the slot identified by
			this entry."
::= { swSysSlotEntry 7 }

swSysSlotFddiMacCount OBJECT-TYPE
	SYNTAX  INTEGER
	ACCESS  read-only
	STATUS  mandatory
	DESCRIPTION
			"The count of FDDI MACs in the slot identified by this
			entry."
::= { swSysSlotEntry 8 }

swSysSlotFddiPortCount OBJECT-TYPE
	SYNTAX  INTEGER
	ACCESS  read-only
	STATUS  mandatory
	DESCRIPTION
			"The count of FDDI ports in the slot identified by this
			entry."
::= { swSysSlotEntry 9 }

swSysSlotOvertemperature OBJECT-TYPE
	SYNTAX  INTEGER {
		true(1),
		false(2),
		notSupported(3)
    }
	ACCESS  read-only
	STATUS  mandatory
	DESCRIPTION
			"This object indicates the current overtemperature status
			for the slot.  If the slot does not support overtemperature
			detection, this object returns notSupported."
::= { swSysSlotEntry 10 }

swSysSlotTokenRingPortCount OBJECT-TYPE
	SYNTAX  INTEGER
	ACCESS  read-only
	STATUS  mandatory
	DESCRIPTION
			"The count of TokenRing ports in the slot identified by this
			entry."
::= { swSysSlotEntry 11 }

swSysSlotBoardRevStr  OBJECT-TYPE
	SYNTAX  DisplayString (SIZE (0..5))
	ACCESS  read-only
	STATUS  mandatory
	DESCRIPTION
		"This revision number of the board in the slot identified
		by this entry.  If the slot is empty, or the revision is
		unknown this object returns a zero length string.  The
		format of the string is XX.YY, where the XX is the major
		revision (artwork), the YY is the minor revision (rework)"
::= { swSysSlotEntry 12 }

swSysSlotConverterBad OBJECT-TYPE
	SYNTAX  INTEGER {
		true(1),
		false(2),
		notSupported(3)
	}
	ACCESS  read-only
	STATUS  mandatory
	DESCRIPTION
			"This object indicates the current status +12V->+5V
			converter for the slot.  If the slot does not support
			+12V->+5V converter detection, this object returns
			notSupported."
::= { swSysSlotEntry 13 }


-- The LANplex Systems MIB control panel group.  Implementation of
-- this group is mandatory for agents which manage system resources
-- for systems which are equipped with manageable control panels.

swSysControlPanelHardwareRevision OBJECT-TYPE
	SYNTAX  OCTET STRING (SIZE (1))
	ACCESS  read-only
	STATUS  mandatory
	DESCRIPTION
			"An 8-bit value specifying the revision level of the
			control panel hardware."
::= { swSysControlPanel 1 }

swSysControlPanelSoftwareRevision OBJECT-TYPE
	SYNTAX  OCTET STRING (SIZE (1))
	ACCESS  read-only
	STATUS  mandatory
	DESCRIPTION
			"An 8-bit value specifying the revision level of the
			control panel software."
::= { swSysControlPanel 2 }

swSysControlPanelLines OBJECT-TYPE
	SYNTAX  INTEGER
	ACCESS  read-only
	STATUS  mandatory
	DESCRIPTION
			"The number of lines in the control panel display."
::= { swSysControlPanel 3 }

swSysControlPanelColumns OBJECT-TYPE
	SYNTAX  INTEGER
	ACCESS  read-only
	STATUS  mandatory
	DESCRIPTION
			"The number of columns in the control panel display."
::= { swSysControlPanel 4 }

swSysControlPanelText OBJECT-TYPE
	SYNTAX  OCTET STRING (SIZE (0..127))
	ACCESS  read-only
	STATUS  mandatory
	DESCRIPTION
			"The currently displayed text in the control panel
			display."
::= { swSysControlPanel 5 }

swSysControlPanelAccess OBJECT-TYPE
	SYNTAX  INTEGER {
		enabled  (1),   --  Panel Access is permitted (unlocked)
        disabled (2)    --  Panel Access is prohibited (locked)
    }
	ACCESS  read-write
	STATUS  mandatory
	DESCRIPTION
		"This object determines whether modifications to system
		 configuration are allowed via the Control Panel"
::= { swSysControlPanel 6 }


-- The Switching Systems MIB power supply group.  Implementation of this
-- group is mandatory for agents which manage system resources for
-- systems which are equipped with managable power supplies.

swSysPowerSupplyCount OBJECT-TYPE
	SYNTAX	INTEGER
	ACCESS	read-only
	STATUS	mandatory
	DESCRIPTION
	"The count of power supplies in the system."
::= { swSysPowerSupply 1 }

-- The Switching Systems MIB power supply status table.

swSysPowerSupplyStatusTable OBJECT-TYPE
	SYNTAX	SEQUENCE OF SwSysPowerSupplyStatusEntry
	ACCESS	not-accessible
	STATUS	mandatory
	DESCRIPTION
			"A list of power supply status entries."
::= { swSysPowerSupply 2 }

swSysPowerSupplyStatusEntry OBJECT-TYPE
	SYNTAX	SwSysPowerSupplyStatusEntry
	ACCESS	not-accessible
	STATUS	mandatory
	DESCRIPTION
			"A power supply status entry contains information about a 
			particular power supply."
			INDEX	{ swSysPowerSupplyStatusIndex }
::= { swSysPowerSupplyStatusTable 1 }

SwSysPowerSupplyStatusEntry ::=
	SEQUENCE {
		swSysPowerSupplyStatusIndex
			INTEGER,
		swSysPowerSupplyStatus
			INTEGER,
		swSysPowerSupplyStatusSupported
			INTEGER
	}

swSysPowerSupplyStatusIndex OBJECT-TYPE
	SYNTAX	INTEGER
	ACCESS	read-only
	STATUS	mandatory
	DESCRIPTION
			"The unique index of the power supply identified by this
			entry."
::= { swSysPowerSupplyStatusEntry 1 }

swSysPowerSupplyStatus OBJECT-TYPE
	SYNTAX	INTEGER
	ACCESS	read-only
	STATUS	mandatory
	DESCRIPTION
			"This object represents the power supply status.  The
			value is a sum. It initially takes on the value 0, then
			for each type which is active, 2 raised to a power is
			added to the sum.  The powers are according to the
			following table.
			For the 6000 Backbone Aggregator an over temp for power
			supply 1 and power supply 2 will be reported as a power
			supply 1 Over Temperature Failure, and a fan failure will
			be reported as a power supply 2 Over Temperature Failure.

				Failure Type		      Power
				AC Failure			0
				Plus 5 Failure			1
				Plus 12 Failure			2
				Over Temperature Failure  	3
				Power Supply Inserted		4
						Power Supply Extracted		5"
::= { swSysPowerSupplyStatusEntry 2 }

swSysPowerSupplyStatusSupported OBJECT-TYPE
	SYNTAX	INTEGER
	ACCESS	read-only
	STATUS	mandatory
	DESCRIPTION
			"This object represents the various power supply status 
			types which are supported.  The value is a sum.  It
			initially takes on the value 0, then for each type
			which is supported, 2 raised to a power is added to the
			sum.  The powers are according to the following table:

				Failure Type		      Power
				AC Failure			0
				Plus 5 Failure			1
				Plus 12 Failure			2
				Over Temperature Failure	3
				Power Supply Inserted		4
				Power Supply Extracted		5

			This object used in conjunction with the
			swSysPowerSupplyStatus object for a given power supply
			provide a complete picture of the status of the power
			supply."
	::= { swSysPowerSupplyStatusEntry 3 }


-- The LANplex Systems MIB SNMP group.  Implementation of this group
-- is mandatory for agents in systems which contain multiple
-- independently manageable devices and which support a multiple agent
-- mode.  Note that this group is only available in the multiple agent
-- mode for those systems that support it.

swSysSnmpAgentId OBJECT-TYPE
	SYNTAX  INTEGER
	ACCESS  read-only
	STATUS  mandatory
	DESCRIPTION
			"The unique id for this SNMP agent within the system."
::= { swSysSnmp 1 }

swSysSnmpInternalAgentTrapMask OBJECT-TYPE
	SYNTAX  OCTET STRING (SIZE (8))
	ACCESS  read-write
	STATUS  mandatory
	DESCRIPTION
			"This value is a bit string that indicates which traps
			are enabled for transmit to other agents in the system.
			The octet string value is treated as a 64-bit integer
			value.  The value is a sum.  It initially takes on the
			value 0, then for each trap which is enabled, 2 raised
			to the value of (swSysAgentTrapDescriptionIndex - 1) for
			that trap is added to the sum."
::= { swSysSnmp 2 }

swSysSnmpInternalAgentTrapDestinationMask OBJECT-TYPE
	SYNTAX  INTEGER
	ACCESS  read-write
	STATUS  mandatory
	DESCRIPTION
			"A value which indicates to which other agents in the
			system traps should be sent.  The value is a sum.  It
			initially takes on the value 0, then for each agent which
			is to receive traps, 2 raised to the value of
			(swSysSnmpAgentId - 1) for that agent is added to the sum.
			Note that only traps which are enabled according to the
			value of the swSysSnmpInternalAgentTrapMask object will be
			forwarded, and that each trap which is forwarded will
			be transmitted to each agent identified by this mask."
::= { swSysSnmp 3 }

swSysSnmpProxyInternalRequests OBJECT-TYPE
	SYNTAX  INTEGER {
				true(1),
				false(2)
			}
	ACCESS  read-write
	STATUS  deprecated
	DESCRIPTION
			"This object determines if this agent will proxy requests
			to other agents in the system.  If the value of this
			object is true(1), this agent will proxy requests to other
			agents in the chassis."
::= { swSysSnmp 4 }

swSysSnmpInternalProxyRequestMaxAge OBJECT-TYPE
	SYNTAX  INTEGER (1..255)
	ACCESS  read-write
	STATUS  mandatory
	DESCRIPTION
			"The maximum time, in seconds, an internal proxy request
			will remain queued waiting for a response before being
			discarded.  Note that when the value of
			swSysSnmpProxyInternalRequests is false(2), the value of
			this object is ignored."
::= { swSysSnmp 5 }

swSysSnmpProxyInternalTraps OBJECT-TYPE
	SYNTAX  INTEGER {
				true(1),
				false(2)
			}
	ACCESS  read-write
	STATUS  deprecated
	DESCRIPTION
			"This object determines if this agent will generate proxy
			traps for those traps received from other agents in the
			system.  If the value of this object is true(1), this
			agent will generate proxy traps for those received from
			other agents in the chassis.  Note that agents will not
			proxy traps to other agents within the system to prevent
			looping of traps."
::= { swSysSnmp 6 }


-- The LANplex Systems MIB SNMP internal proxy table.

swSysSnmpInternalProxyTable OBJECT-TYPE
	SYNTAX  SEQUENCE OF SwSysSnmpInternalProxyEntry
	ACCESS  not-accessible
	STATUS  mandatory
	DESCRIPTION
			"A list of SNMP internal agent proxy entries.  An entry in
			this table exists for each agent in the system that can be
			reached by this agent via the internal proxy mechanism."
::= { swSysSnmp 7 }

swSysSnmpInternalProxyEntry OBJECT-TYPE
	SYNTAX  SwSysSnmpInternalProxyEntry
	ACCESS  not-accessible
	STATUS  mandatory
	DESCRIPTION
			"An entry identifies the communities available for
			communicating with another agent in the system via the
			internal proxy mechanism."
	INDEX   { swSysSnmpInternalProxyAgentId,
			swSysSnmpInternalProxyAccessClass }
::= { swSysSnmpInternalProxyTable 1 }

SwSysSnmpInternalProxyEntry ::=
	SEQUENCE {
		swSysSnmpInternalProxyAgentId
			INTEGER,
		swSysSnmpInternalProxyAccessClass
			INTEGER,
		swSysSnmpInternalProxyCommunity
			OCTET STRING
	}

swSysSnmpInternalProxyAgentId OBJECT-TYPE
	SYNTAX  INTEGER
	ACCESS  read-only
	STATUS  mandatory
	DESCRIPTION
			"The id of the agent identified by this entry."
::= { swSysSnmpInternalProxyEntry 1 }

swSysSnmpInternalProxyAccessClass OBJECT-TYPE
	SYNTAX  INTEGER {
				readOnly(1),
				readWrite(2)
			}
	ACCESS  read-only
	STATUS  mandatory
	DESCRIPTION
			"The access to MIB objects supported by the agent
			identified by this entry provided by this agent, when
			using the community string identified by the corresponding
			value of swSysSnmpInternalProxyCommunity."
::= { swSysSnmpInternalProxyEntry 2 }

swSysSnmpInternalProxyCommunity OBJECT-TYPE
	SYNTAX  OCTET STRING
	ACCESS  read-only
	STATUS  mandatory
	DESCRIPTION
			"A community which allows access to MIB objects supported
			by the agent identified by this entry."
::= { swSysSnmpInternalProxyEntry 3 }



-- The Switching Systems MIB agent group.  Implementation of this group
-- is mandatory for all agents.

swSysAgentRequestMaxAge OBJECT-TYPE
	SYNTAX	INTEGER (1..255)
	ACCESS	read-write
	STATUS	mandatory
	DESCRIPTION
			"The maximum time, in seconds, a local SNMP request will
			remain queued waiting for a response before being
			discarded."
::= { swSysAgent 1 }

swSysAgentProxyRemoteSmtRequests OBJECT-TYPE
	SYNTAX	INTEGER {
				true(1),
				false(2)
			}
	ACCESS	read-write
	STATUS	deprecated
	DESCRIPTION
			"This object determines if this agent will proxy SMT
			requests to other FDDI stations.  If the value of this
			object is true(1), this agent will proxy SMT requests to
			other stations.  Note that only a subset of the above
			values may be valid for some systems."
::= { swSysAgent 2 }

swSysAgentRemoteSmtProxyRequestMaxAge OBJECT-TYPE
	SYNTAX	INTEGER (1..255)
	ACCESS	read-write
	STATUS	mandatory
	DESCRIPTION
			"The maximum time, in seconds, an SMT proxy request will
			remain queued waiting for a response before being
			discarded.  Note that when the value of
			swSysAgentProxyRemoteSmtRequests is false(2), the value of
			this object is ignored."
::= { swSysAgent 3 }

swSysAgentProxyRemoteSmtEvents OBJECT-TYPE
	SYNTAX	INTEGER {
				true(1),
				false(2)
			}
	ACCESS	read-write
	STATUS	mandatory
	DESCRIPTION
			"This object determines if this agent will generate traps
			for SMT events occuring at other stations.  If the value
			of this object is true(1), this agent will generate traps
			for all SMT events, those which occur locally, and those
			which occur at other stations.  If the value of this
			object is false(2), this agent will only generate traps
			for events which occur locally.  Note that only a subset
			of the above values may be valid for some systems."
::= { swSysAgent 4 }

-- The Switching Systems MIB agent trap description table.

swSysAgentTrapDescriptionTable OBJECT-TYPE
	SYNTAX	SEQUENCE OF SwSysAgentTrapDescriptionTableEntry
	ACCESS	not-accessible
	STATUS	mandatory
	DESCRIPTION
			"This table contains a listing of trap descriptions for
			each trap supported by this agent.  This 
			provides a relationship between a trap index, and the trap
			enterprise oid and trap number for a given trap.  In all
			cases except for the MIB-2 generic traps, the enterprise
			under which a trap is defined is the same as that
			appearing in the ENTERPRISE portion of the trap."
::= { swSysAgent 5 }

swSysAgentTrapDescriptionTableEntry OBJECT-TYPE
	SYNTAX	SwSysAgentTrapDescriptionTableEntry
	ACCESS	not-accessible
	STATUS	mandatory
	DESCRIPTION
			"Information relating a trap index to a specific trap
			enterprise oid and trap number."
	INDEX	{ swSysAgentTrapDescriptionIndex }
::= { swSysAgentTrapDescriptionTable 1 }

SwSysAgentTrapDescriptionTableEntry ::=
	SEQUENCE {
		swSysAgentTrapDescriptionIndex
			INTEGER,
		swSysAgentTrapEnterprise
			OBJECT IDENTIFIER,
		swSysAgentTrapNumber
			INTEGER
	}

swSysAgentTrapDescriptionIndex OBJECT-TYPE
	SYNTAX	INTEGER
	ACCESS	read-only
	STATUS	mandatory
	DESCRIPTION
			"A unique index corresponding to the trap described by
			this entry.  This value of this object corresponding to
			a particular trap will remain constant accross system
			resets."
::= { swSysAgentTrapDescriptionTableEntry 1 }

swSysAgentTrapEnterprise OBJECT-TYPE
	SYNTAX	OBJECT IDENTIFIER
	ACCESS	read-only
	STATUS	mandatory
	DESCRIPTION
			"The enterpise under which the trap identified by this
			entry is defined."
::= { swSysAgentTrapDescriptionTableEntry 2 }

swSysAgentTrapNumber OBJECT-TYPE
	SYNTAX	INTEGER
	ACCESS	read-only
	STATUS	mandatory
	DESCRIPTION
			"The number of the trap identified by this entry, within
			the enterprise where it is defined."
::= { swSysAgentTrapDescriptionTableEntry 3 }

-- The Switching Systems MIB agent trap destination table.

swSysAgentTrapDestinationTable OBJECT-TYPE
	SYNTAX	SEQUENCE OF SwSysAgentTrapDestinationTableEntry
	ACCESS	not-accessible
	STATUS	mandatory
	DESCRIPTION
			"This table contains information specifying which traps
			will be transmitted to a given destination address.  The
			table is indexed by the destination address type and
			destination address.  Each entry in the table with a
			status of valid identifies a set of traps which, when
			generated, will be transmitted to the corresponding
			destination address listed in that entry."
::= { swSysAgent 6 }

swSysAgentTrapDestinationTableEntry OBJECT-TYPE
	SYNTAX	SwSysAgentTrapDestinationTableEntry
	ACCESS	not-accessible
	STATUS	mandatory
	DESCRIPTION
			"Information relating a set of traps and a destination
			address to which each trap in ths set will be transmitted
			when it is generated.  To create a new entry, set a
			non-existent instance of swSysAgentTrapDestinationTrapMask
			to a valid value.  To remove an entry, set the instance of
			swSysAgentTrapDestinationEntryStatus for the entry to
			invalid(2)."
	INDEX	{ swSysAgentTrapDestinationAddressType,
			swSysAgentTrapDestinationAddress }
::= { swSysAgentTrapDestinationTable 1 }

SwSysAgentTrapDestinationTableEntry ::=
	SEQUENCE {
		swSysAgentTrapDestinationAddressType
			INTEGER,
		swSysAgentTrapDestinationAddress
			OCTET STRING,
		swSysAgentTrapDestinationTrapMask
			OCTET STRING,
		swSysAgentTrapDestinationEntryStatus
			INTEGER
	}

swSysAgentTrapDestinationAddressType OBJECT-TYPE
	SYNTAX	INTEGER {
				ip(1)
			}
	ACCESS	read-only
	STATUS	mandatory
	DESCRIPTION
			"The type of address identified by this entry."
::= { swSysAgentTrapDestinationTableEntry 1 }

swSysAgentTrapDestinationAddress OBJECT-TYPE
	SYNTAX	OCTET STRING
	ACCESS	read-only
	STATUS	mandatory
	DESCRIPTION
			"The address, of the type specified by the corresponding
			value of swSysAgentTrapDestinationAddressType, to which the
			set of traps identified by this entry are to be
			transmitted."
::= { swSysAgentTrapDestinationTableEntry 2 }

swSysAgentTrapDestinationTrapMask OBJECT-TYPE
	SYNTAX	OCTET STRING (SIZE (8))
	ACCESS	read-write
	STATUS	mandatory
	DESCRIPTION
			"This value is a bit string that indicates which traps
			are enabled for the address identified by this entry.
			The octet string value is treated as a 64-bit value.  The
			value is a sum.  It initially takes on the value 0, then
			for each trap which is enabled, 2 raised to the value of
			(swSysAgentTrapDescriptionIndex - 1) for that trap is
			added to the sum.  A new entry in the table is created by
			setting the value of this object for a new destination
			address type and destination address.  Note that an octet
			string of all zeros is not a valid value for this object."
::= { swSysAgentTrapDestinationTableEntry 3 }

swSysAgentTrapDestinationEntryStatus OBJECT-TYPE
	SYNTAX	INTEGER {
				valid(1),
				invalid(2)
			}
	ACCESS	read-write
	STATUS	mandatory
	DESCRIPTION
			"The status of the trap destination table entry.  Setting
			this object to invalid(1) has the effect of removing the
			corresponding entry from the table."
::= { swSysAgentTrapDestinationTableEntry 4 }

swSysAgentReadCommunity OBJECT-TYPE
	SYNTAX  DisplayString (SIZE (0..48)) 
	ACCESS  read-write
	STATUS  mandatory
	DESCRIPTION
		"This object is the read community string when access is
		 made via SNMP, see RFC1157."	
::= { swSysAgent 7 }

swSysAgentReadWriteCommunity OBJECT-TYPE
	SYNTAX  DisplayString (SIZE (0..48)) 
	ACCESS  read-write
	STATUS  mandatory
	DESCRIPTION
		"This object is the read-write community string when access is
		made via SNMP, see RFC1157.  The read-write community string
	    is required to access this object."
::= { swSysAgent 8 }


-- The Switching Systems MIB interface group.  Implementation of this
-- group is mandatory for all agents.

-- The Switching Systems MIB interface location table.

swSysInterfaceLocationTable OBJECT-TYPE
	SYNTAX	SEQUENCE OF SwSysInterfaceLocationEntry
	ACCESS	not-accessible
	STATUS	mandatory
	DESCRIPTION
			"A list of interface location entries.  A single entry
			exists in this list for each interface managed by this
			agent."
::= { swSysInterface 1 }

swSysInterfaceLocationEntry OBJECT-TYPE
	SYNTAX	SwSysInterfaceLocationEntry
	ACCESS	not-accessible
	STATUS	mandatory
	DESCRIPTION
			"An interface location entry describes the location of
			a particular interface managed by this agent."
	INDEX	{ swSysInterfaceLocationIfIndex }
::= { swSysInterfaceLocationTable 1 }

SwSysInterfaceLocationEntry ::=
	SEQUENCE {
		swSysInterfaceLocationIfIndex
			INTEGER,
		swSysInterfaceLocationInterfaceType
			INTEGER,
		swSysInterfaceLocationType
			INTEGER,
		swSysInterfaceLocationTypeIndex
			INTEGER,
		swSysInterfaceLocationLocalIndex
			INTEGER,
		swSysInterfaceLocationSystemModuleIndex
			INTEGER
	}

swSysInterfaceLocationIfIndex OBJECT-TYPE
	SYNTAX	INTEGER
	ACCESS	read-only
	STATUS	mandatory
	DESCRIPTION
			"The value of the MIB-II ifIndex corresponding to the
			interface identified by this entry."
::= { swSysInterfaceLocationEntry 1 }


swSysInterfaceLocationInterfaceType OBJECT-TYPE
	SYNTAX	INTEGER {
				other(1),
				ethernetPort(2),
				fddiMac(3),
				tokenringPort(4),
				atmPort(5)
			}
	ACCESS	read-only
	STATUS	mandatory
	DESCRIPTION
			"The type of the physical implementation of the interface
			identified by this entry."
::= { swSysInterfaceLocationEntry 2 }

swSysInterfaceLocationType OBJECT-TYPE
	SYNTAX	INTEGER {
				other(1),
				modularSlot(2),
				chassis(3),
				modularCard(4)
			}
	ACCESS	read-only
	STATUS	mandatory
	DESCRIPTION
			"The type of location where the interface identified
			by this entry is physically located."
::= { swSysInterfaceLocationEntry 3 }

swSysInterfaceLocationTypeIndex OBJECT-TYPE
	SYNTAX	INTEGER
	ACCESS	read-only
	STATUS	mandatory
	DESCRIPTION
			"The index of the location identified by the corresponding
			instance of swSysInterfaceLocationType where the interface
			identified by this entry is physically located."
::= { swSysInterfaceLocationEntry 4 }

swSysInterfaceLocationLocalIndex OBJECT-TYPE
	SYNTAX	INTEGER
	ACCESS	read-only
	STATUS	mandatory
	DESCRIPTION
			"The local index of the interface identified by
			this entry relative to its type specified by the
			corresponding value of swSysInterfaceLocationInterfaceType,
			and the location specified by the corresponding values
			of swSysInterfaceLocationType and swSysInterfaceLocationTypeIndex."
::= { swSysInterfaceLocationEntry 5 }

swSysInterfaceLocationSystemModuleIndex OBJECT-TYPE
    SYNTAX  INTEGER
    ACCESS  read-only
    STATUS  mandatory
    DESCRIPTION
        "The system module index of the interface idnetified by
         this entry.  Ths index can be used to acquire the module
         information from the s2SysModuleCardGroup and the
         swSysDiagnosticsGroup groups."
::= { swSysInterfaceLocationEntry 6 }
-- The Switching Systems MIB ethernet port group.  Implementation of
-- this group is mandatory for agents which manage ethernet port
-- resources.

swSysEthernetPortCount OBJECT-TYPE
	SYNTAX	INTEGER
	ACCESS	read-only
	STATUS	mandatory
	DESCRIPTION
			"The count of ethernet ports managed by this agent."
::= { swSysEthernetPort 1 }

-- The Switching Systems MIB ethernet port table.

swSysEthernetPortTable OBJECT-TYPE
	SYNTAX	SEQUENCE OF SwSysEthernetPortEntry
	ACCESS	not-accessible
	STATUS	mandatory
	DESCRIPTION
			"A list of ethernet port entries.  A single entry exists
			in this list for each ethernet port managed by this agent."
::= { swSysEthernetPort 2 }

swSysEthernetPortEntry OBJECT-TYPE
	SYNTAX	SwSysEthernetPortEntry
	ACCESS	not-accessible
	STATUS	mandatory
	DESCRIPTION
			"An ethernet port entry contains information about a
			particular ethernet port managed by this agent."
	INDEX	{ swSysEthernetPortIndex }
::= { swSysEthernetPortTable 1 }

SwSysEthernetPortEntry ::=
	SEQUENCE {
		swSysEthernetPortIndex
			INTEGER,
		swSysEthernetPortIfIndex
			INTEGER,
		swSysEthernetPortLabel
			DisplayString,
		swSysEthernetPortLinkStatus
			INTEGER,
		swSysEthernetPortType
			INTEGER
}

swSysEthernetPortIndex OBJECT-TYPE
	SYNTAX	INTEGER
	ACCESS	read-only
	STATUS	mandatory
	DESCRIPTION
			"The index of the ethernet port identified by this entry,
			relative to this agent."
::= { swSysEthernetPortEntry 1 }

swSysEthernetPortIfIndex OBJECT-TYPE
	SYNTAX	INTEGER
	ACCESS	read-only
	STATUS	mandatory
	DESCRIPTION
			"The value of the MIB-II ifIndex corresponding to the
			ethernet port identified by this entry."
::= { swSysEthernetPortEntry 2 }

swSysEthernetPortLabel OBJECT-TYPE
	SYNTAX	DisplayString (SIZE (0..31))
	ACCESS	read-write
	STATUS	mandatory
	DESCRIPTION
			"An ASCII text string describing the ethernet port
			identified by this entry."
::= { swSysEthernetPortEntry 3 }

swSysEthernetPortLinkStatus OBJECT-TYPE
	SYNTAX	INTEGER {
				active(1),
				inActive(2)
			}
	ACCESS	read-only
	STATUS	mandatory
	DESCRIPTION
			"The current value of the link status for the ethernet port
			identified by this entry."
::= { swSysEthernetPortEntry 4 }

swSysEthernetPortType OBJECT-TYPE
	SYNTAX	INTEGER {
				rj2110BaseT(1),
				rj4510BaseT(2),
				st10BaseFL(3),
				aui(4),
				bnc10Base2(5),
				other(6),
				rj45100BaseT(7),
				sc100BaseFx(8),
				untermBnc10Base2(9),
				sc1000BaseLxSm(10),
				sc1000BaseLxMm(11),
				sc1000BaseLxSmMm(12),
				sc1000BaseLx10km(13),
				sc1000BaseSx(14),
				hssdc1000BaseCx(15),
				db91000BaseCx(16),
				gbicNotPresent(17),
				gbic1000BaseCxDb9(18),
				gbic1000BaseCxHssdc(19),
				gbic1000BaseLx10Km(20),
				gbic1000BaseLx(21),
				gbic1000BaseSx(22),
				rj451000BaseT(23)
			}
	ACCESS	read-only
	STATUS	mandatory
	DESCRIPTION
			"Specific port type description for the ethernet port
			identified by this entry."
::= { swSysEthernetPortEntry 5 }

-- The Switching Systems MIB ethernet port rate table.

swSysEthernetPortRateTable OBJECT-TYPE
	SYNTAX	SEQUENCE OF SwSysEthernetPortRateEntry
	ACCESS	not-accessible
	STATUS	mandatory
	DESCRIPTION
			"A list of ethernet port rate entries.  A single entry
			exists in this list for each ethernet port, managed by
			this agent, which supports rate information."
::= { swSysEthernetPort 3 }

swSysEthernetPortRateEntry OBJECT-TYPE
	SYNTAX	SwSysEthernetPortRateEntry
	ACCESS	not-accessible
	STATUS	mandatory
	DESCRIPTION
			"An ethernet port rate entry contains rate statistics for a
			particular ethernet port managed by this agent.  Rate
			statistics are calculated based on a one second sampling
			interval."
	INDEX	{ swSysEthernetPortRateIndex }
::= { swSysEthernetPortRateTable 1 }

SwSysEthernetPortRateEntry ::=
	SEQUENCE {
		swSysEthernetPortRateIndex
			INTEGER,
		swSysEthernetPortRateByteReceiveRate
			INTEGER,
		swSysEthernetPortRatePeakByteReceiveRate
			INTEGER,
		swSysEthernetPortRateFrameReceiveRate
			INTEGER,
		swSysEthernetPortRatePeakFrameReceiveRate
			INTEGER,
		swSysEthernetPortRateByteTransmitRate
			INTEGER,
		swSysEthernetPortRatePeakByteTransmitRate
			INTEGER,
		swSysEthernetPortRateFrameTransmitRate
			INTEGER,
		swSysEthernetPortRatePeakFrameTransmitRate
			INTEGER
}

swSysEthernetPortRateIndex OBJECT-TYPE
	SYNTAX	INTEGER
	ACCESS	read-only
	STATUS	mandatory
	DESCRIPTION
			"The index of the ethernet port identified by this entry,
			relative to this agent."
::= { swSysEthernetPortRateEntry 1 }

swSysEthernetPortRateByteReceiveRate OBJECT-TYPE
	SYNTAX	INTEGER
	ACCESS	read-only
	STATUS	mandatory
	DESCRIPTION
			"The average number of bytes received per second by the
			ethernet port identified by this entry during the most
			recent sampling period."
::= { swSysEthernetPortRateEntry 2 }

swSysEthernetPortRatePeakByteReceiveRate OBJECT-TYPE
	SYNTAX	INTEGER
	ACCESS	read-only
	STATUS	mandatory
	DESCRIPTION
			"The peak value of swSysEthernetPortRateByteReceiveRate
			since the system was last initialized for the ethernet
			port identified by this entry."
::= { swSysEthernetPortRateEntry 3 }

swSysEthernetPortRateFrameReceiveRate OBJECT-TYPE
	SYNTAX	INTEGER
	ACCESS	read-only
	STATUS	mandatory
	DESCRIPTION
			"The average number of frames received per second by the
			ethernet port identified by this entry during the most
			recent sampling period."
::= { swSysEthernetPortRateEntry 4 }

swSysEthernetPortRatePeakFrameReceiveRate OBJECT-TYPE
	SYNTAX	INTEGER
	ACCESS	read-only
	STATUS	mandatory
	DESCRIPTION
			"The peak value of swSysEthernetPortRateFrameReceiveRate
			since the system was last initialized for the ethernet
			port identified by this entry."
::= { swSysEthernetPortRateEntry 5 }

swSysEthernetPortRateByteTransmitRate OBJECT-TYPE
	SYNTAX	INTEGER
	ACCESS	read-only
	STATUS	mandatory
	DESCRIPTION
			"The average number of bytes transmitted per second by the
			ethernet port identified by this entry during the most
			recent sampling period."
::= { swSysEthernetPortRateEntry 6 }

swSysEthernetPortRatePeakByteTransmitRate OBJECT-TYPE
	SYNTAX	INTEGER
	ACCESS	read-only
	STATUS	mandatory
	DESCRIPTION
			"The peak value of swSysEthernetPortRateByteTransmitRate
			since the system was last initialized for the ethernet
			port identified by this entry."
::= { swSysEthernetPortRateEntry 7 }

swSysEthernetPortRateFrameTransmitRate OBJECT-TYPE
	SYNTAX	INTEGER
	ACCESS	read-only
	STATUS	mandatory
	DESCRIPTION
			"The average number of frames transmitted per second by the
			ethernet port identified by this entry during the most
			recent sampling period."
::= { swSysEthernetPortRateEntry 8 }

swSysEthernetPortRatePeakFrameTransmitRate OBJECT-TYPE
	SYNTAX	INTEGER
	ACCESS	read-only
	STATUS	mandatory
	DESCRIPTION
			"The peak value of swSysEthernetPortRateFrameTransmitRate
			since the system was last initialized for the ethernet
			port identified by this entry."
::= { swSysEthernetPortRateEntry 9 }


-- The Switching Systems MIB SMT group.  Implementation of this group is
-- mandatory for agents which manage SMT resources.

swSysSmtCount OBJECT-TYPE
	SYNTAX	INTEGER
	ACCESS	read-only
	STATUS	mandatory
	DESCRIPTION
			"The count of SMTs managed by this agent."
::= { swSysSmt 1 }

-- The Switching Systems MIB SMT table.
-- This table is currently unused and is reserved for future use.
-- { swSysSmt 2 }

-- The Switching Systems MIB SMT FDDI MAC table.
-- This table is currently unused and is reserved for future use.
-- { swSysSmt 3 }

-- The Switching Systems MIB SMT FDDI MAC beacon table.

swSysSmtFddiMacBeaconTable OBJECT-TYPE
	SYNTAX	SEQUENCE OF SwSysSmtFddiMacBeaconEntry
	ACCESS	not-accessible
	STATUS	mandatory
	DESCRIPTION
			"A list of FDDI MAC beacon entries.  A single entry exists
			in this list for each FDDI MAC, managed by this agent,
			which supports MAC beacon history."
::= { swSysSmt 4 }

swSysSmtFddiMacBeaconEntry OBJECT-TYPE
	SYNTAX	SwSysSmtFddiMacBeaconEntry
	ACCESS	not-accessible
	STATUS	mandatory
	DESCRIPTION
			"An FDDI MAC beacon entry contains information about a
			particular FDDI MAC's beacon history."
	INDEX	{ swSysSmtFddiMacBeaconSmtIndex,
			swSysSmtFddiMacBeaconIndex }
::= { swSysSmtFddiMacBeaconTable 1 }

SwSysSmtFddiMacBeaconEntry ::=
	SEQUENCE {
		swSysSmtFddiMacBeaconSmtIndex
			INTEGER,
		swSysSmtFddiMacBeaconIndex
			INTEGER,
		swSysSmtFddiMacBeaconHistory
			OCTET STRING
}

swSysSmtFddiMacBeaconSmtIndex OBJECT-TYPE
	SYNTAX	INTEGER
	ACCESS	read-only
	STATUS	mandatory
	DESCRIPTION
			"The index of the SMT instance identified by this entry,
			relative to this agent."
	::= { swSysSmtFddiMacBeaconEntry 1 }

swSysSmtFddiMacBeaconIndex OBJECT-TYPE
	SYNTAX	INTEGER
	ACCESS	read-only
	STATUS	mandatory
	DESCRIPTION
			"The index of the FDDI MAC identified by this entry,
			within the SMT identified by this entry."
::= { swSysSmtFddiMacBeaconEntry 2 }

swSysSmtFddiMacBeaconHistory OBJECT-TYPE
	SYNTAX	OCTET STRING (SIZE (0..256))
	ACCESS	read-only
	STATUS	mandatory
	DESCRIPTION
			"This object gives a history of the most recent beacon
			information received on the FDDI MAC identified by this
			entry.  It can contain up to a maximum of eight records.
			Each record is of the form:
				source MAC:				6 bytes
				beacon data length:		2 bytes.
				beacon data:			0-16 bytes."
::= { swSysSmtFddiMacBeaconEntry 3 }

-- The Switching Systems MIB SMT FDDI MAC rate table.

swSysSmtFddiMacRateTable OBJECT-TYPE
	SYNTAX	SEQUENCE OF SwSysSmtFddiMacRateEntry
	ACCESS	not-accessible
	STATUS	mandatory
	DESCRIPTION
			"A list of FDDI MAC rate entries.  A single entry exists
			in this list for each FDDI MAC, managed by this agent,
			which supports rate statistics."
::= { swSysSmt 5 }

swSysSmtFddiMacRateEntry OBJECT-TYPE
	SYNTAX	SwSysSmtFddiMacRateEntry
	ACCESS	not-accessible
	STATUS	mandatory
	DESCRIPTION
			"An FDDI MAC rate entry contains rate statistics for a
			particular FDDI MAC managed by this agent.  Rate statistics
			are calculated based on a one second sampling interval."
	INDEX	{ swSysSmtFddiMacRateSmtIndex,
			swSysSmtFddiMacRateIndex }
::= { swSysSmtFddiMacRateTable 1 }

SwSysSmtFddiMacRateEntry ::=
	SEQUENCE {
		swSysSmtFddiMacRateSmtIndex
			INTEGER,
		swSysSmtFddiMacRateIndex
			INTEGER,
		swSysSmtFddiMacRateByteReceiveRate
			INTEGER,
		swSysSmtFddiMacRatePeakByteReceiveRate
			INTEGER,
		swSysSmtFddiMacRateFrameReceiveRate
			INTEGER,
		swSysSmtFddiMacRatePeakFrameReceiveRate
			INTEGER,
		swSysSmtFddiMacRateByteTransmitRate
			INTEGER,
		swSysSmtFddiMacRatePeakByteTransmitRate
			INTEGER,
		swSysSmtFddiMacRateFrameTransmitRate
			INTEGER,
		swSysSmtFddiMacRatePeakFrameTransmitRate
			INTEGER
	}

swSysSmtFddiMacRateSmtIndex OBJECT-TYPE
	SYNTAX	INTEGER
	ACCESS	read-only
	STATUS	mandatory
	DESCRIPTION
			"The index of the SMT instance identified by this entry,
			relative to this agent."
::= { swSysSmtFddiMacRateEntry 1 }

swSysSmtFddiMacRateIndex OBJECT-TYPE
	SYNTAX	INTEGER
	ACCESS	read-only
	STATUS	mandatory
	DESCRIPTION
			"The index of the FDDI MAC identified by this entry, within
			the SMT identified by this entry."
::= { swSysSmtFddiMacRateEntry 2 }

swSysSmtFddiMacRateByteReceiveRate OBJECT-TYPE
	SYNTAX	INTEGER
	ACCESS	read-only
	STATUS	mandatory
	DESCRIPTION
			"The average number of bytes received per second by the
			FDDI MAC identified by this entry during the most recent
			sampling period."
::= { swSysSmtFddiMacRateEntry 3 }

swSysSmtFddiMacRatePeakByteReceiveRate OBJECT-TYPE
	SYNTAX	INTEGER
	ACCESS	read-only
	STATUS	mandatory
	DESCRIPTION
			"The peak value of swSysSmtFddiMacByteReceiveRate since the
			system was last initialized for the FDDI MAC identified by
			this entry."
::= { swSysSmtFddiMacRateEntry 4 }

swSysSmtFddiMacRateFrameReceiveRate OBJECT-TYPE
	SYNTAX	INTEGER
	ACCESS	read-only
	STATUS	mandatory
	DESCRIPTION
			"The average number of frames received per second by the
			FDDI MAC identified by this entry during the most recent
			sampling period."
::= { swSysSmtFddiMacRateEntry 5 }

swSysSmtFddiMacRatePeakFrameReceiveRate OBJECT-TYPE
	SYNTAX	INTEGER
	ACCESS	read-only
	STATUS	mandatory
	DESCRIPTION
			"The peak value of swSysSmtFddiMacRateFrameReceiveRate since
			the system was last initialized for the FDDI MAC identified
			by this entry."
::= { swSysSmtFddiMacRateEntry 6 }

swSysSmtFddiMacRateByteTransmitRate OBJECT-TYPE
	SYNTAX	INTEGER
	ACCESS	read-only
	STATUS	mandatory
	DESCRIPTION
			"The average number of bytes transmitted per second by the
			FDDI MAC identified by this entry during the most recent
			sampling period."
::= { swSysSmtFddiMacRateEntry 7 }

swSysSmtFddiMacRatePeakByteTransmitRate OBJECT-TYPE
	SYNTAX	INTEGER
	ACCESS	read-only
	STATUS	mandatory
	DESCRIPTION
			"The peak value of swSysSmtFddiMacByteTransmitRate since the
			system was last initialized for the FDDI MAC identified by
			this entry."
::= { swSysSmtFddiMacRateEntry 8 }

swSysSmtFddiMacRateFrameTransmitRate OBJECT-TYPE
	SYNTAX	INTEGER
	ACCESS	read-only
	STATUS	mandatory
	DESCRIPTION
			"The average number of frames transmitted per second by
			the FDDI MAC identified by this entry during the most
			recent sampling period."
	::= { swSysSmtFddiMacRateEntry 9 }

swSysSmtFddiMacRatePeakFrameTransmitRate OBJECT-TYPE
	SYNTAX	INTEGER
	ACCESS	read-only
	STATUS	mandatory
	DESCRIPTION
			"The peak value of swSysSmtFddiMacFrameTransmitRate since the
			system was last initialized for the FDDI MAC identified by
			this entry."
::= { swSysSmtFddiMacRateEntry 10 }

-- The Switching Systems MIB SMT FDDI port table.

swSysSmtFddiPortTable OBJECT-TYPE
	SYNTAX	SEQUENCE OF SwSysSmtFddiPortEntry
	ACCESS	not-accessible
	STATUS	mandatory
	DESCRIPTION
			"A list of FDDI port entries.  A single entry exists in
			this list for each FDDI port managed by this agent."
::= { swSysSmt 6 }

swSysSmtFddiPortEntry OBJECT-TYPE
	SYNTAX	SwSysSmtFddiPortEntry
	ACCESS	not-accessible
	STATUS	mandatory
	DESCRIPTION
			"An FDDI port entry contains information about a particular
			FDDI port managed by this agent."
	INDEX	{ swSysSmtFddiPortSmtIndex,
			swSysSmtFddiPortIndex }
::= { swSysSmtFddiPortTable 1 }

SwSysSmtFddiPortEntry ::=
	SEQUENCE {
		swSysSmtFddiPortSmtIndex
			INTEGER,
		swSysSmtFddiPortIndex
			INTEGER,
		swSysSmtFddiPortLocationType
			INTEGER,
		swSysSmtFddiPortLocationTypeIndex
			INTEGER,
		swSysSmtFddiPortLocationLocalIndex
			INTEGER,
		swSysSmtFddiPortLabel
			DisplayString
	}

swSysSmtFddiPortSmtIndex OBJECT-TYPE
	SYNTAX	INTEGER
	ACCESS	read-only
	STATUS	mandatory
	DESCRIPTION
			"The index of the SMT instance identified by this entry,
			relative to this agent."
::= { swSysSmtFddiPortEntry 1 }

swSysSmtFddiPortIndex OBJECT-TYPE
	SYNTAX	INTEGER
	ACCESS	read-only
	STATUS	mandatory
	DESCRIPTION
			"The index of the FDDI port identified by this entry,
			within the SMT identified by this entry."
::= { swSysSmtFddiPortEntry 2 }

swSysSmtFddiPortLocationType OBJECT-TYPE
	SYNTAX	INTEGER {
				other(1),
				modularSlot(2),
				chassis(3),
				modularCard(4)
			}
	ACCESS	read-only
	STATUS	mandatory
	DESCRIPTION
			"The type of location where the FDDI port identified by
			this entry is physically located."
::= { swSysSmtFddiPortEntry 3 }

swSysSmtFddiPortLocationTypeIndex OBJECT-TYPE
	SYNTAX	INTEGER
	ACCESS	read-only
	STATUS	mandatory
	DESCRIPTION
			"The index of the location identified by the corresponding
			instance of swSysSmtFddiPortLocationType where the FDDI port
			identified by this entry is physically located."
::= { swSysSmtFddiPortEntry 4 }

swSysSmtFddiPortLocationLocalIndex OBJECT-TYPE
	SYNTAX	INTEGER
	ACCESS	read-only
	STATUS	mandatory
	DESCRIPTION
			"The local index of the FDDI port identified by this
			entry relative to the location specified by the
			corresponding values of swSysSmtFddiPortLocationType and
			swSysSmtFddiPortLocationTypeIndex."
::= { swSysSmtFddiPortEntry 5 }

swSysSmtFddiPortLabel OBJECT-TYPE
	SYNTAX	DisplayString (SIZE (0..31))
	ACCESS	read-write
	STATUS	mandatory
	DESCRIPTION
			"An ASCII text string describing the FDDI port identified
			by this entry."
::= { swSysSmtFddiPortEntry 6 }

swSysSmtFddiMacLocationTable OBJECT-TYPE
	SYNTAX SEQUENCE OF SwSysSmtFddiMacLocationEntry
	ACCESS not-accessible
	STATUS mandatory
	DESCRIPTION
		"An FDDI MAC Location table contains information to assign
		an FDDI MAC to a different Location.  The system must be
		rebooted after all changes to this table are completed
		in order that the changes take effect."
::= { swSysSmt 7 }

swSysSmtFddiMacLocationEntry OBJECT-TYPE
	SYNTAX SwSysSmtFddiMacLocationEntry
	ACCESS not-accessible
	STATUS mandatory
	DESCRIPTION
		"An FDDI MAC entry contains information to assign
		an FDDI MAC to a different Location."
	INDEX { swSysSmtFddiMacLocationSmtIndex,
			swSysSmtFddiMacLocationIndex }
::= { swSysSmtFddiMacLocationTable 1 }

SwSysSmtFddiMacLocationEntry ::=
	SEQUENCE {
		swSysSmtFddiMacLocationSmtIndex INTEGER,
		swSysSmtFddiMacLocationIndex INTEGER,
		swSysSmtFddiMacCurrentLocation INTEGER,
		swSysSmtFddiMacRequestedLocation INTEGER,
		swSysSmtFddiMacAvailableLocation INTEGER
	}

swSysSmtFddiMacLocationSmtIndex OBJECT-TYPE
	SYNTAX INTEGER
	ACCESS read-only
	STATUS mandatory
	DESCRIPTION
		"The index of the SMT instance identified by this entry,
		relative to the agent."
::= { swSysSmtFddiMacLocationEntry 1 }

swSysSmtFddiMacLocationIndex OBJECT-TYPE
	SYNTAX INTEGER
	ACCESS read-only
	STATUS mandatory
	DESCRIPTION
		"The index of the FDDI MAC instance identified by this entry,
		relative to the SMT identified by this entry."
::= { swSysSmtFddiMacLocationEntry 2 }

swSysSmtFddiMacCurrentLocation OBJECT-TYPE
	SYNTAX INTEGER {
		internalBackplane(1),
		externalFddiPort(2)
	}
	ACCESS read-only
	STATUS mandatory
	DESCRIPTION
		"Indicates whether the MAC identified by this entry is assigned
		to a backplane FDDI station (internal) or an FDDI station
		configured on a module (external.)"
::= { swSysSmtFddiMacLocationEntry 3 }

swSysSmtFddiMacRequestedLocation OBJECT-TYPE
	SYNTAX INTEGER {
		internalBackplane(1),
		externalFddiPort(2)
	}
	ACCESS read-write
	STATUS mandatory
	DESCRIPTION
		"The Location which the MAC identified by this entry is to
		be assigned to during the next reboot."
::= { swSysSmtFddiMacLocationEntry 4 }

swSysSmtFddiMacAvailableLocation OBJECT-TYPE
	SYNTAX INTEGER{
		internalBackplane(1),
		externalFddiPort(2),
		internalOrExternal(3)
	}
	ACCESS read-only
	STATUS mandatory
	DESCRIPTION
		"Indicates the Location(s) available for this MAC.  A mac Location
		 which can be modified to either the interanl backplane or an
		 external FDDI port is indicated by internalOrExternal(3)."
::= { swSysSmtFddiMacLocationEntry 5 }

swSysSmtFddiMacStationTable OBJECT-TYPE
	SYNTAX SEQUENCE OF SwSysSmtFddiMacStationEntry
	ACCESS not-accessible
	STATUS mandatory
	DESCRIPTION
		"An FDDI station MAC table contains information to assign
		an FDDI MAC to an FDDI Station.  The system must be
		rebooted after all changes to this table are completed 
		in order that the changes take effect."
::= { swSysSmt 8 }

swSysSmtFddiMacStationEntry OBJECT-TYPE
	SYNTAX SwSysSmtFddiMacStationEntry
	ACCESS not-accessible
	STATUS mandatory
	DESCRIPTION
		"An FDDI MAC entry contains information to assign
		an FDDI MAC to an FDDI Station."
	INDEX { swSysSmtFddiMacStationSmtIndex,
			swSysSmtFddiMacStationIndex }
::= { swSysSmtFddiMacStationTable 1 }

SwSysSmtFddiMacStationEntry ::=
	SEQUENCE {
		swSysSmtFddiMacStationSmtIndex INTEGER,
		swSysSmtFddiMacStationIndex INTEGER,
		swSysSmtFddiMacCurrentStation INTEGER,
		swSysSmtFddiMacRequestedStation INTEGER,
		swSysSmtFddiMacAvailableStations INTEGER
	}

swSysSmtFddiMacStationSmtIndex OBJECT-TYPE
	SYNTAX INTEGER
	ACCESS read-only
	STATUS mandatory
	DESCRIPTION
		"The index of the SMT instance identified by this entry,
		relative to this agent."
::= { swSysSmtFddiMacStationEntry 1 }

swSysSmtFddiMacStationIndex OBJECT-TYPE
	SYNTAX INTEGER
	ACCESS read-only
	STATUS mandatory
	DESCRIPTION
		"The index of the MAC instance identified by this entry,
		relative to the SMT identified by this entry."
::= { swSysSmtFddiMacStationEntry 2 }

swSysSmtFddiMacCurrentStation OBJECT-TYPE
	SYNTAX INTEGER
	ACCESS read-only
	STATUS mandatory
	DESCRIPTION
		"Indicates which FDDI station that the FDDI MAC identified
		by this entry is assigned to. A value of 0 indicates
		that the mac is assigned to an external station. Otherwise
		the value represents the internal backplane station number."
::= { swSysSmtFddiMacStationEntry 3 }

swSysSmtFddiMacRequestedStation OBJECT-TYPE
	SYNTAX INTEGER
	ACCESS read-write
	STATUS mandatory
	DESCRIPTION
		"Indicates which FDDI station the FDDI MAC identified
		by this entry will be set to during the next system reboot.
		A value of 0 indicates an external station. Otherwise the
		value represents the internal backplane	station number."
::= { swSysSmtFddiMacStationEntry 4 }

swSysSmtFddiMacAvailableStations OBJECT-TYPE
	SYNTAX INTEGER
	ACCESS read-only
	STATUS mandatory
	DESCRIPTION
		"This value is a sum. Setting of the first bit (LSB)
		indicates that the MAC can be assigned to an external
		station. Available backplane stations are indicated
		by adding 2^StationNumber to the sum.  Where StationNumber
		represents a backplane station number."
::= { swSysSmtFddiMacStationEntry 5 }

swSysSmtFddiPortStationTable OBJECT-TYPE
	SYNTAX SEQUENCE OF SwSysSmtFddiPortStationEntry
	ACCESS not-accessible
	STATUS mandatory
	DESCRIPTION
		"An FDDI station Port table contains information to assign
		an FDDI Port to an FDDI Station.  The system must be
		rebooted after all changes to this table are completed 
		in order that the changes take effect."
::= { swSysSmt 9 }

swSysSmtFddiPortStationEntry OBJECT-TYPE
	SYNTAX SwSysSmtFddiPortStationEntry
	ACCESS not-accessible
	STATUS mandatory
	DESCRIPTION
		"An FDDI Port entry contains information to assign
		an FDDI Port to an FDDI Station."
	INDEX { swSysSmtFddiPortStationSmtIndex,
			swSysSmtFddiPortStationIndex }
::= { swSysSmtFddiPortStationTable 1 }

SwSysSmtFddiPortStationEntry ::=
	SEQUENCE {
		swSysSmtFddiPortStationSmtIndex INTEGER,
		swSysSmtFddiPortStationIndex INTEGER,
		swSysSmtFddiPortCurrentStation INTEGER,
		swSysSmtFddiPortRequestedStation INTEGER,
		swSysSmtFddiPortAvailableStations INTEGER
	}

swSysSmtFddiPortStationSmtIndex OBJECT-TYPE
	SYNTAX INTEGER
	ACCESS read-only
	STATUS mandatory
	DESCRIPTION
	"The index of the SMT instance identified by this entry,
	relative to this agent."
::= { swSysSmtFddiPortStationEntry 1 }

swSysSmtFddiPortStationIndex OBJECT-TYPE
	SYNTAX INTEGER
	ACCESS read-only
	STATUS mandatory
	DESCRIPTION
		"The index of the Port instance identified by this entry,
		relative to the SMT indentified by this entry."
::= { swSysSmtFddiPortStationEntry 2 }

swSysSmtFddiPortCurrentStation OBJECT-TYPE
	SYNTAX INTEGER
	ACCESS read-only
	STATUS mandatory
	DESCRIPTION
		"Indicates which FDDI station the FDDI Port identified
		by this entry is assigned to. A value of 0 indicates
		that the Port is assigned to an external station. Otherwise
		the value represents the internal backplane station number."
::= { swSysSmtFddiPortStationEntry 3 }

swSysSmtFddiPortRequestedStation OBJECT-TYPE
	SYNTAX INTEGER
	ACCESS read-write
	STATUS mandatory
	DESCRIPTION
		"Indicates which FDDI station the FDDI port identified
		by this entry will be set to during the next system reboot.
		A value of 0 indicates an external station. Otherwise the
		value represents the internal backplane	station number."
::= { swSysSmtFddiPortStationEntry 4 }

swSysSmtFddiPortAvailableStations OBJECT-TYPE
	SYNTAX INTEGER
	ACCESS read-only
	STATUS mandatory
	DESCRIPTION
		"This value is a sum. Setting of the first bit
		indicates that the port can be assigned to an external
		station. Available backplane stations are indicated
		by adding 2^StationNumber to the sum.  Where StationNumber
		represents a backplane station number."
::= { swSysSmtFddiPortStationEntry 5 }



-- The Switching Systems MIB bridge group.  Implementation of this group
-- is mandatory for agents which manage bridge resources.

swSysBridgeCount OBJECT-TYPE
	SYNTAX	INTEGER
	ACCESS	read-only
	STATUS	mandatory
	DESCRIPTION
			"The count of bridges managed by this agent."
::= { swSysBridge 1 }

-- The Switching Systems MIB bridge table.

swSysBridgeTable OBJECT-TYPE
	SYNTAX	SEQUENCE OF SwSysBridgeEntry
	ACCESS	not-accessible
	STATUS	mandatory
	DESCRIPTION
			"A list of bridge entries.  A single entry exists in this
			list for each bridge managed by this agent."
::= { swSysBridge 2 }

swSysBridgeEntry OBJECT-TYPE
	SYNTAX	SwSysBridgeEntry
	ACCESS	not-accessible
	STATUS	mandatory
	DESCRIPTION
			"A bridge entry contains information about a particular
			bridge managed by this agent."
	INDEX	{ swSysBridgeIndex }
::= { swSysBridgeTable 1 }
						
SwSysBridgeEntry ::=
	SEQUENCE {
		swSysBridgeIndex
			INTEGER,
		swSysBridgePortCount
			INTEGER,
		swSysBridgeAddressTableSize
			INTEGER,
		swSysBridgeAddressTableCount
			INTEGER,
		swSysBridgeAddressTablePeakCount
			INTEGER,
		swSysBridgeAddressThreshold
			INTEGER,
		swSysBridgeMode
			INTEGER,
		swSysBridgeBackbonePort
			INTEGER,
		swSysBridgeIpFragmentationEnabled
			INTEGER,
		swSysBridgeTrFddiTranslationMode
			INTEGER,
		swSysBridgeSTPGroupAddress 
			OCTET STRING,
		swSysBridgeSTPEnable
			INTEGER,
		swSysBridgeIpxSnapTranslationEnable
			INTEGER,
		swSysBridgeLowLatencyEnable
			INTEGER,
		swSysBridgeVlanMode
			INTEGER
		}


swSysBridgeIndex OBJECT-TYPE
	SYNTAX	INTEGER
	ACCESS	read-only
	STATUS	mandatory
	DESCRIPTION
			"The index of the bridge identified by this entry,
			relative to this agent."
::= { swSysBridgeEntry 1 }

swSysBridgePortCount OBJECT-TYPE
	SYNTAX	INTEGER
	ACCESS	read-only
	STATUS	mandatory
	DESCRIPTION
			"The number of bridge ports that the bridge identified by
			this entry controls."
::= { swSysBridgeEntry 2 }

swSysBridgeAddressTableSize OBJECT-TYPE
	SYNTAX	INTEGER 
	ACCESS	read-only
	STATUS	mandatory
	DESCRIPTION
			"The size of the address table for the bridge identified
			by this entry."
::= { swSysBridgeEntry 3 }

swSysBridgeAddressTableCount OBJECT-TYPE
	SYNTAX	INTEGER 
	ACCESS	read-only
	STATUS	mandatory
	DESCRIPTION
			"The current count of addresses in the address table for
			the bridge identified by this entry."
::= { swSysBridgeEntry 4 }

swSysBridgeAddressTablePeakCount OBJECT-TYPE
	SYNTAX	INTEGER 
	ACCESS	read-only
	STATUS	mandatory
	DESCRIPTION
			"The peak count of addresses in the address table for the
			bridge identified by this entry, since the system was last
			initialized."
::= { swSysBridgeEntry 5 }

swSysBridgeAddressThreshold OBJECT-TYPE
	SYNTAX	INTEGER 
	ACCESS	read-write
	STATUS	mandatory
	DESCRIPTION
			"A reporting threshold for the total number of addresses
			known for the bridge identified by this entry.  When this
			threshold is reached, the event
			swSysBridgeAddressThresholdEvent is generated.  The range of
			valid values for setting this object is between 1 and the
			corresponding value reported by swSysBridgeAddressTableSize
			+ 1 (Note that this range applies to values issued in set
			requests.  The current value may be outside this range,
			for example if the corresponding value of swSysBridgeMode is
			changed). Setting this object to one greater than the
			address table size disables the generation of
			swSysBridgeAddressThresholdEvents since the limit will never
			be reached."
::= { swSysBridgeEntry 6 }

swSysBridgeMode OBJECT-TYPE
	SYNTAX	INTEGER {
			expressMode(1),
			ieee8021dBridgeMode(2),
			notSupported(3),
			ieee8021dSRTBridgeMode(4),
			ieee8021dSRBridgeMode(5),
			ibmSRBridgeMode(6),
			srtBBridgeMode(7),
			srExpressBridgeMode(8)
			}
	ACCESS	read-write
	STATUS	mandatory
	DESCRIPTION
			"The operational mode of the bridge identified by this
			entry.  Note that bridges which report notSupported(3)
			will not support sets of this object, and that the value
			notSupported(3) is not a valid value for a set operation."
::= { swSysBridgeEntry 7 }

swSysBridgeBackbonePort OBJECT-TYPE
	SYNTAX	INTEGER
	ACCESS	read-write
	STATUS	mandatory
	DESCRIPTION
			"The number of the port selected as the backbone segment
			port when the corresponding value of swSysBridgeMode is
			is expressMode(1).  The value of this object can range
			from 1 to the corresponding value of swSysBridgePortCount,
			however, some bridges may support only a subset of ports
			as backbone ports.  If the corresponding value of
			swSysBridgeMode is not expressMode(1), the value of this
			object is ignored."
::= { swSysBridgeEntry 8 }

swSysBridgeIpFragmentationEnabled OBJECT-TYPE
	SYNTAX	INTEGER {
				true(1),
				false(2),
				notSupported(3)
			}
	ACCESS	read-write
	STATUS	mandatory
	DESCRIPTION
			"A flag indicating whether or not IP fragmentation is
			enabled on this bridge.  Note that bridges which report
			notSupported(3) will not support sets of this object, and
			that the value notSupported(3) is not a valid value for a
			set operation."
::= { swSysBridgeEntry 9 }

swSysBridgeTrFddiTranslationMode OBJECT-TYPE
	SYNTAX	INTEGER {
			native(1),
			backbone(2)
			}
	ACCESS	read-write
	STATUS	mandatory
	DESCRIPTION
			"The mode used to describe whether the embedded MAC
			addresses are byte-conjugated in order to convert them
			from Token Ring format to native FDDI format (and vice
			versa), or whether they are left alone (used for traffic
			flowing	across a FDDI backbone to/from Token Ring end
			stations)."
::= { swSysBridgeEntry 10 }

swSysBridgeSTPGroupAddress OBJECT-TYPE
	SYNTAX	OCTET STRING (SIZE (6)) -- 6 octet address in "canonical" order
	ACCESS  read-write
	STATUS  mandatory
	DESCRIPTION
			"Spanning tree bridge group address. The address cannot be 
			changed if the spanning tree is enabled (swSysBridgeStpEnabled)."
::= { swSysBridgeEntry 11 }

swSysBridgeSTPEnable OBJECT-TYPE
	SYNTAX  INTEGER {
				true(1),
				false(2)
			}
	ACCESS  read-write
	STATUS  mandatory
	DESCRIPTION
	"This object indicates if spanning tree bridge feature is
	enabled or disabled.  If enabled this value will equal true(1)."
::= { swSysBridgeEntry 12 }

swSysBridgeIpxSnapTranslationEnable OBJECT-TYPE
	SYNTAX  INTEGER {
				true(1),
				false(2)
			}
	ACCESS  read-write
	STATUS  mandatory
	DESCRIPTION
		"This object indicates if the IPX 802.3-FDDI SNAP Translation
		 bridge feature is enabled or disabled.  If enabled this
		 value will equal true(1). Note, this object may not be
		 supported on all bridges."
::= { swSysBridgeEntry 13  }

swSysBridgeLowLatencyEnable OBJECT-TYPE
	SYNTAX  INTEGER {
				true(1),
				false(2)
			}
	ACCESS  read-write
	STATUS  mandatory
	DESCRIPTION
		"This object indicates if the bridge low latency
		 feature is enabled or disabled.  If enabled this
		 value will equal true(1). Note, this object may not be
		 supported on all bridges."
::= { swSysBridgeEntry 14  }

swSysBridgeVlanMode OBJECT-TYPE
	SYNTAX  INTEGER {
		open(1),
		closed(2),
		mixed(3),
		notSupported(4)
		}
	ACCESS  read-write
	STATUS  mandatory
	DESCRIPTION
		"This object indicates the VLAN types that this
		bridge will support.  Open mode means that each VLAN
		within this bridge will be of the Open type; all VLANs
		within this bridge will share the same address table.
		Closed mode means that each VLAN within this bridge
		will be of the Closed type; each VLAN within this
		bridge will have its own address table.  Mixed mode
		means that each VLAN within this bridge with be of
		either the Open or Closed type; all Open VLANs will
		share the same address table and each Closed VLAN
		will have its own address table."
::= { swSysBridgeEntry 15  }

-- The Switching Systems MIB bridge port table.

swSysBridgePortTable OBJECT-TYPE
	SYNTAX	SEQUENCE OF SwSysBridgePortEntry
	ACCESS	not-accessible
	STATUS	mandatory
	DESCRIPTION
			"A list of bridge port entries.  A single entry exists in
			this list for each bridge port managed by this agent."
::= { swSysBridge 3 }

swSysBridgePortEntry OBJECT-TYPE
	SYNTAX	SwSysBridgePortEntry
	ACCESS	not-accessible
	STATUS	mandatory
	DESCRIPTION
			"A bridge port entry contains information about a
			particular bridge port managed by this agent."
	INDEX	{ swSysBridgePortBridgeIndex,
					swSysBridgePortIndex }
::= { swSysBridgePortTable 1 }

SwSysBridgePortEntry ::=
	SEQUENCE {
		swSysBridgePortBridgeIndex
			INTEGER,
		swSysBridgePortIndex
			INTEGER,
		swSysBridgePortIfIndex
			INTEGER,
		swSysBridgePortReceiveMulticastLimit
			INTEGER,
		swSysBridgePortAddressAction
			INTEGER,
		swSysBridgePortSpanningTreeFrameReceivedCounts
			Counter,
		swSysBridgePortReceiveBlockedDiscards
			Counter,
		swSysBridgePortReceiveMulticastLimitExceededs
			Counter,
		swSysBridgePortReceiveMulticastLimitExceededDiscards
			Counter,
		swSysBridgePortReceiveSecurityDiscards
			Counter,
		swSysBridgePortReceiveUnknownDiscards
			Counter,
		swSysBridgePortReceiveOtherDiscards
			Counter,
		swSysBridgePortReceiveErrorDiscards
			Counter,
		swSysBridgePortSameSegmentDiscards
			Counter,
		swSysBridgePortTransmitBlockedDiscards
			Counter,
		swSysBridgePortReceiveAllPathFilteredFrames
			Counter,
		swSysBridgePortReceiveMulticastPathFilteredFrames
			Counter,
		swSysBridgePortTransmitAllPathFilteredFrames
			Counter,
		swSysBridgePortTransmitMulticastPathFilteredFrames
			Counter,
		swSysBridgePortForwardedUnicastFrames
			Counter,
		swSysBridgePortForwardedUnicastOctets
			Counter,
		swSysBridgePortForwardedMulticastFrames
			Counter,
		swSysBridgePortForwardedMulticastOctets
			Counter,
		swSysBridgePortFloodedUnicastFrames
			Counter,
		swSysBridgePortFloodedUnicastOctets
			Counter,
		swSysBridgePortStpMode
			INTEGER,
		swSysBridgePortReceiveMulticastLimitFrameType
			INTEGER
	}

swSysBridgePortBridgeIndex OBJECT-TYPE
	SYNTAX	INTEGER
	ACCESS	read-only
	STATUS	mandatory
	DESCRIPTION
			"The index of the bridge identified by this entry,
			relative to this agent."
::= { swSysBridgePortEntry 1 }

swSysBridgePortIndex OBJECT-TYPE
	SYNTAX	INTEGER
	ACCESS	read-only
	STATUS	mandatory
	DESCRIPTION
			"The index of the bridge port identified by this entry,
			within the bridge identified by this entry."
::= { swSysBridgePortEntry 2 }

swSysBridgePortIfIndex OBJECT-TYPE
	SYNTAX	INTEGER
	ACCESS	read-only
	STATUS	mandatory
	DESCRIPTION
			"The value of the MIB-II ifIndex corresponding to the
			bridge port identified by this entry."
::= { swSysBridgePortEntry 3 }

swSysBridgePortReceiveMulticastLimit OBJECT-TYPE
	SYNTAX	INTEGER (0..65535)
	ACCESS	read-write
	STATUS	mandatory
	DESCRIPTION
			"The maximum number of multicast frames per second that
			can be received in the sample interval.  The sample
			interval is one second.  The default value for this object
			is zero which implies an infinite rate."
::= { swSysBridgePortEntry 4 }

swSysBridgePortAddressAction OBJECT-TYPE
	SYNTAX	INTEGER {
				other(1),
				freezeAddress(2),
				flushAddress(3),
				flushDynamicAddress(4)
					}
	ACCESS	read-write
	STATUS	mandatory
	DESCRIPTION
			"This object, when read, always returns the value
			other(1).  The behavior of setting this object to each of
			the acceptable values is as follows:

				freezeAddress:	causes all the learned dynamic
								addresses to be converted into static
								addresses.

				flushAddress:   causes all the addresses to be flushed
								from the address list for the bridge
								port identified by this entry.

				flushDynamicAddress:
								causes all dynamic addresses to be
								flushed from the address list for the
								bridge port identified by this entry."
::= { swSysBridgePortEntry 5 }

swSysBridgePortSpanningTreeFrameReceivedCounts OBJECT-TYPE
	SYNTAX	Counter
	ACCESS	read-only
	STATUS	mandatory
	DESCRIPTION
			"The number of spanning tree frames received by the
			bridge port identified by this entry."
::= { swSysBridgePortEntry 6 }

swSysBridgePortReceiveBlockedDiscards OBJECT-TYPE
	SYNTAX	Counter
	ACCESS	read-only
	STATUS	mandatory
	DESCRIPTION
			"The number of frames discarded by the bridge port
			identified by this entry because the receiving bridge port
			was not in the 'forwarding' state."
::= { swSysBridgePortEntry 7 }

swSysBridgePortReceiveMulticastLimitExceededs OBJECT-TYPE
	SYNTAX	Counter
	ACCESS	read-only
	STATUS	mandatory
	DESCRIPTION
			"The number of times the value of
			swSysBridgePortReceiveMulticastLimit was exceeded for the
			port identified by this entry."
::= { swSysBridgePortEntry 8 }

swSysBridgePortReceiveMulticastLimitExceededDiscards OBJECT-TYPE
	SYNTAX	Counter
	ACCESS	read-only
	STATUS	mandatory
	DESCRIPTION
			"The number of multicast/broadcast frames discarded by the
			bridge port identified by this entry because the
			corresponding value of swSysBridgePortReceiveMulticastLimit
			was exceeded."
::= { swSysBridgePortEntry 9 }

swSysBridgePortReceiveSecurityDiscards OBJECT-TYPE
	SYNTAX	Counter
	ACCESS	read-only
	STATUS	mandatory
	DESCRIPTION
			"The number of frames discarded by the bridge port
			identified by this entry because they contained source
			addresses which were statically configured on another
			bridge port.  A statically configured address (station),
			which is not allowed to move, appears to have moved."
::= { swSysBridgePortEntry 10 }

swSysBridgePortReceiveUnknownDiscards OBJECT-TYPE
	SYNTAX	Counter
	ACCESS	read-only
	STATUS	mandatory
	DESCRIPTION
			"The number of frames discarded by the bridge port
			identified by this entry because the destination address
			was unknown.  Note that this counter is only valid for
			backbone ports, and only when the bridge is operating in
			express mode."
::= { swSysBridgePortEntry 11 }

swSysBridgePortReceiveOtherDiscards OBJECT-TYPE
	SYNTAX	Counter
	ACCESS	read-only
	STATUS	mandatory
	DESCRIPTION
			"The number of frames discarded by the bridge port
			identified by this entry because they contained either
			invalid (group) source addresses or source addresses
			belonging to this bridge (indicative of network loops)."
::= { swSysBridgePortEntry 12 }

swSysBridgePortReceiveErrorDiscards OBJECT-TYPE
	SYNTAX	Counter
	ACCESS	read-only
	STATUS	mandatory
	DESCRIPTION
			"The number of frames discarded by the bridge port
			identified by this entry because of internal bridge system
			errors (e.g., hardware and software address table
			discrepencies)."
::= { swSysBridgePortEntry 13 }

swSysBridgePortSameSegmentDiscards OBJECT-TYPE
	SYNTAX	Counter
	ACCESS	read-only
	STATUS	mandatory
	DESCRIPTION
			"The number of frames discarded by the bridge port
			identified by this entry because the destination address
			is known on the same network segment as the source address,
			i.e., the frame does not need to be bridged."
::= { swSysBridgePortEntry 14 }

swSysBridgePortTransmitBlockedDiscards OBJECT-TYPE
	SYNTAX	Counter
	ACCESS	read-only
	STATUS	mandatory
	DESCRIPTION
			"The number of frames discarded by the bridge port
			identified by this entry because the transmitting bridge
			port was not in the 'forwarding' state."
::= { swSysBridgePortEntry 15 }

swSysBridgePortReceiveAllPathFilteredFrames OBJECT-TYPE
	SYNTAX	Counter
	ACCESS	read-only
	STATUS	mandatory
	DESCRIPTION
			"The number of frames discarded by the bridge port
			identified by this entry due to user defined receive all
			path filters."
::= { swSysBridgePortEntry 16 }

swSysBridgePortReceiveMulticastPathFilteredFrames OBJECT-TYPE
	SYNTAX	Counter
	ACCESS	read-only
	STATUS	mandatory
	DESCRIPTION
			"The number of frames discarded by the bridge port
			identified by this entry due to user defined receive
			multicast path filters."
::= { swSysBridgePortEntry 17 }

swSysBridgePortTransmitAllPathFilteredFrames OBJECT-TYPE
	SYNTAX	Counter
	ACCESS	read-only
	STATUS	mandatory
	DESCRIPTION
			"The number of frames discarded by the bridge port
			identified by this entry due to user defined transmit all
			path filters."
::= { swSysBridgePortEntry 18 }

swSysBridgePortTransmitMulticastPathFilteredFrames OBJECT-TYPE
	SYNTAX	Counter
	ACCESS	read-only
	STATUS	mandatory
	DESCRIPTION
			"The number of frames discarded by the bridge port
			identified by this entry due to user defined transmit
			multicast path filters."
::= { swSysBridgePortEntry 19 }

swSysBridgePortForwardedUnicastFrames OBJECT-TYPE
	SYNTAX	Counter
	ACCESS	read-only
	STATUS	mandatory
	DESCRIPTION
			"The number of unicast frames which this port forwarded
			to a single destination port."
::= { swSysBridgePortEntry 20 }

swSysBridgePortForwardedUnicastOctets OBJECT-TYPE
	SYNTAX	Counter
	ACCESS	read-only
	STATUS	mandatory
	DESCRIPTION
			"The number of octets contained in unicast frames
			which this port forwarded to a single destination port."
::= { swSysBridgePortEntry 21 }

swSysBridgePortForwardedMulticastFrames OBJECT-TYPE
	SYNTAX	Counter
	ACCESS	read-only
	STATUS	mandatory
	DESCRIPTION
			"The number of multicast frames which this port forwarded."
::= { swSysBridgePortEntry 22 }

swSysBridgePortForwardedMulticastOctets OBJECT-TYPE
	SYNTAX	Counter
	ACCESS	read-only
	STATUS	mandatory
	DESCRIPTION
			"The number of octets contained in multicast frames which
			this port forwarded."
::= { swSysBridgePortEntry 23 }

swSysBridgePortFloodedUnicastFrames OBJECT-TYPE
	SYNTAX	Counter
	ACCESS	read-only
	STATUS	mandatory
	DESCRIPTION
			"The number of unicast frames which this port flooded to
			all other ports in the bridge."
::= { swSysBridgePortEntry 24 }

swSysBridgePortFloodedUnicastOctets OBJECT-TYPE
	SYNTAX	Counter
	ACCESS	read-only
	STATUS	mandatory
	DESCRIPTION
			"The number of octets contained in unicast frames which
			this port flooded to all other ports in the bridge."
::= { swSysBridgePortEntry 25 }


swSysBridgePortStpMode OBJECT-TYPE
	SYNTAX  INTEGER {
				enable(1),
				disable(2),
				remove(3)
				}
	ACCESS  read-write
	STATUS  mandatory
	DESCRIPTION
			"The mode of the bridge port."
	REFERENCE
			"IEEE 802.1D-1990: Section 4.5.5.2 for enable and disable modes."
::= { swSysBridgePortEntry 26 }

swSysBridgePortReceiveMulticastLimitFrameType OBJECT-TYPE
	SYNTAX  INTEGER {
				broadcastAndMulticast(1),
				broadcastOnly(2)
			}
	ACCESS  read-write
	STATUS  mandatory
	DESCRIPTION
		"This object identifies the frames type(s) that are to be
		counted when determining if the receive multicast limit
		has been exceeded for this bridge port.  Devices attached
		to networks with predominantly high multicast traffic
		(e.g. video) should set this value to broadcastOnly(2)
		to detect broadcast storms."
::= { swSysBridgePortEntry 27 }


--	::= { swSysBridge 4 } Reserved.  Do not use.


-- The Switching Systems MIB bridge port address table

swSysBridgePortAddressTable OBJECT-TYPE
	SYNTAX	SEQUENCE OF SwSysBridgePortAddressEntry
	ACCESS	not-accessible
	STATUS	mandatory
	DESCRIPTION
			"A list of bridge port address information.  A single
			entry exists in this list for each learned address,
			accross all bridge ports and all bridges managed by this
			agent."
::= { swSysBridge 5 }

swSysBridgePortAddressEntry OBJECT-TYPE
	SYNTAX	SwSysBridgePortAddressEntry
	ACCESS	not-accessible
	STATUS	mandatory
	DESCRIPTION
			"An bridge port address entry contains information about a
			particular bridge port address.  To create a new entry,
			set an instance of swSysBridgePortAddressRemoteAddress with
			the address index portion of the instance set to 0, to a
			valid value.  To remove an entry, set the instance of the
			swSysBridgePortAddressType for the entry to invalid(2)."
	INDEX	{ swSysBridgePortAddressBridgeIndex, 
			swSysBridgePortAddressPortIndex, 
			swSysBridgePortAddressIndex }
::= { swSysBridgePortAddressTable 1 }

SwSysBridgePortAddressEntry ::=
	SEQUENCE {
		swSysBridgePortAddressBridgeIndex
			INTEGER,
		swSysBridgePortAddressPortIndex
			INTEGER,
		swSysBridgePortAddressIndex
			INTEGER,
		swSysBridgePortAddressRemoteAddress
			OCTET STRING,
		swSysBridgePortAddressType
			INTEGER,
		swSysBridgePortAddressIsStatic
			INTEGER,
		swSysBridgePortAddressStaticPort
			INTEGER,
		swSysBridgePortAddressAge
			INTEGER
	}

swSysBridgePortAddressBridgeIndex OBJECT-TYPE
	SYNTAX	INTEGER
	ACCESS	read-only
	STATUS	mandatory
	DESCRIPTION
			"The index of the bridge identified by this entry,
			relative to this agent."
::= { swSysBridgePortAddressEntry 1 }

swSysBridgePortAddressPortIndex OBJECT-TYPE
	SYNTAX	INTEGER
	ACCESS	read-only
	STATUS	mandatory
	DESCRIPTION
			"The index of the bridge port identified by this entry,
			within the bridge identified by this entry."
::= { swSysBridgePortAddressEntry 2 }

swSysBridgePortAddressIndex OBJECT-TYPE
	SYNTAX	INTEGER
	ACCESS	read-only
	STATUS	mandatory
	DESCRIPTION
			"The index of this address entry within the bridge address
			table for the bridge identified by this entry.  This index
			ranges from 1 to the corresponding value of
			swSysBridgeAddressTableSize." 
::= { swSysBridgePortAddressEntry 3 }

swSysBridgePortAddressRemoteAddress OBJECT-TYPE
	SYNTAX	OCTET STRING (SIZE (6)) -- 6 octet address in "canonical" order
	ACCESS	read-write
	STATUS	mandatory
	DESCRIPTION
			"The remote MAC address detected on the bridge port
			identified by to this entry.  Setting this object results
			in an attempt to create a new entry in the table.  Since
			the value of swSysBridgePortAddressIndex is determined
			automatically internal to the bridge, a set is only
			successful if the index value specified for
			swSysBridgePortAddressIndex is zero.  A get-next
			using the values of swSysBridgePortAddressTypeIndex and
			swSysBridgePortAddressPortIndex can be used to determine the
			address index assigned to the newly added address entry."
::= { swSysBridgePortAddressEntry 4 }

swSysBridgePortAddressType OBJECT-TYPE
	SYNTAX INTEGER {
				valid(1),
				invalid(2)
			}
	ACCESS	read-write
	STATUS	mandatory
	DESCRIPTION
			"This object, when read, always returns the value valid(1).
			Setting this object to invalid(2) will remove the
			corresponding address entry from the table."
::= { swSysBridgePortAddressEntry 5 }

swSysBridgePortAddressIsStatic OBJECT-TYPE
	SYNTAX	INTEGER {
				isStatic(1),
				isDynamic(2)
			}
	ACCESS	read-write
	STATUS	mandatory
	DESCRIPTION
			"A value indicating whether this MAC address was
			statically configured or was dynamically learned.  Note
			that isStatic(1) it the only valid for set operations."
::= { swSysBridgePortAddressEntry 6 }

swSysBridgePortAddressStaticPort OBJECT-TYPE
	SYNTAX	INTEGER
	ACCESS	read-only
	STATUS	mandatory
	DESCRIPTION
			"If the corresponding value of the object 
			swSysBridgePortAddressIsStatic is isStatic(1), this object
			indicates the local bridge port index (as reported by
			swSysBridgePortLocalIndex) for which this address MAC was
			statically configured.  If the object
			swSysBridgePortAddressIsStatic has the value isDynamic(2),
			the value of this object is 0."
::= { swSysBridgePortAddressEntry 7 }

swSysBridgePortAddressAge OBJECT-TYPE
	SYNTAX	INTEGER
	ACCESS	read-only
	STATUS	mandatory
	DESCRIPTION
			"This object indicates the time, in seconds, elapsed since
			a packet containing this address as a source was last seen
			on the bridge port identified by this entry."
::= { swSysBridgePortAddressEntry 8 }

swSysBridgeStpGroupAddress OBJECT-TYPE
	SYNTAX	OCTET STRING (SIZE (6)) -- 6 octet address in "canonical" order
	ACCESS  read-write
	STATUS  obsolete
	DESCRIPTION
			"Spanning tree bridge group address. The address cannot be 
			changed if the spanning tree is enabled (swSysBridgeStpEnabled).
			This object can now be found under the swSysBridgeTable 
			as swSysBridgeSTPGroupAddress."
		::= { swSysBridge 6 }

swSysBridgeStpEnable OBJECT-TYPE
	SYNTAX  INTEGER {
				true(1),
				false(2)
			}
	ACCESS  read-write
	STATUS  obsolete
	DESCRIPTION
			"This object indicates if spanning tree bridge feature is
			enabled or disabled.  If enabled this value will equal true(1).
			This object can now be found under the swSysBridgeTable 
			as swSysBridgeSTPEnable."
::= { swSysBridge 7 }

-- The Switching Systems MIB IP router group.  Implementation of this
-- group is mandatory for agents which manage IP router resources.
-- This group is reserved for future use.

-- The Switching Systems MIB networking monitoring group.  Implementation
-- of this group is manadatory for all agents which manage bridge
-- resources that support network monitoring.

-- The Switching Systems MIB network analyzer table.

swSysNetworkAnalyzerTable OBJECT-TYPE
	SYNTAX	SEQUENCE OF SwSysNetworkAnalyzerTableEntry
	ACCESS	not-accessible
	STATUS	mandatory
	DESCRIPTION
			"A list of analyzer entries.  A single entry exists in this
			list for each bridge port configured for an analyzer."
::= { swSysNetworkMonitor 1 }

swSysNetworkAnalyzerTableEntry OBJECT-TYPE
	SYNTAX	SwSysNetworkAnalyzerTableEntry
	ACCESS	not-accessible
	STATUS	mandatory
	DESCRIPTION
			"An analyzer table entry contains information relating an
			analyzer port address to the bridge and port index for that
			analyzer.

			The effect of creating an entry for a particular port is
			to configure that port for monitoring.  A port which is
			configured for monitoring is no longer available for
			switching.  To create an entry, set the value of the
			swSysNetworkAnalyzerStatus object for a non-existent instance
			to valid(1).  The value of the swSysNetworkAnalyzerPhysicalAddress
			object for the new entry is filled in as a result of the
			creation.

			The effect of removing an entry for a particular port is to
			disable the port for monitoring.  The port is then available
			for switching.  To remove an entry, set the value of the
			corresponding instance of the swSysNetworkAnalyzerStatus object
			to invalid(2)."
	INDEX	{ swSysNetworkAnalyzerBridgeIndex,
			swSysNetworkAnalyzerBridgePortIndex}
::= { swSysNetworkAnalyzerTable 1 }

SwSysNetworkAnalyzerTableEntry ::=
	SEQUENCE {
		swSysNetworkAnalyzerBridgeIndex
			INTEGER,
		swSysNetworkAnalyzerBridgePortIndex
			INTEGER,
		swSysNetworkAnalyzerPhysicalAddress
			OCTET STRING,
		swSysNetworkAnalyzerStatus
			INTEGER
	}

swSysNetworkAnalyzerBridgeIndex OBJECT-TYPE
	SYNTAX	INTEGER
	ACCESS	read-only
	STATUS	mandatory
	DESCRIPTION
			"The index of the bridge relative to this agent where the
			analyzer identified by this entry is configured."
::= { swSysNetworkAnalyzerTableEntry 1 }

swSysNetworkAnalyzerBridgePortIndex OBJECT-TYPE
	SYNTAX	INTEGER
	ACCESS	read-only
	STATUS	mandatory
	DESCRIPTION
			"The index of the port relative to the bridge identified by
			this entry where the analyzer identified by this entry is
			configured."
::= { swSysNetworkAnalyzerTableEntry 2 }

swSysNetworkAnalyzerPhysicalAddress OBJECT-TYPE
	SYNTAX	OCTET STRING (SIZE (6)) -- 6 octet address in "canonical" order
	ACCESS	read-only
	STATUS	mandatory
	DESCRIPTION
			"The physical address of the bridge port identified by the
			corresponding values of swSysNetworkAnalyzerBridgeIndex and
			swSysNetworkAnayzerBridgePortIndex."
::= { swSysNetworkAnalyzerTableEntry 3 }

swSysNetworkAnalyzerStatus OBJECT-TYPE
	SYNTAX	INTEGER {
				valid(1),
				invalid(2)
			}
	ACCESS	read-write
	STATUS	mandatory
	DESCRIPTION
			"The status of the entry.  Setting the value of a non-existent
			instance of this object to valid(1) attempts to add the
			corresponding entry to the table.  The effect of adding an
			entry to the table is to configure the port for monitoring and
			to disable it for switching.  Setting an existing instance of
			this object to invalid(2) attempts to remove the corresponding
			entry from the table.  The effect of removing an entry from
			the table is to disable the port for monitoring and to make
			available for switching."
::= { swSysNetworkAnalyzerTableEntry 4 }

-- The Switching Systems MIB network port monitor table.

swSysNetworkPortMonitorTable OBJECT-TYPE
	SYNTAX	SEQUENCE OF SwSysNetworkPortMonitorTableEntry
	ACCESS	not-accessible
	STATUS	mandatory
	DESCRIPTION
			"A list of monitor port entries.  A single entry exists in
			this for each bridge port being monitored."
::= { swSysNetworkMonitor 2 }

swSysNetworkPortMonitorTableEntry OBJECT-TYPE
	SYNTAX	SwSysNetworkPortMonitorTableEntry
	ACCESS	not-accessible
	STATUS	mandatory
	DESCRIPTION
			"A port monitor table entry contains information relating a
			bridge port being monitored with the address of the analyzer
			which is being used to monitor the port.

			The effect of creating an entry for a particular port is to
			enable monitoring of that port by the analyzer specified.  To
			create an entry, set the value of the
			swSysNetworkPortMonitorAnalyzerAddress object to the address of
			the network analyzer port.  This value should be the same as
			the value of the swSysNetworkAnalyzerPhysicalAddress object for
			the analyzer.

			The effect of removing an entry for a particular port is to
			disable monitoring of that port.  To remove an entry, set the
			value of the corresponding instance of the
			swSysNetworkPortMonitorStatus object to invalid(2)."
	INDEX	{ swSysNetworkPortMonitorBridgeIndex,
			swSysNetworkPortMonitorBridgePortIndex }
::= { swSysNetworkPortMonitorTable 1 }

SwSysNetworkPortMonitorTableEntry ::=
	SEQUENCE {
		swSysNetworkPortMonitorBridgeIndex
			INTEGER,
		swSysNetworkPortMonitorBridgePortIndex
			INTEGER,
		swSysNetworkPortMonitorAnalyzerAddress
			OCTET STRING,
		swSysNetworkPortMonitorStatus
			INTEGER
	}

swSysNetworkPortMonitorBridgeIndex OBJECT-TYPE
	SYNTAX	INTEGER
	ACCESS	read-only
	STATUS	mandatory
	DESCRIPTION
			"The index of the bridge relative to this agent where the
			monitored port identified by this entry is located."
::= { swSysNetworkPortMonitorTableEntry 1 }

swSysNetworkPortMonitorBridgePortIndex OBJECT-TYPE
	SYNTAX	INTEGER
	ACCESS	read-only
	STATUS	mandatory
	DESCRIPTION
			"The index of the port which is being monitored relative to
			the bridge identified by this entry."
::= { swSysNetworkPortMonitorTableEntry 2 }

swSysNetworkPortMonitorAnalyzerAddress OBJECT-TYPE
	SYNTAX	OCTET STRING (SIZE (6)) -- 6 octet address in "canonical" order
	ACCESS	read-write
	STATUS	mandatory
	DESCRIPTION
			"The physical address of the port where the analyzer,
			which is monitoring the port identified by this entry, is
			located.  Setting the value of a non-existent instance of
			this object attempts to add an entry to the table.  The effect
			of adding an entry to the table is to enable monitoring of the
			port by the analyzer specified.  Setting the value of an
			existing instance of this object will switch the monitored
			port to the new analyzer address."
::= { swSysNetworkPortMonitorTableEntry 3 }

swSysNetworkPortMonitorStatus OBJECT-TYPE
	SYNTAX	INTEGER {
				valid(1),
				invalid(2)
			}
	ACCESS	read-write
	STATUS	mandatory
	DESCRIPTION
			"The status of the entry.  Setting an existing instance
			of this object to invalid(2) attempts to remove the
			corresponding entry from the table.  The effect of removing
			an entry from the table is to disable monitoring of the
			port."
::= { swSysNetworkPortMonitorTableEntry 4 }

-- The Switching Systems MIB token ring port group.  Implementation of
-- this group is mandatory for agents which manage token ring port
-- resources.

swSysTokenRingPortCount OBJECT-TYPE
	SYNTAX	INTEGER
	ACCESS	read-only
	STATUS	mandatory
	DESCRIPTION
			"The count of token ring ports managed by this agent."
::= { swSysTokenRingPort 1 }


-- The Switching Systems MIB token ring port table.

swSysTokenRingPortTable OBJECT-TYPE
	SYNTAX	SEQUENCE OF SwSysTokenRingPortEntry
	ACCESS	not-accessible
	STATUS	mandatory
	DESCRIPTION
			"A list of token ring port entries.  A single entry exists
			 in this list for each token ring port managed by this agent."
::= { swSysTokenRingPort 2 }

swSysTokenRingPortEntry OBJECT-TYPE
	SYNTAX	SwSysTokenRingPortEntry
	ACCESS	not-accessible
	STATUS	mandatory
	DESCRIPTION
			"A token ring port entry contains information about a
			 particular token ring port managed by this agent."
	INDEX	{ swSysTokenRingPortIndex }
::= { swSysTokenRingPortTable 1 }

SwSysTokenRingPortEntry ::=
	SEQUENCE {
		swSysTokenRingPortIndex			INTEGER,
		swSysTokenRingPortIfIndex		INTEGER,
		swSysTokenRingPortLabel			DisplayString,
		swSysTokenRingPortInsertStatus	INTEGER,
		swSysTokenRingPortType			INTEGER,
		swSysTokenRingPortMode			INTEGER,
		swSysTokenRingPortSpeed			INTEGER,
		swSysTokenRingPortLineErrors	Counter,
		swSysTokenRingPortBurstErrors	Counter,
		swSysTokenRingPortACErrors		Counter,
		swSysTokenRingPortAbortTransErrors	Counter,
		swSysTokenRingPortInternalErrors	Counter,
		swSysTokenRingPortLostFrameErrors	Counter,
		swSysTokenRingPortReceiveCongestionErrors	Counter,
		swSysTokenRingPortFrameCopiedErrors	Counter,
		swSysTokenRingPortTokenErrors		Counter,
		swSysTokenRingPortSoftErrors		Counter,
		swSysTokenRingPortHardErrors		Counter,
		swSysTokenRingPortTransmitBeacons	Counter,
		swSysTokenRingPortLobeWires			Counter,
		swSysTokenRingPortRemoves			Counter,
		swSysTokenRingPortSingles			Counter,
		swSysTokenRingPortFreqErrors		Counter,
		swSysTokenRingPortRingStatus		INTEGER
	}

swSysTokenRingPortIndex OBJECT-TYPE
	SYNTAX	INTEGER
	ACCESS	read-only
	STATUS	mandatory
	DESCRIPTION
		"The index of the token ring port identified by this entry,
		 relative to this agent."
::= { swSysTokenRingPortEntry 1 }

swSysTokenRingPortIfIndex OBJECT-TYPE
	SYNTAX	INTEGER
	ACCESS	read-only
	STATUS	mandatory
	DESCRIPTION
			"The value of the MIB-II ifIndex corresponding to the
			 token ring port identified by this entry."
::= { swSysTokenRingPortEntry 2 }

swSysTokenRingPortLabel OBJECT-TYPE
	SYNTAX	DisplayString (SIZE (0..31))
	ACCESS	read-write
	STATUS	mandatory
	DESCRIPTION
			"An ASCII text string describing the token ring port
			 identified by this entry."
::= { swSysTokenRingPortEntry 3 }

swSysTokenRingPortInsertStatus OBJECT-TYPE
	SYNTAX	INTEGER {
			inserted(1),
			deinserted(2)
			}
	ACCESS	read-only
	STATUS	mandatory
	DESCRIPTION
		"The current value of the link status for the token ring port
		 identified by this entry."
	::= { swSysTokenRingPortEntry 4 }

swSysTokenRingPortType OBJECT-TYPE
	SYNTAX	INTEGER {
			rj45(1),
			other(2)
			}
	ACCESS	read-only
	STATUS	mandatory
	DESCRIPTION
			"Specific port type description for the token ring port
			 identified by this entry."
::= { swSysTokenRingPortEntry 5 }

swSysTokenRingPortMode OBJECT-TYPE
	SYNTAX	INTEGER	{
			station(1),
			lobe(2)
			}
	ACCESS	read-write
	STATUS	mandatory
	DESCRIPTION
			"The current mode of the port. The default mode (station) is
			used to connect a hub to the port.  Lobe mode is used to direct
			connect a Token Ring station into the port.  This selection
			can only be made on ports 1 and 2 of the module."
::= { swSysTokenRingPortEntry 6 }

swSysTokenRingPortSpeed OBJECT-TYPE
	SYNTAX	INTEGER {
			fourMegabit(1),
			sixteenMegabit(2),
			sixteenMegabitETR(3)
			}
	ACCESS	read-write
	STATUS	mandatory
	DESCRIPTION
			"The current speed of the port. The default speed is
			 sixteenMegabit."
::= { swSysTokenRingPortEntry 7 }

swSysTokenRingPortLineErrors OBJECT-TYPE
	SYNTAX  Counter
	ACCESS  read-only
	STATUS  mandatory
	DESCRIPTION
		"This counter is incremented when a frame
		or token is copied or repeated by a
		station, the E bit is zero in the frame
		or token and one of the following
		conditions exists: 1) there is a
		non-data bit (J or K bit) between the SD
		and the ED of the frame or token, or
		2) there is an FCS error in the frame."
::= { swSysTokenRingPortEntry 8 }

swSysTokenRingPortBurstErrors OBJECT-TYPE
	SYNTAX  Counter
	ACCESS  read-only
	STATUS  mandatory
	DESCRIPTION
				"This counter is incremented when a station
				detects the absence of transitions for five
				half-bit timers (burst-five error)."
::= {  swSysTokenRingPortEntry 9 }

swSysTokenRingPortACErrors OBJECT-TYPE
	SYNTAX  Counter
	ACCESS  read-only
	STATUS  mandatory
	DESCRIPTION
		"This counter is incremented when a station
		receives an AMP or SMP frame in which A is
		equal to C is equal to 0, and then receives
		another SMP frame with A is equal to C is
		equal to 0 without first receiving an AMP
		frame. It denotes a station that cannot set
		the AC bits properly."
::= { swSysTokenRingPortEntry 10 }

swSysTokenRingPortAbortTransErrors OBJECT-TYPE
	SYNTAX  Counter
	ACCESS  read-only
	STATUS  mandatory
	DESCRIPTION
		"This counter is incremented when a station
		transmits an abort delimiter while
		transmitting."
::= { swSysTokenRingPortEntry 11 }

swSysTokenRingPortInternalErrors OBJECT-TYPE
	SYNTAX  Counter
	ACCESS  read-only
	STATUS  mandatory
	DESCRIPTION
		"This counter is incremented when a station
		recognizes an internal error."
::= { swSysTokenRingPortEntry 12 }

swSysTokenRingPortLostFrameErrors OBJECT-TYPE
	SYNTAX  Counter
	ACCESS  read-only
	STATUS  mandatory
	DESCRIPTION
		"This counter is incremented when a station
		is transmitting and its TRR timer expires.
		This condition denotes a condition where a
		transmitting station in strip mode does not
		receive the trailer of the frame before the
		TRR timer goes off."
::= { swSysTokenRingPortEntry 13 }

swSysTokenRingPortReceiveCongestionErrors OBJECT-TYPE
	SYNTAX  Counter
	ACCESS  read-only
	STATUS  mandatory
	DESCRIPTION
		"This counter is incremented when a station
		recognizes a frame addressed to its
		specific address, but has no available
		buffer space indicating that the station
		is congested."
::= { swSysTokenRingPortEntry 14 }

swSysTokenRingPortFrameCopiedErrors OBJECT-TYPE
	SYNTAX  Counter
	ACCESS  read-only
	STATUS  mandatory
	DESCRIPTION
		"This counter is incremented when a station
		recognizes a frame addressed to its
		specific address and detects that the FS
		field A bits are set to 1 indicating a
		possible line hit or duplicate address."
::= { swSysTokenRingPortEntry 15 }

swSysTokenRingPortTokenErrors OBJECT-TYPE
	SYNTAX  Counter
	ACCESS  read-only
	STATUS  mandatory
	DESCRIPTION
		"This counter is incremented when a station
		acting as the active monitor recognizes an
		error condition that needs a token
		transmitted."
::= { swSysTokenRingPortEntry 16 }

swSysTokenRingPortSoftErrors OBJECT-TYPE
	SYNTAX  Counter
	ACCESS  read-only
	STATUS  mandatory
	DESCRIPTION
		"The number of Soft Errors the interface
		has detected. It directly corresponds to
		the number of Report Error MAC frames
		that this interface has transmitted.
		Soft Errors are those which are
		recoverable by the MAC layer protocols."
::= { swSysTokenRingPortEntry 17 }

swSysTokenRingPortHardErrors OBJECT-TYPE
	SYNTAX  Counter
	ACCESS  read-only
	STATUS  mandatory
	DESCRIPTION
		"The number of times this interface has
		detected an immediately recoverable
		fatal error.  It denotes the number of
		times this interface is either
		transmitting or receiving beacon MAC
		frames."
::= { swSysTokenRingPortEntry 18 }

swSysTokenRingPortTransmitBeacons OBJECT-TYPE
	SYNTAX  Counter
	ACCESS  read-only
	STATUS  mandatory
	DESCRIPTION
		"The number of times this interface has
		transmitted a beacon frame."
::= { swSysTokenRingPortEntry 19 }

swSysTokenRingPortLobeWires OBJECT-TYPE
	SYNTAX  Counter
	ACCESS  read-only
	STATUS  mandatory
	DESCRIPTION
		"The number of times the interface has
		detected an open or short circuit in the
		lobe data path.  The adapter will be closed
		when this condition occurs."
::= { swSysTokenRingPortEntry 20 }

swSysTokenRingPortRemoves OBJECT-TYPE
	SYNTAX  Counter
	ACCESS  read-only
	STATUS  mandatory
	DESCRIPTION
		"The number of times the interface has
		received a Remove Ring Station MAC frame
		request.  When this frame is received
		the interface will enter the close state."
::= { swSysTokenRingPortEntry 21 }

swSysTokenRingPortSingles OBJECT-TYPE
	SYNTAX  Counter
	ACCESS  read-only
	STATUS  mandatory
	DESCRIPTION
			"The number of times the interface has
			sensed that it is the only station on the
			ring.  This will happen if the interface
			is the first one up on a ring, or if
			there is a hardware problem."
::= { swSysTokenRingPortEntry 22 }


swSysTokenRingPortFreqErrors OBJECT-TYPE
	SYNTAX  Counter
	ACCESS  read-only
	STATUS  optional
	DESCRIPTION
		"The number of times the interface has
		detected that the frequency of the
		incoming signal differs from the expected
		frequency."
::= { swSysTokenRingPortEntry 23 }

swSysTokenRingPortRingStatus OBJECT-TYPE
	 SYNTAX  INTEGER
	 ACCESS  read-only
	 STATUS  mandatory
	 DESCRIPTION
				"The current interface status which can
				be used to diagnose fluctuating problems
				that can occur on token rings, after a
				station has successfully been added to
				the ring.
					Before an open is completed, this
				object has the value for the 'no status'
				condition.  This object is useful for
				debugging problems when the station
				can not even enter the ring.
					The object's value is a sum of
				values, one for each currently applicable
				condition.  The following values are
				defined for various conditions:
					 0 = No Problems detected
					32 = Ring Recovery
					64 = Single Station
				   256 = Remove Received
				   512 = reserved
				  1024 = Auto-Removal Error
				  2048 = Lobe Wire Fault
				  4096 = Transmit Beacon
				  8192 = Soft Error
				 16384 = Hard Error
				 32768 = Signal Loss
				131072 = no status, open not completed."
::= { swSysTokenRingPortEntry 24 }

--
-- swSysFtGroup file transfer mib
--	
-- The Switching Systems MIB file transfer table.
--

swSysFtTable OBJECT-TYPE
	SYNTAX SEQUENCE OF SwSysFtTableEntry
	ACCESS not-accessible
	STATUS mandatory
	DESCRIPTION
				"A list of entries which describe file transfers."
::= { swSysFtGroup 1 }

swSysFtTableEntry OBJECT-TYPE
	SYNTAX SwSysFtTableEntry
	ACCESS not-accessible
	STATUS mandatory
	DESCRIPTION
			"A description of a particular file transfer entry."
		INDEX { swSysFtIndex }
::= { swSysFtTable 1 }

SwSysFtTableEntry ::=
		SEQUENCE {
		swSysFtIndex				INTEGER,
		swSysFtDirection			INTEGER,
		swSysFtLocalStorageType		SwSysStorageType,
		swSysFtLocalResourceType	SwSysResourceType,
		swSysFtLocalResourceMask	SwSysResourceBitMask,
		swSysFtLocalResourceAttribute	OBJECT IDENTIFIER,
		swSysFtRemoteAddressType	SwSysAddressType,
		swSysFtRemoteAddress		OCTET STRING,
		swSysFtRemoteFileName		DisplayString,
		swSysFtRemoteUserName		DisplayString,
		swSysFtRemoteUserPassword	OCTET STRING,
		swSysFtForceTransfer		INTEGER,
		swSysFtBytesTransferred		Counter,
		swSysFtStatus				INTEGER,
		swSysFtDetailedStatus		OBJECT IDENTIFIER,
		swSysFtDetailedStatusString	DisplayString,
		swSysFtOwnerString			DisplayString,
		swSysFtRowStatus			RowStatus
		}

swSysFtIndex OBJECT-TYPE
	SYNTAX INTEGER (1..65535)
	ACCESS read-only
	STATUS mandatory
		DESCRIPTION
				"A unique index used to identifying this entry."
::= { swSysFtTableEntry 1 }

swSysFtDirection OBJECT-TYPE
	SYNTAX INTEGER {
			localToRemote(1),
			remoteToLocal(2)
		}
	ACCESS read-write
	STATUS mandatory
	DESCRIPTION
			"Specifies the direction of the file transfer."
	DEFVAL { remoteToLocal }    
::= { swSysFtTableEntry 2 }

swSysFtLocalStorageType OBJECT-TYPE
	SYNTAX SwSysStorageType
	ACCESS read-write
	STATUS mandatory
	DESCRIPTION
			"The type of storage on the local system to be
			used as the source/destination for the file transfer."
	DEFVAL { 3 }   --storageFlashMemory     
::= { swSysFtTableEntry 3 }

swSysFtLocalResourceType OBJECT-TYPE
	SYNTAX SwSysResourceType
	ACCESS read-write
	STATUS mandatory
	DESCRIPTION
			"The type of resource on the local system to be
			used as the source/destination for the file transfer."
	DEFVAL { 2 }    -- resourceSystem
::= { swSysFtTableEntry 4 }

swSysFtLocalResourceMask OBJECT-TYPE
	SYNTAX SwSysResourceBitMask
	ACCESS read-write
	STATUS mandatory
	DESCRIPTION
			"The indices of the resources on the local system to
			be used as the source/destination for the file transfer.
			The type of resource to which these indices apply is
			specified by the corresponding value of
			swSysFtLocalResourceType. If resourceBridge is used,
			swSysFtLocalResourceMask indicates the bridge slot
			number the filter code will be downloaded.
			For instance, swSysFtLocalResourceMask value of 0x03
			indicates bridge slot number 1 and 2."
	DEFVAL { '80'h }    
::= { swSysFtTableEntry 5 }

swSysFtLocalResourceAttribute OBJECT-TYPE
	SYNTAX OBJECT IDENTIFIER
	ACCESS read-write
	STATUS mandatory
	DESCRIPTION
			"An identifier which specifies the particular resource
			attribute on the local system which is the source/destination
			of the file transfer. The resource(s) to which this attribute
			applies is specified by the corresponding values of
			swSysFtLocalResourceType and swSysFtLocalResourceMask."
	DEFVAL { swSysFtSystemOperationalCode }    
::= { swSysFtTableEntry 6 }

swSysFtRemoteAddressType OBJECT-TYPE
	SYNTAX SwSysAddressType
	ACCESS read-write
	STATUS mandatory
	DESCRIPTION
			"The type of address which is specified by the corresponding
			value of swSysFtRemoteAddress."
DEFVAL { 2 }  --addrIp    
::= { swSysFtTableEntry 7 }

swSysFtRemoteAddress OBJECT-TYPE
	SYNTAX OCTET STRING (SIZE (0..32))
	ACCESS read-write	
	STATUS mandatory
	DESCRIPTION
				"The address of the source/destination file on the remote
				system."
	::= { swSysFtTableEntry 8 }

swSysFtRemoteFileName OBJECT-TYPE
	SYNTAX DisplayString (SIZE (0..128))
	ACCESS read-write
	STATUS mandatory
	DESCRIPTION
				"The full path name of the source/destination file on the
				remote system."
::= { swSysFtTableEntry 9 }

swSysFtRemoteUserName OBJECT-TYPE
	SYNTAX DisplayString (SIZE (0..128))
   	ACCESS read-write
   	STATUS mandatory
   	DESCRIPTION
          		"The user name to be used when requesting the file transfer
           		to/from the remote system."
::= { swSysFtTableEntry 10 }

swSysFtRemoteUserPassword OBJECT-TYPE
	SYNTAX OCTET STRING (SIZE (0..128))
	ACCESS read-write
	STATUS mandatory
	DESCRIPTION
		"The password to be used when requesting the file transfer
		to/from the remote system. When read, this object returns
		a zero length string. Note that, for security reasons,
		some ftp servers may insist on a non-zero length user password."
::= { swSysFtTableEntry 11 }

swSysFtForceTransfer OBJECT-TYPE
	SYNTAX INTEGER {
		true(1),
		false(2)
	}
	ACCESS read-write
	STATUS mandatory
	DESCRIPTION
		"Setting this object to true makes the agent ignore
		non-fatal (i.e. version/id mismatch) errors encountered 
		during a file transfer request."
	DEFVAL { false }    
::= { swSysFtTableEntry 12 }

swSysFtBytesTransferred OBJECT-TYPE
	SYNTAX Counter
	ACCESS read-only
	STATUS mandatory
	DESCRIPTION
		"The number of bytes successfully transferred."
::= { swSysFtTableEntry 13 }

swSysFtStatus OBJECT-TYPE
	SYNTAX INTEGER {
		statusSuccessfulCompletion(1),
		statusInProgress(2),
		statusLocalInvalid(3),
		statusRemoteInvalid(4),
		statusRemoteUnreachable(5),
		statusUserAuthFailed(6),
		statusFileNotFound(7),
		statusFileTooBig(8),
		statusFileIncompatible(9),
		statusError(10)
	}
	ACCESS read-only
	STATUS mandatory
	DESCRIPTION
		"The status of the file transfer."
::= { swSysFtTableEntry 14 }

swSysFtDetailedStatus OBJECT-TYPE
	SYNTAX OBJECT IDENTIFIER
	ACCESS read-only
	STATUS mandatory
	DESCRIPTION
		"Detailed status for the transfer for the particular 
		local resource attribute specified by the corresponding
		values of swSysFtLocalStorageType, swSysFtLocalResourceType,
		swSysFtLocalResourceMask, and swSysFtLocalResourceAttribute.

		Note that this object is only valid in the case where
		swSysFtStatus indicates an error."
::= { swSysFtTableEntry 15 }

swSysFtDetailedStatusString OBJECT-TYPE
	SYNTAX DisplayString
	ACCESS read-only
	STATUS mandatory
	DESCRIPTION
		"Detailed status description for the requested transfer."
::= { swSysFtTableEntry 16 }

swSysFtOwnerString OBJECT-TYPE
	SYNTAX DisplayString (SIZE (0..128))
	ACCESS read-write
	STATUS mandatory
	DESCRIPTION
		"A string describing the creator/owner of this entry."
::= { swSysFtTableEntry 17 }

swSysFtRowStatus OBJECT-TYPE
	SYNTAX RowStatus
	ACCESS read-write
	STATUS mandatory
	DESCRIPTION
		"The row status object controls the creation/deletion of rows
		in this table. Its semantics are the same as those for the
		RowStatus textual convention specified for SNMPv2. 

		Setting this object to createAndGo(4) is not allowed.

		Setting this object to createAndWait(5) causes an entry
		to be created with swSysFtRowStatus value of notReady(3).
	
		Setting this object to active(1) causes the transfer to
		start for the given row. Objects within the row cannot 
		be modified once a row has been set to active(1),

		Setting this object to destroy(6) causes the corresponding
		row to be deleted.
		
		Note that a request to set a row to notInService(2) or 
		destroy(6) will fail if the current rowStatus value is active(1)
		(i.e. a file transfer is currently in progress). This is
		necessary since aborting a file transfer may leave the
		system in an inconsistent state.

		Note that, currently, only a single instance of a row 
		can be created in this table."
::= { swSysFtTableEntry 18 }


 -- File transfer resource attributes.

swSysFtResourceAttributes OBJECT IDENTIFIER ::= { swSysFtGroup 2 }


-- File transfer resource attributes groups.

swSysFtSystemAttributes        OBJECT IDENTIFIER ::= { swSysFtResourceAttributes 1 }


-- File transfer system resource attributes.

swSysFtSystemOperationalCode  OBJECT IDENTIFIER ::= { swSysFtSystemAttributes 1 }
swSysFtSystemConfiguration    OBJECT IDENTIFIER ::= { swSysFtSystemAttributes 2 }

-- File transfer bridge resource attributes

swSysFtSystemBridgeFilterCode OBJECT IDENTIFIER ::= { swSysFtSystemAttributes 3 }

-- File transfer detailed resource status.

swSysFtDetailedResourceStatus OBJECT IDENTIFIER ::= { swSysFtGroup 3 }


-- File transfer detailed resource status groups.

swSysFtSystemDetailedStatus   OBJECT IDENTIFIER ::= { swSysFtDetailedResourceStatus 1 }

-- File transfer system detailed status.

swSysFtSysStatusNotApplicable OBJECT IDENTIFIER ::= { swSysFtSystemDetailedStatus 1 }
swSysFtSysStatusNoImageLabel  OBJECT IDENTIFIER ::= { swSysFtSystemDetailedStatus 2 }
swSysFtSysStatusConfigIdMismatch OBJECT IDENTIFIER ::= { swSysFtSystemDetailedStatus 3 }
swSysFtSysStatusChecksumError OBJECT IDENTIFIER ::= { swSysFtSystemDetailedStatus 4 }
swSysFtSysStatusNvRamError    OBJECT IDENTIFIER ::= { swSysFtSystemDetailedStatus 5 }
swSysFtSysStatusFlashError    OBJECT IDENTIFIER ::= { swSysFtSystemDetailedStatus 6 }
swSysFtSysStatusNoRoom        OBJECT IDENTIFIER ::= { swSysFtSystemDetailedStatus 7 }

-- File transfer bridge detailed status

swSysFtSysBridgeFilterNotApplicable   OBJECT IDENTIFIER ::= { swSysFtSystemDetailedStatus 8 }
swSysFtSysBridgeFilterSyntaxError     OBJECT IDENTIFIER ::= { swSysFtSystemDetailedStatus 9 }
swSysFtSysBridgeFilterdownloadError   OBJECT IDENTIFIER ::= { swSysFtSystemDetailedStatus 10 }
swSysFtSysBridgeFilterNoRoom          OBJECT IDENTIFIER ::= { swSysFtSystemDetailedStatus 11 }

--
-- IP Group
--

-- The swSysIpBaseGroup is resreved for future use

swSysIpBaseGroup			OBJECT IDENTIFIER ::= { swSysIpGroup 1 }
swSysIpInterfaceGroup		OBJECT IDENTIFIER ::= { swSysIpGroup 2 } 

swSysIpInterfaceCount OBJECT-TYPE 
	SYNTAX  INTEGER
	ACCESS	read-only
	STATUS	mandatory
	DESCRIPTION
		"A count of the total number of IP interfaces configured."
::= { swSysIpInterfaceGroup 1 }

swSysIpInterfaceTable OBJECT-TYPE
	SYNTAX	SEQUENCE OF SwSysIpInterfaceEntry
	ACCESS	not-accessible
	STATUS	mandatory
	DESCRIPTION
		"A list of configured IP interfaces."
::= { swSysIpInterfaceGroup 2 }

swSysIpInterfaceEntry OBJECT-TYPE
	SYNTAX	SwSysIpInterfaceEntry
	ACCESS	not-accessible	
	STATUS	mandatory
	DESCRIPTION
		"An individual IP interface."
	INDEX	{ swSysIpInterfaceIpStackIndex, swSysIpInterfaceAddr, swSysIpInterfaceNetMask }
::= { swSysIpInterfaceTable 1 }

SwSysIpInterfaceEntry	::= SEQUENCE {
	swSysIpInterfaceIpStackIndex  INTEGER,
	swSysIpInterfaceAddr		  IpAddress,
	swSysIpInterfaceNetMask		  IpAddress,
	swSysIpInterfaceIndex		  INTEGER,
	swSysIpInterfaceBcastAddr	  INTEGER,
	swSysIpInterfaceCost		  INTEGER,
	swSysIpInterfaceStatus        RowStatus
}

swSysIpInterfaceIpStackIndex OBJECT-TYPE
	SYNTAX	INTEGER
	ACCESS	read-only
	STATUS	mandatory
	DESCRIPTION
			"The index of the IP stack identified by this entry
			relative to this agent."
::= { swSysIpInterfaceEntry 1 }

swSysIpInterfaceAddr OBJECT-TYPE
	SYNTAX	IpAddress	
	ACCESS	read-only
	STATUS	mandatory
	DESCRIPTION
		"The IP address of this entry within the IP stack identified
		within this entry."
::= { swSysIpInterfaceEntry 2 }

swSysIpInterfaceNetMask OBJECT-TYPE
	SYNTAX	IpAddress
	ACCESS	read-only
	STATUS	mandatory
	DESCRIPTION
		"The subnet mask associated with this IP interface.  The value of the mask 
		is an IP address with all the network bits set to 1 and all the host bits
		set to 0."
::= { swSysIpInterfaceEntry 3 }

swSysIpInterfaceIndex OBJECT-TYPE
	SYNTAX	INTEGER	
	ACCESS	read-write
	STATUS	mandatory
	DESCRIPTION
		"The index value which uniquely identifies the interface
		to which this entry is applicable.  lspIPInterfaceIndex maps to
		the same interface as identified by ifIndex in the ifTable.  Currently,
		this object can not be modified after creation."
	::= { swSysIpInterfaceEntry 4 }

swSysIpInterfaceBcastAddr OBJECT-TYPE
	SYNTAX	INTEGER
	ACCESS	read-write
	STATUS	mandatory
	DESCRIPTION
		"This object represents the value of the least significant
		bit of this entry's direct broadcast address.  For example,
		a value of one signifies that the host portion of the broadcast
		address is set to all ones."
	DEFVAL	{ 1 }
::= { swSysIpInterfaceEntry 5 }

swSysIpInterfaceCost OBJECT-TYPE
	SYNTAX	INTEGER ( 1..15 )
	ACCESS	read-write
	STATUS	mandatory
	DESCRIPTION
		"The route cost metric used for this entry."
	DEFVAL	{ 1 }
::= { swSysIpInterfaceEntry 6 }

swSysIpInterfaceStatus OBJECT-TYPE
	SYNTAX  RowStatus	
	ACCESS	read-write
	STATUS	mandatory
	DESCRIPTION
		"The status column for this IP interface.  This object can be set to:
		createAndGo(4)
		destroy(6)

		The following value may be read:
		active(1)

		Setting this object to createAndGo(4) causes the agent to
		attempt to create and commit the row based on the contents
		of the object in the row.  If all necessary information is
		present in the row and the values are acceptable to the
		agent, the agent will change the status to active(1).  If any
		of the necessary objects are not available the agent
		will reject the request.

		Other objects in this row entry can be individually modified
		while the row status is active(1).

		Setting this object to destroy(6) will remove this entry."
::= { swSysIpInterfaceEntry 7 }

-- 
-- The IPX Group
--

swSysIpxBaseGroup		OBJECT IDENTIFIER ::= { swSysIpxGroup 1 }
swSysIpxInterfaceGroup	OBJECT IDENTIFIER ::= { swSysIpxGroup 2 }

swSysIpxInterfaceCount OBJECT-TYPE
	SYNTAX	INTEGER
	ACCESS	read-only
	STATUS	mandatory
	DESCRIPTION
		"A count of the total number of IPX interfaces configured."
::= { swSysIpxInterfaceGroup 1 }

swSysIpxInterfaceTable OBJECT-TYPE
	SYNTAX	SEQUENCE OF SwSysIpxInterfaceEntry
	ACCESS	not-accessible
	STATUS	mandatory
	DESCRIPTION
		"A list of configured IPX interfaces."
::= { swSysIpxInterfaceGroup 2 }

swSysIpxInterfaceEntry OBJECT-TYPE
	SYNTAX	SwSysIpxInterfaceEntry
	ACCESS	not-accessible
	STATUS	mandatory
	DESCRIPTION
		"An individual IPX interface."
	INDEX	{ swSysIpxInterfaceIpxStackIndex, swSysIpxInterfaceNetNumber }
::= { swSysIpxInterfaceTable 1 }

SwSysIpxInterfaceEntry ::= SEQUENCE {
	swSysIpxInterfaceIpxStackIndex  INTEGER,
	swSysIpxInterfaceNetNumber	    IpxNetworkNumber,
	swSysIpxInterfaceIfIndex		INTEGER,
	swSysIpxInterfaceCost		    INTEGER,
	swSysIpxInterfaceFrameType	    INTEGER,
	swSysIpxInterfaceStatus		    RowStatus
}

swSysIpxInterfaceIpxStackIndex OBJECT-TYPE
	SYNTAX	INTEGER
	ACCESS	read-only
	STATUS	mandatory
	DESCRIPTION
			"The index of the IPX stack identified by this entry
			relative to this agent."
::= { swSysIpxInterfaceEntry 1 }

swSysIpxInterfaceNetNumber OBJECT-TYPE
	SYNTAX	IpxNetworkNumber
	ACCESS	read-only
	STATUS	mandatory
	DESCRIPTION
		"The IPX Network Number of this entry."
::= { swSysIpxInterfaceEntry 2 }

swSysIpxInterfaceIfIndex OBJECT-TYPE
	SYNTAX	INTEGER
	ACCESS	read-write
	STATUS	mandatory
	DESCRIPTION
		"The ifIndex of the virtual interface that this IPX interface is
		is configured over.  The swSysIpxInterfaceIfIndex identifies a
		virtual interface, for example a VLAN, that this local address 
		is associated with for purposes of routing or network management." 
::= { swSysIpxInterfaceEntry 3 }

swSysIpxInterfaceCost OBJECT-TYPE
	SYNTAX	INTEGER
	ACCESS	read-write
	STATUS	mandatory
	DESCRIPTION
		"The cost associated with the IPX address of this entry."
	DEFVAL	{ 1 }
::= { swSysIpxInterfaceEntry 4 }	

swSysIpxInterfaceFrameType OBJECT-TYPE
	SYNTAX	INTEGER {
			frame-ethernetII(1),
			frame-802-2(2),
			frame-802-3-Raw(3),
			frame-SNAP(4)
		}
	ACCESS	read-write
	STATUS mandatory
	DESCRIPTION
		"The frame format used for routing frames on this IPX interface.  The framing
		formats are for ethernet ports.  There are two frame formats for FDDI ports:
		802.2 and FDDI SNAP.  The correct FDDI format is automatically chosen if 
		this interface is associated with a VLAN interface that contains both ethernet
		and FDDI ports.  If the VLAN interface is an FDDI port, than the only
		values that can be written to this object are: frame-802-2(2) and
		frame-SNAP(4). " 
::= { swSysIpxInterfaceEntry 5 }

swSysIpxInterfaceStatus OBJECT-TYPE
	SYNTAX  RowStatus	
	ACCESS	read-write
	STATUS	mandatory
	DESCRIPTION
		"The status column for this IPX interface.  This OBJECT can be set to:
		createAndGo(4)
		destroy(6)

		The following value may be read:
		active(1)

		Setting this object ot createAndGo(4) causes the agent to
		attempt to create and commit the row based on the contents
		of the object in the row.  If all necessary information is
		present in the row and the values are acceptable to the
		agent, the agent will change the status to active(1).  If any
		of the necessary objects are not available the agent
		will reject the request.

		Other objects in this row entry can be individually modified
		while the row status is active(1).

		Setting this object to destroy(6) will remove this entry."
::= { swSysIpxInterfaceEntry 6 }

--
-- The Apple Talk Group
--

swSysAppleTalkBaseGroup         OBJECT IDENTIFIER ::= { swSysAppleTalkGroup 1 }
swSysAppleTalkInterfaceGroup    OBJECT IDENTIFIER ::= { swSysAppleTalkGroup 2 }

-- The AppleTalkInterace Group
--
-- Implementation of this group is mandatory for all entities
-- that implement AppleTalk ports

swSysAtInterfaceCount OBJECT-TYPE 
	SYNTAX	INTEGER
	ACCESS	read-only
	STATUS	mandatory
	DESCRIPTION
		"A count of the total number of AppleTalk interfaces configured."
::= { swSysAppleTalkInterfaceGroup 1 }

swSysAtInterfaceTable OBJECT-TYPE
	SYNTAX SEQUENCE OF SwSysAtInterfaceEntry
	ACCESS not-accessible
	STATUS mandatory
	DESCRIPTION
		"A list of AppleTalk ports for this entity."
::= { swSysAppleTalkInterfaceGroup 2 }

swSysAtInterfaceEntry OBJECT-TYPE
	SYNTAX SwSysAtInterfaceEntry
	ACCESS not-accessible
	STATUS mandatory
	DESCRIPTION
		"An individual appletalk interface entry.
		Appletalk entries with row status of active(1)
		cannot be modified but must set to destroy(6)
		and recreated."
	INDEX { swSysAtInterfaceAtStackIndex, swSysAtInterfaceIfIndex }
::= { swSysAtInterfaceTable 1 }

SwSysAtInterfaceEntry ::= SEQUENCE {
		swSysAtInterfaceAtStackIndex       	INTEGER,
		swSysAtInterfaceNetAddress         	DdpNodeAddress,
		swSysAtInterfaceType               	INTEGER,
		swSysAtInterfaceNetStart           	ATNetworkNumber,
		swSysAtInterfaceNetEnd             	ATNetworkNumber,
		swSysAtInterfaceZoneDefault  	    ATName,
		swSysAtInterfaceZone1               ATName,
		swSysAtInterfaceZone2               ATName,
		swSysAtInterfaceZone3               ATName,
		swSysAtInterfaceZone4               ATName,
		swSysAtInterfaceZone5               ATName,
		swSysAtInterfaceZone6               ATName,
		swSysAtInterfaceZone7               ATName,
		swSysAtInterfaceZone8               ATName,
		swSysAtInterfaceZone9               ATName,
		swSysAtInterfaceZone10              ATName,
		swSysAtInterfaceZone11              ATName,
		swSysAtInterfaceZone12              ATName,
		swSysAtInterfaceZone13              ATName,
		swSysAtInterfaceZone14              ATName,
		swSysAtInterfaceZone15              ATName,
		swSysAtInterfaceIfIndex		        INTEGER,  
		swSysAtInterfaceState              	INTEGER,
		swSysAtInterfaceStatus            	RowStatus
}

swSysAtInterfaceAtStackIndex OBJECT-TYPE
	SYNTAX	INTEGER
	ACCESS	read-write
	STATUS	mandatory
	DESCRIPTION
		"The index of the Appletalk stack identified by this entry
		relative to this agent.

		Setting of this object is required for all interface creations."
::= { swSysAtInterfaceEntry 1 }

swSysAtInterfaceNetAddress OBJECT-TYPE
	SYNTAX DdpNodeAddress
	ACCESS read-only
	STATUS mandatory
	DESCRIPTION
		"The AppleTalk network address configured for this
		port."
::= { swSysAtInterfaceEntry 2 }

swSysAtInterfaceType OBJECT-TYPE
	SYNTAX INTEGER {
					seedInterface(1), 
					nonseedInterface(2)
				   }
	ACCESS read-write
	STATUS mandatory
	DESCRIPTION
		"The type of interface that is configured for this port.
		Setting of this object is required for all interface creations."
::= { swSysAtInterfaceEntry 3 }

swSysAtInterfaceNetStart OBJECT-TYPE
	SYNTAX ATNetworkNumber
	ACCESS read-write
	STATUS mandatory
	DESCRIPTION
		"The first AppleTalk network address in the range
		configured for this port.  If this port is not a
		native AppleTalk port, this object shall have the
		value of two octets of zero.
		Setting of this object is mandatory only for interfaces
		with swSysAtInterfaceType equal to seedInterface(1)."
::= { swSysAtInterfaceEntry 4 }

swSysAtInterfaceNetEnd OBJECT-TYPE
	SYNTAX ATNetworkNumber
	ACCESS read-write
	STATUS mandatory
	DESCRIPTION
		"The last AppleTalk network address in the range
		configured for this port.  If the network to which
		this AppleTalk port is connected is a non-extended
		network, or if it is not a native AppleTalk port,
		the value for swSysAtInterfaceNetEnd shall be two octets of
		zero.

		Setting of this object is mandatory only for
		interfaces with swSysAtInterfaceType equal to seedInterface(1)."
::= { swSysAtInterfaceEntry 5 }


swSysAtInterfaceZoneDefault OBJECT-TYPE
	SYNTAX ATName
	ACCESS read-write
	STATUS mandatory
	DESCRIPTION
		"The name of the default zone for this port.  If
		this port only has one zone, that zone is
		represented here.

		Setting of this object is mandatory for
		interfaces with swSysAtInterfaceType equal to seedInterface(1)."
::= { swSysAtInterfaceEntry 6 }

swSysAtInterfaceZone1 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 7 }

swSysAtInterfaceZone2 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 8 }

swSysAtInterfaceZone3 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 9 }

swSysAtInterfaceZone4 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 10 }

swSysAtInterfaceZone5 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 11 }

swSysAtInterfaceZone6 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 12 }

swSysAtInterfaceZone7 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 13 }

swSysAtInterfaceZone8 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 14 }

swSysAtInterfaceZone9 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 15 }

swSysAtInterfaceZone10 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 16 }

swSysAtInterfaceZone11 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 17 }

swSysAtInterfaceZone12 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 18 }

swSysAtInterfaceZone13 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 19 }

swSysAtInterfaceZone14 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 20 }

swSysAtInterfaceZone15 OBJECT-TYPE
	SYNTAX ATName
	ACCESS read-write
	STATUS mandatory
	DESCRIPTION
		"Zone name in this entry's zone list.

		This object may only only be set for interfaces
		with swSysAtInterfaceType equal to seedInterface(1)."
::= { swSysAtInterfaceEntry 21 }


swSysAtInterfaceIfIndex OBJECT-TYPE
	SYNTAX INTEGER
	ACCESS read-write
	STATUS mandatory
	DESCRIPTION
		"The  interface associated with this
		AppleTalk port.  The interface identified by a
		particular value of this index is the same interface
		as identified by the same value of ifIndex in the ifTable.

		Setting of this object is required for all interface creations."
::= { swSysAtInterfaceEntry 22 }

swSysAtInterfaceState OBJECT-TYPE
	SYNTAX INTEGER {
					unused(1),
					initialize(2),
					terminate(3),
					failed(4),
					down(5),
					validate(6),
					discover(7),
					waiting(8),
					enabled(9)
					}
	ACCESS read-only
	STATUS mandatory
	DESCRIPTION
				"The current state of the appletalk interface."
::= { swSysAtInterfaceEntry 23 }

swSysAtInterfaceStatus OBJECT-TYPE
	SYNTAX RowStatus
	ACCESS read-write
	STATUS mandatory
	DESCRIPTION
		"The status column for this IP interface.  This object can be set to:
		createAndGo(4)
		createAndWait(5)
		destroy(6)

		The following value may be read:
		active(1)
		notInService(2)

		Setting this object to createAndGo(4) causes the agent to
		attempt to create and commit the row based on the contents
		of the object in the row.  If all necessary information is
		present in the row and the values are acceptable to the
		agent, the agent will change the status to active(1).  If any
		of the necessary objects are not available the agent
		will reject the request.

		Setting this object to createAndWait(5) causes the agent to
		create an entry which has the value notInService(2).  Only three
		notInService(2) entries are permitted at any one time.
		Setting a row with status notInService(2) to active(1) 
		will cause this entry to change to active(1) if the
		appropriate columns have been set.

		Setting this object to destroy(6) will remove this entry."
::= { swSysAtInterfaceEntry 24 }


-- The SwSys Module Card group.  Implementation of this
-- group is mandatory for agents which manage system resources for
-- systems with modular components.

swSysModuleCardCount OBJECT-TYPE
	SYNTAX  INTEGER
	ACCESS  read-only
	STATUS  mandatory
	DESCRIPTION
		"The current count of module components present in the
		system."
::= { swSysModuleCardGroup 1 }


-- The SwSys Module Card information table.

swSysModuleCardInfoTable OBJECT-TYPE
	SYNTAX  SEQUENCE OF SwSysModuleCardInfoEntry
	ACCESS  not-accessible
	STATUS  mandatory
	DESCRIPTION
		"A list of module card information entries.  A single entry exists in
		this list for each modular component in the system."
::= { swSysModuleCardGroup 2 }

swSysModuleCardInfoEntry OBJECT-TYPE
	SYNTAX  SwSysModuleCardInfoEntry
	ACCESS  not-accessible
	STATUS  mandatory
	DESCRIPTION
			"A module card info entry contains information about a
			particular modular component within the system."
	INDEX   { swSysModuleCardInfoIndex }
::= { swSysModuleCardInfoTable 1 }

SwSysModuleCardInfoEntry ::=
	SEQUENCE {
		swSysModuleCardInfoIndex
			INTEGER,
		swSysModuleCardInfoFamily
			INTEGER,
		swSysModuleCardInfoGenericType
			INTEGER,
		swSysModuleCardInfoSpecificType
			INTEGER,
		swSysModuleCardInfoPartNumber
			DisplayString,
		swSysModuleCardInfoManufacturingDate
			DisplayString,
		swSysModuleCardInfoModuleSerialNumber
			DisplayString,
		swSysModuleCardInfoTLASerialNumber
			DisplayString,
		swSysModuleCardInfo3CNumber
			DisplayString,
		swSysModuleCardInfoICTTestStatus
			INTEGER,
		swSysModuleCardInfoICTTestRevision
			DisplayString,
		swSysModuleCardInfoSystemTestStatus
			INTEGER,
		swSysModuleCardInfoFunctionalTestStatus
			INTEGER,
		swSysModuleCardInfoFunctionalTestRevision
			DisplayString,
		swSysModuleCardInfoBoardRevision
			DisplayString,
		swSysModuleCardInfoRuntimeHours
			INTEGER
	}

swSysModuleCardInfoIndex OBJECT-TYPE
	SYNTAX  INTEGER
	ACCESS  read-only
	STATUS  mandatory
	DESCRIPTION
			"The index of the modular component identified by this
			entry."
::= { swSysModuleCardInfoEntry 1 }

swSysModuleCardInfoFamily OBJECT-TYPE
	SYNTAX  INTEGER {
				coreBuilder3500(1),
				superStack7000(2),
				superStack9000(3)
			}
	ACCESS  read-only
	STATUS  mandatory
	DESCRIPTION
			"The family code for this module."
::= { swSysModuleCardInfoEntry 2 }

swSysModuleCardInfoGenericType OBJECT-TYPE
	SYNTAX  INTEGER {
				backplaneOrMotherboard(1),
				processorBoard(2),
				enet10MbAnd100MbAdaptor(3),
				enet1GbAdaptor(4),
				fddiAdaptor(5),
				atmAdaptor(6)
			}

	ACCESS  read-only
	STATUS  mandatory
	DESCRIPTION
			"The generic type code for this module."
::= { swSysModuleCardInfoEntry 3 }

swSysModuleCardInfoSpecificType OBJECT-TYPE
	SYNTAX  INTEGER {
				notApplicable(1),
				atmSonetOC3Fiber(161),
				atmSonetOC12Fiber(162),
				atmSonetOC3Copper(163),
				atmSonetOC12Copper(164),

				enet1Gb850nMMultimodeFiber(177),
				enet1Gb1300nMFiber(178),
				enet1GbCoax(179),
				enet1Gb1000BaseTx(180),

				enet100Mb100BaseTx(225),
				enet100Mb100BaseT2(226),
				enet100Mb100BaseFx(227),
				enet100Mb100BaseT4(228),
				enet100Mb100BaseTxSTP(229),

				fddiMultimodeSC(241),
				fddiSingleModeSC(242),
				fddiCopperUTP(243),
				fddiCopperSTP(244)
			}
	ACCESS  read-only
	STATUS  mandatory
	DESCRIPTION
			"The specific type code for this module."
::= { swSysModuleCardInfoEntry 4 }

swSysModuleCardInfoPartNumber OBJECT-TYPE
	SYNTAX  DisplayString
	ACCESS  read-only
	STATUS  mandatory
	DESCRIPTION
			"The specific part number for this module."
::= { swSysModuleCardInfoEntry 5 }

swSysModuleCardInfoManufacturingDate OBJECT-TYPE
	SYNTAX  DisplayString
	ACCESS  read-only
	STATUS  mandatory
	DESCRIPTION
			"The date that this module was manufactured in the
			format mm/dd/yyyy."
::= { swSysModuleCardInfoEntry 6 }

swSysModuleCardInfoModuleSerialNumber OBJECT-TYPE
	SYNTAX  DisplayString (SIZE(12))
	ACCESS  read-only
	STATUS  mandatory
	DESCRIPTION
			"3Com serial number."
::= { swSysModuleCardInfoEntry 7 }

swSysModuleCardInfoTLASerialNumber OBJECT-TYPE
	SYNTAX  DisplayString (SIZE(12))
	ACCESS  read-only
	STATUS  mandatory
	DESCRIPTION
			"TOP level assembly serial number for boards with
	non-removable daughter cards. Null string for
	all other board types."
::= { swSysModuleCardInfoEntry 8 }

swSysModuleCardInfo3CNumber OBJECT-TYPE
	SYNTAX  DisplayString (SIZE(10))
	ACCESS  read-only
	STATUS  mandatory
	DESCRIPTION
			"On a backplane or non-removable module this is the
			3C number of the chassis. On a removable module this
			is the 3C number of the module."
::= { swSysModuleCardInfoEntry 9 }

swSysModuleCardInfoICTTestStatus OBJECT-TYPE
	SYNTAX  INTEGER
	ACCESS  read-only
	STATUS  mandatory
	DESCRIPTION
			"1 equals test passed, or greater than 1 identifies the
			test number failure (0 or FF indicates field yet not
			written)."
::= { swSysModuleCardInfoEntry 10 }

swSysModuleCardInfoICTTestRevision OBJECT-TYPE
	SYNTAX  DisplayString
	ACCESS  read-only
	STATUS  mandatory
	DESCRIPTION
			"Manufacturing ATE test revision number (XX.XX)."
::= { swSysModuleCardInfoEntry 11 }

swSysModuleCardInfoSystemTestStatus OBJECT-TYPE
	SYNTAX  INTEGER
	ACCESS  read-only
	STATUS  mandatory
	DESCRIPTION
			"1 equals test passed, or greater than 1 identifies the
			test number failure (0 or FF indicates field yet not
			written)."
::= { swSysModuleCardInfoEntry 12 }

swSysModuleCardInfoFunctionalTestStatus OBJECT-TYPE
	SYNTAX  INTEGER
	ACCESS  read-only
	STATUS  mandatory
	DESCRIPTION
			"1 equals test passed, or greater than 1 identifies the
			test number failure (0 or FF indicates field yet not
			written)."
::= { swSysModuleCardInfoEntry 13 }

swSysModuleCardInfoFunctionalTestRevision OBJECT-TYPE
	SYNTAX  DisplayString
	ACCESS  read-only
	STATUS  mandatory
	DESCRIPTION
			"Manufacturing functional test revision number (XX.XX)."
::= { swSysModuleCardInfoEntry 14 }

swSysModuleCardInfoBoardRevision OBJECT-TYPE
	SYNTAX  DisplayString
	ACCESS  read-only
	STATUS  mandatory
	DESCRIPTION
			"Board revision code. "
::= { swSysModuleCardInfoEntry 15 }

swSysModuleCardInfoRuntimeHours OBJECT-TYPE
	SYNTAX  INTEGER
	ACCESS  read-only
	STATUS  mandatory
	DESCRIPTION
			"A total count of the number of hours this module has
			been in operation."
::= { swSysModuleCardInfoEntry 16 }



-- The SwSys Diagnostics group.  Implementation of this
-- group is mandatory for agents which manage system resources for
-- systems with modular components.


-- The SwSys Diagnostics event information table.  Each PI-ROM maintains
-- its own last diagnostic event information, hence they are tabularized
-- separately.

swSysDiagnosticsInfoTable OBJECT-TYPE
	SYNTAX  SEQUENCE OF SwSysDiagnosticsInfoEntry
	ACCESS  not-accessible
	STATUS  mandatory
	DESCRIPTION
			"A list of module card information entries.  A single entry exists in
			this list for each modular component in the system."
::= { swSysDiagnosticsGroup 1 }

swSysDiagnosticsInfoEntry OBJECT-TYPE
	SYNTAX  SwSysDiagnosticsInfoEntry
	ACCESS  not-accessible
	STATUS  mandatory
	DESCRIPTION
			"A diagnostics info entry contains information about a particular
			 diagnostics event on a modular component within the system."
	INDEX   { swSysDiagnosticsInfoIndex }
::= { swSysDiagnosticsInfoTable 1 }

SwSysDiagnosticsInfoEntry ::=
	SEQUENCE {
		swSysDiagnosticsInfoIndex
			INTEGER,
		swSysDiagnosticsInfoPOVDiagnosticsRevision
			DisplayString,
		swSysDiagnosticsInfoExtendedDiagnosticsRevision
			DisplayString,
		swSysDiagnosticsInfoDiagnosticFailureCode
			DisplayString,
		swSysDiagnosticsInfoDiagnosticFailureDateTime
			DisplayString,
		swSysDiagnosticsInfoDiagnosticFailureSlotNumber
			INTEGER,
		swSysDiagnosticsInfoDiagnosticFailureCounter
			INTEGER,
		swSysDiagnosticsInfoDiagnosticFieldDOACounter
			INTEGER
	}

swSysDiagnosticsInfoIndex OBJECT-TYPE
	SYNTAX  INTEGER
	ACCESS  read-only
	STATUS  mandatory
	DESCRIPTION
			"The index of the diagnostics modular component identified by this
			 entry."
::= { swSysDiagnosticsInfoEntry 1 }

swSysDiagnosticsInfoPOVDiagnosticsRevision OBJECT-TYPE
	SYNTAX  DisplayString
	ACCESS  read-only
	STATUS  mandatory
	DESCRIPTION
		"The revision of the POV (power on verification) diagnostics
		 software at the most recent failure."
::= { swSysDiagnosticsInfoEntry 2 }

swSysDiagnosticsInfoExtendedDiagnosticsRevision OBJECT-TYPE
	SYNTAX  DisplayString
	ACCESS  read-only
	STATUS  mandatory
	DESCRIPTION
		"The revision of the extended diagnostics software at the
		 most recent failure."
::= { swSysDiagnosticsInfoEntry 3 }

swSysDiagnosticsInfoDiagnosticFailureCode OBJECT-TYPE
	SYNTAX	DisplayString
	ACCESS  read-only
	STATUS  mandatory
	DESCRIPTION
			"The code written by the diagnostics at the most recent
			 failure.  This identifies both the test number and failure 
			 code in the following format:  -.
			 If there is no failure then 000-000 is displayed."
::= { swSysDiagnosticsInfoEntry 4 }

swSysDiagnosticsInfoDiagnosticFailureDateTime OBJECT-TYPE
	SYNTAX  DisplayString
	ACCESS  read-only
	STATUS  mandatory
	DESCRIPTION
			"The date and time of the most recent diagnostic failure
			 for the module."
::= { swSysDiagnosticsInfoEntry 5 }

swSysDiagnosticsInfoDiagnosticFailureSlotNumber OBJECT-TYPE
	SYNTAX  INTEGER
	ACCESS  read-only
	STATUS  mandatory
	DESCRIPTION
			"The slot number (network adapter cards only) of the most
			 recent diagnostic failure for the module."
::= { swSysDiagnosticsInfoEntry 6 }

swSysDiagnosticsInfoDiagnosticFailureCounter OBJECT-TYPE
	SYNTAX  INTEGER
	ACCESS  read-only
	STATUS  mandatory
	DESCRIPTION
			"The total number of diagnostic failures logged against this
			 module."
::= { swSysDiagnosticsInfoEntry 7 }

swSysDiagnosticsInfoDiagnosticFieldDOACounter OBJECT-TYPE
	SYNTAX  INTEGER
	ACCESS  read-only
	STATUS  mandatory
	DESCRIPTION
			"The total number of failures occurring at this module during
			 the first 48 hours of operation."
	::= { swSysDiagnosticsInfoEntry 8 }

--
-- The Switching Systems MIB traps.
--

swSysSystemOverTemperatureEvent TRAP-TYPE
	ENTERPRISE	switchingSystemsMib
	VARIABLES	{ swSysSystemOvertemperature }
	DESCRIPTION
		"The trap that is generated when the system temperature
		exceeds a certain threshold."
	::= 1

swSysPowerSupplyFailureEvent TRAP-TYPE
	ENTERPRISE	switchingSystemsMib  
	VARIABLES	{ swSysPowerSupplyStatusIndex,
				  swSysPowerSupplyStatus,
				  swSysPowerSupplyStatusSupported }
	DESCRIPTION
		"The trap that is generated when a power supply unit
		fails."
	::= 2

swSysChassisSlotOverTemperatureEvent TRAP-TYPE
	ENTERPRISE  switchingSystemsMib
	VARIABLES   { swSysSlotIndex,
				  swSysSlotBoardType,
				  swSysSlotBoardRevision,
                  swSysSlotBoardStatus,
                  swSysSlotOvertemperature,
                  swSysSlotConverterBad }
    DESCRIPTION
        "The trap that is generated when the temperature of a
         board in a particular slot exceeds a certain threshold."
    ::= 3

swSysChassisSlotInsertEvent TRAP-TYPE
	ENTERPRISE  switchingSystemsMib
    VARIABLES   { swSysSlotIndex,
                  swSysSlotBoardType,
                  swSysSlotBoardRevision }
    DESCRIPTION
        "The trap that is generated when a board is inserted into a
         particular slot."
    ::= 4

swSysChassisSlotExtractEvent TRAP-TYPE
     ENTERPRISE  switchingSystemsMib
     VARIABLES   { swSysSlotIndex }
     DESCRIPTION
         "The trap that is generated when a board is extracted
          from a particular slot."
    ::= 5

swSysBridgeAddressThresholdEvent TRAP-TYPE
	ENTERPRISE	switchingSystemsMib 
	VARIABLES	{ swSysBridgeIndex }
	DESCRIPTION
			"The trap that is generated when the number of addresses
			stored in the bridge reaches swSysBridgeAddressThreshold."
	::= 6

swSysSystemFanFailureEvent TRAP-TYPE
	ENTERPRISE	switchingSystemsMib 
	VARIABLES	{ swSysSystemFanFailure }
	DESCRIPTION
			"The trap that is generated when one of the system fans
			fails."
	::= 7

swModuleCardSysOverTemperatureEvent TRAP-TYPE
	ENTERPRISE	switchingSystemsMib 
	VARIABLES	{ swSysModuleCardInfoIndex,
    			  swSysModuleCardInfoFamily,
				  swSysModuleCardInfoGenericType }
	DESCRIPTION
			"The trap that is generated when the temperature of 
			the system exceeds a certain threshold.  This trap is
            generated from agents that support the 
            swSysModuleCardInfoTable."
	::= 8

swModuleCardInsertEvent TRAP-TYPE
	ENTERPRISE	switchingSystemsMib 
	VARIABLES	{ swSysModuleCardInfoIndex,
				  swSysModuleCardInfoFamily,
				  swSysModuleCardInfoGenericType,
				  swSysModuleCardInfoSpecificType }
	DESCRIPTION
			"The trap that is generated when a board is inserted into a
			particular modular slot.  This trap is generated from agents 
            that support the swSysModuleCardInfoTable."
	::= 9

swModuleCardExtractEvent TRAP-TYPE
	ENTERPRISE	switchingSystemsMib 
	VARIABLES	{ swSysModuleCardInfoIndex}
	DESCRIPTION
			"The trap that is generated when a board is extracted
			from a particular modular slot.  This trap is generated
            from agents that support the swSysModuleCardInfoTable."
	::= 10
END
