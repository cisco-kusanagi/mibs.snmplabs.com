RM-TRAP-MIB DEFINITIONS ::= BEGIN

IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    host, percentage, status, load, disk, file, curSize, maxSize, processName, processID, cpuUsage, memUsage
        FROM AGGREGATED-EXT-MIB
    TruthValue, DisplayString, TestAndIncr, TimeStamp, RowStatus
        FROM SNMPv2-TC;

	lucent		    OBJECT IDENTIFIER  ::=  {  enterprises  1751  }
	products	    OBJECT IDENTIFIER  ::=  {  lucent  1  }
	softSwitch	    OBJECT IDENTIFIER  ::=  {  products 1198  }
	resourceMonitor	OBJECT IDENTIFIER  ::=  {  softSwitch  4  }

rmTraps   MODULE-IDENTITY    
        LAST-UPDATED "240701"
        ORGANIZATION "Lucent Technologies"    
        CONTACT-INFO 
                ""    
        DESCRIPTION
                "The MIB module for entities implementing the xxxx
                protocol."  

::=  {  resourceMonitor 0 }

	cpuUtilWarning NOTIFICATION-TYPE	
        OBJECTS  { host, percentage }
        STATUS current
        DESCRIPTION
        "Indicating the load on cpu exceeded the warning level.
		The variables are:
        1) host - Identify the machine
        2) percentage - cpu usage
		Severity: MAJOR"
    ::= { rmTraps  0 }

    cpuUtilAlarm NOTIFICATION-TYPE	
        OBJECTS  { host, percentage }
        STATUS current
        DESCRIPTION
        "Indicating the cpu is overloaded.
		The variables are:
        1) host - Identify the machine
        2) percentage - cpu usage
		Severity: CRITICAL"
    ::= { rmTraps  1 }

    cpuUtilInform NOTIFICATION-TYPE   
        OBJECTS  { host, percentage, status}
        STATUS current
        DESCRIPTION
        "Indicating previously raised cpuUtilAlarm or 
		cpuUtilAttention cleared.
		The variables are:
        1) host - Identify the machine
        2) percentage - cpu usage
        3) status - to clear Marjor or Critical
		Severity: INFO"
    ::= { rmTraps  2 }

	cpuLoadWarning NOTIFICATION-TYPE 
        OBJECTS  { host, load }
        STATUS current
        DESCRIPTION
        "Indicating the load on cpu exceeded the warning level.
		The variables are:
        1) host - Identify the machine
        2) load - cpu load
		Severity: MAJOR"
    ::= { rmTraps  3 }

    cpuLoadAlarm NOTIFICATION-TYPE   
        OBJECTS  { host, load }
        STATUS current
        DESCRIPTION
        "Indicating the cpu is overloaded.
		The variables are:
        1) host - Identify the machine
        2) load - cpu load
		Severity: CRITICAL"
    ::= { rmTraps  4 }

    cpuLoadInform NOTIFICATION-TYPE  
        OBJECTS  { host, load, status }
        STATUS current
        DESCRIPTION
        "Indicating previously raised cpuLoadAlarm or 
		cpuLoadWarning cleared.
		The variables are:
        1) host - Identify the machine
        2) load - current cpu load
        3) status - to clear Major or Critical
		Severity: INFO"
    ::= { rmTraps  5 }

    diskUsageWarning NOTIFICATION-TYPE    
        OBJECTS  { disk, percentage  }
        STATUS current
        DESCRIPTION
        "Indicating the load on disk exceeded the warning level.
		The variables are:
        1) disk - Identify the disk
        2) percentage - disk usage
		Severity: MAJOR"
     ::= { rmTraps  6 }

     diskUsageAlarm NOTIFICATION-TYPE
        OBJECTS  { disk, percentage  }
        STATUS current
        DESCRIPTION
        "Indicating the disk is overloaded.
		The variables are:
        1) disk - Identify the disk
        2) percentage - disk usage
		Severity: CRITICAL"
     ::= { rmTraps  7 }

     diskUsageInform NOTIFICATION-TYPE 
       OBJECTS  { disk, percentage, status  }
        STATUS current
        DESCRIPTION
        "Indicating previously raised diskUsageWarning or 
		diskUsageAlarm NOTIFICATION cleared.
		The variables are:
        1) disk - Identify the disk
        2) percentage - disk usage
        3) status - to clear Major or critical
		Severity: INFO"
     ::= { rmTraps  8 }

	 fileSizeEvent NOTIFICATION-TYPE 
        OBJECTS  { file, curSize, maxSize }
        STATUS current
        DESCRIPTION
        "Indicates that a log file has exceeded its maximum 
		allowed size.
		The variables are:
        1) fileName - this file being monitored for size
        2) curSize - the current file size (in KB)
        3) maxSize - the size (in KB) after which the trap was
           to be triggered.
		Severity: MAJOR"
     ::= { rmTraps  9 }


        unixProcessDied NOTIFICATION-TYPE            
            OBJECTS  { host, processName, processID }
        STATUS current
            DESCRIPTION
                "Indicating that a specific process has died
                The variables are:
                    host - Identify the machine
                    processName and processID - the processs
                Severity: MAJOR"
            ::= { rmTraps  10 }

       procCpuAlarm NOTIFICATION-TYPE          
            OBJECTS  { host, processName, processID, cpuUsage }
        STATUS current
            DESCRIPTION
                "Indicating tha a process has used too much cpu.
                The variables are:
                    host - Identify the machine
                    processName and processID - the process
		    cpuUsage - CPU usage
                Severity: CRITICAL"
            ::= { rmTraps  11 }

       procCpuWarn NOTIFICATION-TYPE          
            OBJECTS  { host, processName, processID, cpuUsage }
        STATUS current
            DESCRIPTION
                "Indicating tha a process has used too much cpu.
                The variables are:
                    host - Identify the machine
                    processName and processID - the process
		    cpuUsage - CPU usage
                Severity: MAJOR"
            ::= { rmTraps  12 }

       procMemAlarm NOTIFICATION-TYPE       
            OBJECTS  { host, processName, processID, memUsage }
        STATUS current
            DESCRIPTION
                "Indicating tha a process has used too much memory.
                The variables are:
                    host - Identify the machine
                    processName and processID - the process
		    memUsage - Memory usage
                Severity: CRITICAL"
            ::= { rmTraps  13 }

       procCpuInform NOTIFICATION-TYPE     
            OBJECTS  { host, processName, processID }
        STATUS current
            DESCRIPTION
                "Indicating previously raised procCpuAlarm or
                procCpuWarn cleared.
                The variables are:
                    host - Identify the machine
                    processName and processID - the process"

            ::= { rmTraps  14 }

    procMemInform NOTIFICATION-TYPE    
        OBJECTS  { host, processName, processID }
        STATUS current
        DESCRIPTION
                "Indicating previously raised procMemAlarm cleared.
                The variables are:
                    host - Identify the machine
                    processName and processID - the process"

            ::= { rmTraps  15 }

END
