NETOPIA-MIB DEFINITIONS ::= BEGIN


          IMPORTS
              enterprises, Counter, Gauge, IpAddress
                  FROM RFC1155-SMI
              OBJECT-TYPE
                  FROM RFC-1212
              DisplayString
                  FROM RFC1213-MIB
              DdpAddress
                  FROM RFC1243-MIB;

          farallon       OBJECT IDENTIFIER ::= { enterprises 304 }
          netopia        OBJECT IDENTIFIER ::= { farallon products(1)
                                                 rtrProds(3) 1 }


          --  Textual Conventions Used in this MIB Module

          ATNetworkNumber ::= OCTET STRING (SIZE(2))  -- 2 octets of net number
                                                      -- in network byte order

          HostNameOrIpAddr ::= OCTET STRING
          --
          --  A host's fully- or partially-qualified domain name (in the format
          --  specified in RFCs 952 and 1123) or IP address (expressed as a
          --  string in the familiar "dotted-quad" notation).

          UInteger ::= Gauge                          -- an unsigned integer


          --
          --
          --  MIB Groups
          --

          sysParams      OBJECT IDENTIFIER ::= { netopia  1 }
          clockParams    OBJECT IDENTIFIER ::= { netopia  2 }
          sysStats       OBJECT IDENTIFIER ::= { netopia  3 }
          ipParams       OBJECT IDENTIFIER ::= { netopia  4 }
          ripParams      OBJECT IDENTIFIER ::= { netopia  5 }
          atParams       OBJECT IDENTIFIER ::= { netopia  6 }
          macipParams    OBJECT IDENTIFIER ::= { netopia  7 }
          dhcpParams     OBJECT IDENTIFIER ::= { netopia  8 }
          aurpParams     OBJECT IDENTIFIER ::= { netopia  9 }
          bootParams     OBJECT IDENTIFIER ::= { netopia 10 }
          snmpParams     OBJECT IDENTIFIER ::= { netopia 11 }
          isdnParams     OBJECT IDENTIFIER ::= { netopia 12 }
          consoleParams  OBJECT IDENTIFIER ::= { netopia 13 }
          pcCardParams   OBJECT IDENTIFIER ::= { netopia 14 }
          logParams      OBJECT IDENTIFIER ::= { netopia 15 }
          filterParams   OBJECT IDENTIFIER ::= { netopia 16 }


          --  The sysParams group

          --  This group contains general information regarding the
          --  managed node that supplements information available in
          --  the system group of MIB-II (RFC 1213).

          hwVersion OBJECT-TYPE
              SYNTAX    OCTET STRING (SIZE(4))
              ACCESS    read-only
              STATUS    mandatory
              DESCRIPTION
                        "The device's hardware version, consisting of a
                        major version, minor version, release stage, and
                        revision number, packed into 4 octets.  The
                        first octet contains the major version encoded
                        as two packed binary coded decimal (bcd) digits.
                        The second octet contains the minor version
                        encoded as two packed bcd digits.  The third
                        byte contains the release stage, consisting of
                        two packed bcd digits, the first of which is
                        always zero and the second of which is either D
                        (development), A (alpha), B (beta), E
                        (experimental), or F (final).  The fourth byte
                        contains the revision number encoded as two
                        packed bcd digits.

                        Thus, the hardware version '1.2 final' would be
                        encoded as the octet string 01 02 0F 00."
              ::= { sysParams 1 }

          fwVersion OBJECT-TYPE
              SYNTAX    OCTET STRING (SIZE(4))
              ACCESS    read-only
              STATUS    mandatory
              DESCRIPTION
                        "The device's firmware version, consisting of a
                        major version, minor version, release stage, and
                        revision number, packed into 4 octets.  The
                        first octet contains the major version encoded
                        as two packed binary coded decimal (bcd) digits.
                        The second octet contains the minor version
                        encoded as two packed bcd digits.  The third
                        byte contains the release stage, consisting of
                        two packed bcd digits, the first of which is
                        always zero and the second of which is either D
                        (development), A (alpha), B (beta), E
                        (experimental), or F (final).  The fourth byte
                        contains the revision number encoded as two
                        packed bcd digits.

                        Thus, the firmware version '1.2 final' would be
                        encoded as the octet string 01 02 0F 00."
              ::= { sysParams 2 }

          productMIBVersion OBJECT-TYPE
              SYNTAX    OCTET STRING (SIZE(4))
              ACCESS    read-only
              STATUS    mandatory
              DESCRIPTION
                        "The version of the product specific MIB
                        implemented by the device's SNMP agent,
                        consisting of a major version, minor version,
                        release stage, and revision number, packed into
                        4 octets.  The first octet contains the major
                        version encoded as two packed binary coded
                        decimal (bcd) digits.  The second octet contains
                        the minor version encoded as two packed bcd
                        digits.  The third byte contains the release
                        stage, consisting of two packed bcd digits, the
                        first of which is always zero and the second of
                        which is either D (development), A (alpha), B
                        (beta), E (experimental), or F (final).  The
                        fourth byte contains the revision number encoded
                        as two packed bcd digits.

                        Thus, the product specific MIB version '1.2
                        final' would be encoded as the octet string 01
                        02 0F 00."
              ::= { sysParams 3 }

          serialNumber OBJECT-TYPE
              SYNTAX    OCTET STRING (SIZE(3))
              ACCESS    read-only
              STATUS    mandatory
              DESCRIPTION
                        "The device's 24-bit serial number.  The value
                        of this object is the same as the least
                        significant three bytes of the physical address
                        of the device's Ethernet interface."
              ::= { sysParams 4 }

          modelNumber OBJECT-TYPE
              SYNTAX    INTEGER
              ACCESS    read-only
              STATUS    mandatory
              DESCRIPTION
                        "The device's model number."
              ::= { sysParams 5 }


          --  The clockParams group

          --  This group contains objects related to the operation of
          --  the device's real-time clock.

          bootTime OBJECT-TYPE
              SYNTAX    DisplayString
              ACCESS    read-only
              STATUS    mandatory
              DESCRIPTION
                        "The time and date (in human-readable form) when
                        the device was last restarted."
              ::= { clockParams 1 }

          systemClock OBJECT-TYPE
              SYNTAX    OCTET STRING (SIZE(14))
              ACCESS    read-write
              STATUS    mandatory
              DESCRIPTION
                        "The current setting of the system clock encoded
                        as fourteen decimal-ASCII digits in the form
                        'YYYYMMDDHHMMSS'.

                        Thus, 10:35:00 p.m. on August 6, 1959 would be
                        represented by the following fourteen octets:
                        '19590806223500'."
              ::= { clockParams 2 }


          --  The sysStats group

          --  This group contains general system statistics.

          --  cpu utilization statistics

          currentCpuUtil OBJECT-TYPE
              SYNTAX    INTEGER (0..100)
              ACCESS    read-only
              STATUS    mandatory
              DESCRIPTION
                        "The device's current CPU utilization, measured
                        as the percentage of time the device has been
                        non-idle during the most recent one-second
                        interval."
              ::= { sysStats 1 }

          averageCpuUtil OBJECT-TYPE
              SYNTAX    INTEGER (0..100)
              ACCESS    read-only
              STATUS    mandatory
              DESCRIPTION
                        "The device's average CPU utilization, measured
                        as the percentage of time the device has been
                        non-idle during the most recent one-minute
                        interval."
              ::= { sysStats 2 }

          --  buffer utilization statistics

          currentBufs OBJECT-TYPE
              SYNTAX    INTEGER (0..100)
              ACCESS    read-only
              STATUS    mandatory
              DESCRIPTION
                        "The device's current 1-second buffer
                        utilization, measured as a percentage of all
                        available buffers."
              ::= { sysStats 3 }

          averageBufs OBJECT-TYPE
              SYNTAX    INTEGER (0..100)
              ACCESS    read-only
              STATUS    mandatory
              DESCRIPTION
                        "The device's current 1-minute buffer
                        utilization, measured as a percentage of all
                        available buffers."
              ::= { sysStats 4 }

          --  memory utilization statistics

          totalRAM OBJECT-TYPE
              SYNTAX    INTEGER
              ACCESS    read-only
              STATUS    mandatory
              DESCRIPTION
                        "The number of bytes of Random-Access Memory
                        (RAM) available on the device."
              ::= { sysStats 5 }

          usedRAM OBJECT-TYPE
              SYNTAX    INTEGER
              ACCESS    read-only
              STATUS    mandatory
              DESCRIPTION
                        "The number of bytes of RAM in use at the
                        current time."
              ::= { sysStats 6 }

          totalFEPROM OBJECT-TYPE
              SYNTAX    INTEGER
              ACCESS    read-only
              STATUS    mandatory
              DESCRIPTION
                        "The number of bytes of Flash-Erasable
                        Programmable Read-Only Memory (Flash-EPROM)
                        available on the device."
              ::= { sysStats 7 }

          usedFEPROM OBJECT-TYPE
              SYNTAX    INTEGER
              ACCESS    read-only
              STATUS    mandatory
              DESCRIPTION
                        "The number of bytes of Flash-Erasable
                        Programmable Read-Only Memory (Flash-EPROM) in
                        use at the current time."
              ::= { sysStats 8 }


          --  The ipParams group

          --  This group contains objects that control the device's
          --  implementation of the TCP/IP protocols.

          ipAddr OBJECT-TYPE
              SYNTAX    IpAddress
              ACCESS    read-write
              STATUS    mandatory
              DESCRIPTION
                        "The IP address that the device will use after a
                        restart.  The device's active IP address can be
                        determined by examining the appropriate instance
                        of the ipAdEntAddr object in the MIB-II IP
                        address table."
              ::= { ipParams 1 }

          ipNetMask OBJECT-TYPE
              SYNTAX    IpAddress
              ACCESS    read-write
              STATUS    mandatory
              DESCRIPTION
                        "The subnet mask that the device will use after
                        a restart.  The device's active subnet mask can
                        be determined by examining the appropriate
                        instance of the ipAdEntNetMask object in the
                        MIB-II IP address table."
              ::= { ipParams 2 }

          ipBcastForm OBJECT-TYPE
              SYNTAX    INTEGER {
                            allOnes(1),
                            allZeros(2)
                        }
              ACCESS    read-write
              STATUS    mandatory
              DESCRIPTION
                        "The type of IP broadcast address that the
                        device will use after a restart:  the Internet
                        standard all-ones broadcast address or the non-
                        standard all zeros broadcast address.  The
                        device's active broadcast address type can be
                        determined by examining the appropriate instance
                        of the ipAdEntBcastAddr object in the MIB-II IP
                        address table."
              ::= { ipParams 3 }

          ipEncap OBJECT-TYPE
              SYNTAX    INTEGER {
                            ethernet(1),
                            ieee8022(2)
                        }
              ACCESS    read-write
              STATUS    mandatory
              DESCRIPTION
                        "The type of IP datagram encapsulation that the
                        device will use after a restart:  Ethernet or
                        IEEE802.2.  The active type of IP datagram
                        encapsulation  can be determined by examining
                        the appropriate instance of the ifType object in
                        the MIB-II interfaces table entry for the
                        device's Ethernet interface.  If the value of
                        that instance of ifType is 'ethernet-csmacd(6)',
                        then the active type of IP datagram
                        encapsulation is Ethernet; if the value of that
                        instance of ifType is 'iso88023-csmacd(7)', then
                        the active type of IP datagram encapsulation is
                        IEEE802.2."
              ::= { ipParams 4 }

          ipDefaultGateway OBJECT-TYPE
              SYNTAX    IpAddress
              ACCESS    read-write
              STATUS    mandatory
              DESCRIPTION
                        "The default gateway IP address that the device
                        will use after a restart.  The device's
                        operational default gateway IP address can be
                        determined by examining the value of the
                        ipRouteNextHop.0.0.0.0 object in the MIB-II IP
                        routing table."
              ::= { ipParams 5 }

          ipDomainName OBJECT-TYPE
              SYNTAX    OCTET STRING
              ACCESS    read-write
              STATUS    mandatory
              DESCRIPTION
                        "The device's domain name."
              ::= { ipParams 6 }

          ipDNSServerTable OBJECT-TYPE
              SYNTAX    SEQUENCE OF IpDNSServerEntry
              ACCESS    not-accessible
              STATUS    mandatory
              DESCRIPTION
                        "A list of entries describing the device's
                        Domain Name System name servers.

                        This table supports 'conceptual row creation'
                        according to section 3.2(3) of RFC 1212:  To add
                        a new row to this table, a management station
                        must provide a value for the new instance of the
                        ipDNSServerAddress object, and may, in addition,
                        provide a value for the corresponding instance
                        of the ipDNSServerStatus object.  If no value is
                        supplied for the corresponding instance of the
                        ipDNSServerStatus object, its value will default
                        to 'valid(1)'."
              ::= { ipParams 7 }

          ipDNSServerEntry OBJECT-TYPE
              SYNTAX    IpDNSServerEntry
              ACCESS    not-accessible
              STATUS    mandatory
              DESCRIPTION
                        "An entry describing one of the device's Domain
                        Name System name servers."
              INDEX     { ipDNSServerIndex }
              ::= { ipDNSServerTable 1 }

          IpDNSServerEntry ::=
              SEQUENCE {
                  ipDNSServerIndex
                      INTEGER,
                  ipDNSServerAddress
                      IpAddress,
                  ipDNSServerStatus
                      INTEGER
              }

          ipDNSServerIndex OBJECT-TYPE
              SYNTAX    INTEGER
              ACCESS    read-only
              STATUS    mandatory
              DESCRIPTION
                        "A unique value for each of the device's Domain
                        Name System name servers.

                        The value of this object ranges between one and
                        the number of such servers.  Servers are listed
                        in order of preference:  A server with a lower-
                        valued ipDNSServerIndex is preferred over a
                        server with a higher-valued ipDNSServerIndex.
                        Thus, if it exists, ipDNSServerAddress.1
                        indicates the IP address of the device's primary
                        DNS server."
              ::= { ipDNSServerEntry 1 }

          ipDNSServerAddress OBJECT-TYPE
              SYNTAX    IpAddress
              ACCESS    read-write
              STATUS    mandatory
              DESCRIPTION
                        "The IP address of the Domain Name System name
                        server described by this entry."
              ::= { ipDNSServerEntry 2 }

          ipDNSServerStatus OBJECT-TYPE
              SYNTAX    INTEGER {
                            valid(1),
                            invalid(2)
                        }
              ACCESS    read-write
              STATUS    mandatory
              DESCRIPTION
                        "The status of this entry.

                        Setting this object to the value 'invalid(2)'
                        has the effect of invalidating the corresponding
                        entry in the ipDNSServerTable.  That is, it
                        effectively disassociates the mapping identified
                        with said entry.  It is an implementation-
                        specific matter as to whether the agent removes
                        an invalidated entry from the table.
                        Accordingly, management stations must be
                        prepared to receive from agents tabular
                        information corresponding to entries not
                        currently in use.  Proper interpretation of such
                        entries requires examination of the relevant
                        ipDNSServerStatus object."
              ::= { ipDNSServerEntry 3 }


          --  The ripParams group

          --  This group contains objects that control the device's
          --  implementation of the RIP protocol.

          ripEnTxEnable OBJECT-TYPE
              SYNTAX    INTEGER {
                            enabled(1),
                            disabled(2)
                        }
              ACCESS    read-write
              STATUS    mandatory
              DESCRIPTION
                        "Indicates whether or not transmission of RIP
                        packets on the device's Ethernet interface will
                        be enabled when the device is next restarted.

                        Transmission of RIP packets should normally be
                        enabled if MacIP is enabled in IP subnetting
                        mode.  This enables the device to broadcast RIP
                        packets advertising the route to the IP subnet
                        of MacIP clients.

                        If transmission of RIP packets is disabled and
                        MacIP is enabled in IP subnetting mode, a static
                        route for the IP subnet corresponding to the
                        MacIP network must be added to the routing table
                        of all IP routers and hosts on the IP network;
                        otherwise, devices on IP networks other than the
                        one directly connected to the device will not be
                        able to communicate with MacIP clients."
              ::= { ripParams 1 }

          ripEnRxEnable OBJECT-TYPE
              SYNTAX    INTEGER {
                            enabled(1),
                            disabled(2)
                        }
              ACCESS    read-write
              STATUS    mandatory
              DESCRIPTION
                        "Indicates whether or not reception of RIP
                        packets will be enabled on the Ethernet
                        interface when the device is next restarted.

                        Reception of RIP packets should normally be
                        enabled if MacIP is enabled in IP subnetting
                        mode.  This enables the device to update its
                        routing table with routes to IP networks other
                        than those directly connected to the device.

                        If reception of RIP packets is disabled and
                        MacIP is enabled in IP subnetting mode,
                        encapsulated IP packets from MacIP clients
                        addressed to a host on an IP network other than
                        those directly connected to the device will be
                        sent to the device's default gateway."
              ::= { ripParams 2 }


          --  The atParams group

          --  This group contains definitions extending the AppleTalk
          --  MIB (RFC 1243).

          --  The objects in this group are not applicable to a
          --  Netopia PN630 or Netopia PN640.

          atportXTable OBJECT-TYPE
              SYNTAX    SEQUENCE OF AtportXEntry
              ACCESS    not-accessible
              STATUS    mandatory
              DESCRIPTION
                        "A list of entries providing additional
                        information for the device's AppleTalk ports."
              ::= { atParams 1 }

          atportXEntry OBJECT-TYPE
              SYNTAX    AtportXEntry
              ACCESS    not-accessible
              STATUS    mandatory
              DESCRIPTION
                        "An entry containing additional information one
                        of the device's AppleTalk ports."
              INDEX     { atportXIndex }
              ::= { atportXTable 1 }

          AtportXEntry ::=
              SEQUENCE {
                  atportXIndex
                      INTEGER,
                  atportXHide
                      INTEGER,
                  atportXSeed
                      INTEGER
              }

          atportXIndex OBJECT-TYPE
              SYNTAX    INTEGER
              ACCESS    read-only
              STATUS    mandatory
              DESCRIPTION
                        "The AppleTalk router port to which this entry
                        applies.  The port identified by a particular
                        value of this index is the same port as is
                        identified by the same value of the atportIndex
                        object in the atportTable in RFC 1243."
              ::= { atportXEntry 1 }

          atportXHide OBJECT-TYPE
              SYNTAX    INTEGER {
                            visible(1),
                            hidden(2)
                        }
              ACCESS    read-write
              STATUS    mandatory
              DESCRIPTION
                        "Indicates whether or not this AppleTalk port
                        will be hidden by the router.  Hiding an
                        AppleTalk port prevents the router from
                        forwarding AppleTalk Name Binding Protocol (NBP)
                        responses from that port to other ports.  The
                        effect of hiding a port is that devices on the
                        port are invisible via NBP to devices elsewhere
                        on the network."
              ::= { atportXEntry 2 }

          atportXSeed OBJECT-TYPE
              SYNTAX    INTEGER {
                            other(1),
                            softseed(2),
                            hardseed(3),
                            noseed(4)
                        }
              ACCESS    read-write
              STATUS    mandatory
              DESCRIPTION
                        "Indicates how this AppleTalk port will seed
                        itself at startup.  If the port is set to
                        softseed, the router will get the port's network
                        seed configuration from another router on the
                        port or will act as the seed router if no other
                        router is connected.  If the port is set to
                        hardseed, the router will act as the seed router
                        for the port and disable the port if another
                        router is connected with a different network
                        configuration.  If the port is set to noseed,
                        the router will only startup the port if another
                        router is connected.  The value of this object
                        will be 'other(1)' for ports that are not native
                        AppleTalk ports."
              ::= { atportXEntry 3 }

          atportZoneTable OBJECT-TYPE
              SYNTAX    SEQUENCE OF AtportZoneEntry
              ACCESS    not-accessible
              STATUS    mandatory
              DESCRIPTION
                        "The table of zone information for ports.

                        The atportZoneTable object supports 'conceptual
                        row creation' according to section 3.2(3) of RFC
                        1212:  To add a new row to the atportZoneTable,
                        a management station must provide a value for
                        the new instance of the atportZoneDefault
                        object, and may, in addition, provide values for
                        any or all of the remaining object instances in
                        the new row.

                        If no values are supplied for the corresponding
                        instances of the atportZonePort and
                        atportZoneName objects, their values will be
                        derived from the atportZoneDefault object
                        instance.  If no value is supplied for the
                        corresponding instance of the atportZoneStatus
                        object, its value will default to 'valid(1)'."
              ::= { atParams 2 }

          atportZoneEntry OBJECT-TYPE
              SYNTAX    AtportZoneEntry
              ACCESS    not-accessible
              STATUS    mandatory
              DESCRIPTION
                        "An entry of zone information for a port."
              INDEX     { atportZonePort, atportZoneName }
              ::= { atportZoneTable 1 }

          AtportZoneEntry ::=
              SEQUENCE {
                  atportZonePort
                      INTEGER,
                  atportZoneName
                      OCTET STRING (SIZE(1..32)),
                  atportZoneDefault
                      INTEGER,
                  atportZoneStatus
                      INTEGER
              }

          atportZonePort OBJECT-TYPE
              SYNTAX    INTEGER
              ACCESS    read-write
              STATUS    mandatory
              DESCRIPTION
                        "An integer representing the port to which this
                        zone belongs.  The port identified by a
                        particular value of this object is the same port
                        as is identified by the same value of
                        atportIndex."
              ::= { atportZoneEntry 1 }

          atportZoneName OBJECT-TYPE
              SYNTAX    OCTET STRING (SIZE(1..32))
              ACCESS    read-write
              STATUS    mandatory
              DESCRIPTION
                        "A zone name configured for the AppleTalk port
                        identified by the corresponding instance of
                        atportZonePort."
              ::= { atportZoneEntry 2 }

          atportZoneDefault OBJECT-TYPE
              SYNTAX    INTEGER {
                            default(1),
                            notDefault(2)
                        }
              ACCESS    read-write
              STATUS    mandatory
              DESCRIPTION
                        "The zone is marked as 'default(1)' if it is the
                        default zone for the network attached to this
                        port, and 'notDefault(2)' if it is not.  Exactly
                        one zone must be marked as 'default(1)' for each
                        port for which zones are configured."
              ::= { atportZoneEntry 3 }

          atportZoneStatus OBJECT-TYPE
              SYNTAX    INTEGER {
                            valid(1),
                            invalid(2)
                        }
              ACCESS    read-write
              STATUS    mandatory
              DESCRIPTION
                        "The status of this zone entry.

                        Setting this object to the value 'invalid(2)'
                        has the effect of invalidating the corresponding
                        entry in the atportZoneTable.  That is, it
                        effectively disassociates the mapping identified
                        with said entry.  It is an implementation-
                        specific matter as to whether the agent removes
                        an invalidated entry from the table.
                        Accordingly, management stations must be
                        prepared to receive from agents tabular
                        information corresponding to entries not
                        currently in use.  Proper interpretation of such
                        entries requires examination of the relevant
                        atportZoneStatus object."
              ::= { atportZoneEntry 4 }


          atportTrafficTable OBJECT-TYPE
              SYNTAX    SEQUENCE OF AtportTrafficEntry
              ACCESS    not-accessible
              STATUS    mandatory
              DESCRIPTION
                        "A list of traffic statistics for the router
                        ports."
              ::= { atParams 3 }

          atportTrafficEntry OBJECT-TYPE
              SYNTAX    AtportTrafficEntry
              ACCESS    not-accessible
              STATUS    mandatory
              DESCRIPTION
                        "The traffic statistics for a single router
                        port."
              INDEX     { atportTrafficIndex }
              ::= { atportTrafficTable 1 }

          AtportTrafficEntry ::=
              SEQUENCE {
                  atportTrafficIndex
                      INTEGER,
                  atportTrafficRxBytes
                      Counter,
                  atportTrafficRxPackets
                      Counter,
                  atportTrafficTxBytes
                      Counter,
                  atportTrafficTxPackets
                      Counter
              }

          atportTrafficIndex OBJECT-TYPE
              SYNTAX    INTEGER
              ACCESS    read-only
              STATUS    mandatory
              DESCRIPTION
                        "The AppleTalk router port to which this entry
                        applies.  The AppleTalk router port identified
                        by a particular value of this index is the same
                        AppleTalk router port as is identified by the
                        same value of atportIndex."
              ::= { atportTrafficEntry 1 }

          atportTrafficRxBytes OBJECT-TYPE
              SYNTAX    Counter
              ACCESS    read-only
              STATUS    mandatory
              DESCRIPTION
                        "The number of bytes the AppleTalk router has
                        received from this port."
              ::= { atportTrafficEntry 2 }

          atportTrafficRxPackets OBJECT-TYPE
              SYNTAX    Counter
              ACCESS    read-only
              STATUS    mandatory
              DESCRIPTION
                        "The number of packets the AppleTalk router has
                        received from this port."
              ::= { atportTrafficEntry 3 }

          atportTrafficTxBytes OBJECT-TYPE
              SYNTAX    Counter
              ACCESS    read-only
              STATUS    mandatory
              DESCRIPTION
                        "The number of bytes the AppleTalk router has
                        transmitted to this port."
              ::= { atportTrafficEntry 4 }

          atportTrafficTxPackets OBJECT-TYPE
              SYNTAX    Counter
              ACCESS    read-only
              STATUS    mandatory
              DESCRIPTION
                        "The number of packets the AppleTalk router has
                        transmitted to this port."
              ::= { atportTrafficEntry 5 }

          deviceNBPObject OBJECT-TYPE
              SYNTAX    OCTET STRING (SIZE(0..32))
              ACCESS    read-write
              STATUS    mandatory
              DESCRIPTION
                        "The object portion of the AppleTalk Name
                        Binding Protocol (NBP) name used by device-
                        resident service providers to advertise their
                        services using NBP.

                        Setting this object to a zero-length OCTET
                        STRING will restore this object to its default
                        value."
              ::= { atParams 4 }


          --  The macipParams group

          --  This group contains definitions of objects that control
          --  the device's implementation of the MacIP protocol.

          --  The objects in this group are not applicable to
          --  a Netopia PN630 or Netopia PN640.

          macipSupport OBJECT-TYPE
              SYNTAX    INTEGER {
                            disabled(1),
                            ipSubnetting(2),
                            kipForwarding(3)
                        }
              ACCESS    read-write
              STATUS    mandatory
              DESCRIPTION
                        "Indicates whether or not MacIP support will be
                        enabled when the device is restarted, and, if
                        enabled, specifies the type of MacIP support to
                        be used:  IP subnetting or KIP forwarding.

                        In KIP forwarding mode, the MacIP network is an
                        extension of the device's Ethernet IP network;
                        the network portion of MacIP client IP addresses
                        will be the same as the network portion of the
                        MacIP gateway's IP address on the Ethernet IP
                        network.

                        In IP subnetting mode, the MacIP network is
                        treated as a distinct IP subnet; the network
                        portion of MacIP client IP addresses will be
                        different from the network portion of the MacIP
                        gateway's IP address on the Ethernet IP
                        network."
              ::= { macipParams 1 }

          macipIpSubIpAddr OBJECT-TYPE
              SYNTAX    IpAddress
              ACCESS    read-write
              STATUS    mandatory
              DESCRIPTION
                        "Indicates the MacIP gateway's IP address on the
                        MacIP subnet in IP Subnetting mode.

                        The value of this object is meaningful only if
                        the value of macipSupport is 'ipSubnetting(2)'.

                        (In KIP Forwarding mode, the MacIP gateway's IP
                        address is the same as the device's Ethernet IP
                        address.)"
              ::= { macipParams 2 }

          macipIpSubNetMask OBJECT-TYPE
              SYNTAX    IpAddress
              ACCESS    read-write
              STATUS    mandatory
              DESCRIPTION
                        "The subnet mask associated with
                        macipIpSubIpAddr.  This is also the subnet mask
                        sent to clients in response to a SERVER request.
                        The value of this object is meaningful only if
                        the value of macipSupport is 'ipSubnetting(2)'.

                        (If the value of macipSupport is
                        'kipForwarding(3)', then the ipNetMask object
                        indicates the subnet mask sent to clients in
                        response to a SERVER request.)

                        Note:  The value of this object should be the
                        same as the value of the ipNetMask object if
                        transmission of RIP packets on the Ethernet IP
                        network is enabled, since there is no provision
                        for including network addresses with different
                        subnet masks in RIP version-1 packets."
              ::= { macipParams 3 }

          macipFirstClientIpAddr OBJECT-TYPE
              SYNTAX    IpAddress
              ACCESS    read-write
              STATUS    mandatory
              DESCRIPTION
                        "Indicates the first static MacIP client
                        address, or, if the value of macipNumStaticAddrs
                        is zero, the first dynamic MacIP client address.
                        (If the value of macipNumStaticAddrs is non-
                        zero, then the first dynamic MacIP client
                        address is equal to the sum of the value of this
                        object and the value of macipNumStaticAddrs.)

                        The network portion of the value of this object
                        must match the network portion of the MacIP
                        gateway's IP address (i.e., in KIP Forwarding
                        mode, the value of the ipAddr object in the
                        ipParams group, and in IP Subnetting mode, the
                        value of the macipIpSubIpAddr object in this
                        group)."
              ::= { macipParams 4 }

          macipNumStaticAddrs OBJECT-TYPE
              SYNTAX    INTEGER
              ACCESS    read-write
              STATUS    mandatory
              DESCRIPTION
                        "Indicates the maximum number of static IP
                        addresses available to clients of the MacIP
                        gateway.  The sum of the maximum number of
                        static and dynamic IP addresses available must
                        not exceed a pre-configured limit that is equal
                        to the value of the macipMaxAddrs object."
              ::= { macipParams 5 }

          macipNumDynamicAddrs OBJECT-TYPE
              SYNTAX    INTEGER
              ACCESS    read-write
              STATUS    mandatory
              DESCRIPTION
                        "Indicates the maximum number of dynamic IP
                        addresses available to clients requesting an IP
                        address from the MacIP gateway.  The sum of the
                        maximum number of static and dynamic IP
                        addresses available must not exceed a pre-
                        configured limit that is equal to the value of
                        the macipMaxAddrs object."
              ::= { macipParams 6 }

          macipMaxAddrs OBJECT-TYPE
              SYNTAX    INTEGER
              ACCESS    read-only
              STATUS    mandatory
              DESCRIPTION
                        "Indicates the pre-configured limit on the sum
                        of the maximum number of static and dynamic
                        addresses available to MacIP gateway clients.
                        The sum of the values of the macipNumStaticAddrs
                        and macipNumDynamicAddrs objects cannot exceed
                        the value of this object."
              ::= { macipParams 7 }

          macipUnusedDynamicAddrs OBJECT-TYPE
              SYNTAX    Gauge
              ACCESS    read-only
              STATUS    mandatory
              DESCRIPTION
                        "Indicates the current number of unused dynamic
                        addresses available to MacIP gateway clients."
              ::= { macipParams 8 }

          macipAssignRequests OBJECT-TYPE
              SYNTAX    Counter
              ACCESS    read-only
              STATUS    mandatory
              DESCRIPTION
                        "Indicates the number of ASSIGN requests
                        received by the MacIP gateway."
              ::= { macipParams 9 }

          macipServerRequests OBJECT-TYPE
              SYNTAX    Counter
              ACCESS    read-only
              STATUS    mandatory
              DESCRIPTION
                        "Indicates the number of SERVER requests
                        received by the MacIP gateway."
              ::= { macipParams 10 }

          macipRefusedAssignRequests OBJECT-TYPE
              SYNTAX    Counter
              ACCESS    read-only
              STATUS    mandatory
              DESCRIPTION
                        "Indicates the number of times that the gateway
                        was unable to assign a dynamic IP address to a
                        client because all available dynamic addresses
                        were in use."
              ::= { macipParams 11 }

          macipBadRequests OBJECT-TYPE
              SYNTAX    Counter
              ACCESS    read-only
              STATUS    mandatory
              DESCRIPTION
                        "Indicates the number of unsupported and/or
                        unknown requests received by the MacIP gateway.
                        These include NAME, RELEASE, and STATIC requests
                        as well as requests containing unknown request
                        codes."
              ::= { macipParams 12 }

          macipForwardedAtFrames OBJECT-TYPE
              SYNTAX    Counter
              ACCESS    read-only
              STATUS    mandatory
              DESCRIPTION
                        "The total number of frames that the MacIP
                        gateway received from the AppleTalk network and
                        forwarded to the IP network."
              ::= { macipParams 13 }

          macipForwardedAtOctets OBJECT-TYPE
              SYNTAX    Counter
              ACCESS    read-only
              STATUS    mandatory
              DESCRIPTION
                        "The total number of octets contained in the
                        frames counted by the macipForwardedAtFrames
                        object."
              ::= { macipParams 14 }

          macipDroppedAtFrames OBJECT-TYPE
              SYNTAX    Counter
              ACCESS    read-only
              STATUS    mandatory
              DESCRIPTION
                        "The number of frames that the MacIP gateway
                        received from the AppleTalk network that the
                        gateway was unable to forward to the IP
                        network."
              ::= { macipParams 15 }

          macipForwardedIpFrames OBJECT-TYPE
              SYNTAX    Counter
              ACCESS    read-only
              STATUS    mandatory
              DESCRIPTION
                        "The total number of frames that the MacIP
                        gateway received from the IP network and
                        forwarded to the AppleTalk network."
              ::= { macipParams 16 }

          macipForwardedIpOctets OBJECT-TYPE
              SYNTAX    Counter
              ACCESS    read-only
              STATUS    mandatory
              DESCRIPTION
                        "The total number of octets contained in the
                        frames counted by the macipForwardedIpFrames
                        object."
              ::= { macipParams 17 }

          macipDroppedIpFrames OBJECT-TYPE
              SYNTAX    Counter
              ACCESS    read-only
              STATUS    mandatory
              DESCRIPTION
                        "The number of frames that the MacIP gateway
                        received from the IP network that the gateway
                        was unable to forward to the AppleTalk network."
              ::= { macipParams 18 }


          --  The MacIP Client Table

          macipClientTable OBJECT-TYPE
              SYNTAX    SEQUENCE OF MacipClientEntry
              ACCESS    not-accessible
              STATUS    mandatory
              DESCRIPTION
                        "A list of entries containing information about
                        the device's MacIP clients."
              ::= { macipParams 19 }

          macipClientEntry OBJECT-TYPE
              SYNTAX    MacipClientEntry
              ACCESS    not-accessible
              STATUS    mandatory
              DESCRIPTION
                        "An entry containing information about one of
                        the device's MacIP clients."
              INDEX     { macipClientIpAddr }
              ::= { macipClientTable 1 }

          MacipClientEntry ::=
              SEQUENCE {
                  macipClientIpAddr
                      IpAddress,
                  macipClientIpAddrType
                      INTEGER,
                  macipClientAtAddr
                      DdpAddress,
                  macipClientIdleTime
                      INTEGER
              }

          macipClientIpAddr OBJECT-TYPE
              SYNTAX    IpAddress
              ACCESS    read-only
              STATUS    mandatory
              DESCRIPTION
                        "The IP address assigned to this MacIP client."
              ::= { macipClientEntry 1 }

          macipClientIpAddrType OBJECT-TYPE
              SYNTAX    INTEGER {
                            static(1),
                            dynamic(2)
                        }
              ACCESS    read-only
              STATUS    mandatory
              DESCRIPTION
                        "Indicates whether the IP address assigned to
                        this MacIP client is a static or dynamic IP
                        address."
              ::= { macipClientEntry 2 }

          macipClientAtAddr OBJECT-TYPE
              SYNTAX    DdpAddress
              ACCESS    read-only
              STATUS    mandatory
              DESCRIPTION
                        "The AppleTalk address of this MacIP client."
              ::= { macipClientEntry 3 }

          macipClientIdleTime OBJECT-TYPE
              SYNTAX    INTEGER
              ACCESS    read-only
              STATUS    mandatory
              DESCRIPTION
                        "The length of time in seconds that this MacIP
                        client has been idle."
              ::= { macipClientEntry 4 }


          --  The dhcpParams group

          --  This group contains definitions of objects that control
          --  the device's implementation of the Dynamic Host
          --  Configuration Protocol (DHCP).

          dhcpConfig     OBJECT IDENTIFIER ::= { dhcpParams 1 }
          dhcpInfo       OBJECT IDENTIFIER ::= { dhcpParams 2 }

          dhcpSupport OBJECT-TYPE
              SYNTAX    INTEGER {
                            enabled(1),
                            disabled(2)
                        }
              ACCESS    read-write
              STATUS    mandatory
              DESCRIPTION
                        "Indicates whether or not DHCP support will be
                        enabled when the device is next restarted."
              ::= { dhcpConfig 1 }

          dhcpFirstClientAddr OBJECT-TYPE
              SYNTAX    IpAddress
              ACCESS    read-write
              STATUS    mandatory
              DESCRIPTION
                        "Indicates the first IP address available for
                        assignment to DHCP clients.  The network portion
                        of this IP address must match the network
                        portion of the device's IP address on the
                        Ethernet interface."
              ::= { dhcpConfig 2 }

          dhcpNumClientAddrs OBJECT-TYPE
              SYNTAX    INTEGER
              ACCESS    read-write
              STATUS    mandatory
              DESCRIPTION
                        "Indicates the initial size, when the device is
                        next restarted, of the pool of IP addresses
                        available for assignment to clients requesting
                        IP addresses via DHCP.  The value of this object
                        may not exceed the value of the
                        dhcpMaxClientAddrs object."
              ::= { dhcpConfig 3 }

          dhcpMaxClientAddrs OBJECT-TYPE
              SYNTAX    INTEGER
              ACCESS    read-only
              STATUS    mandatory
              DESCRIPTION
                        "Indicates the maximum value of the
                        dhcpNumClientAddrs object."
              ::= { dhcpConfig 4 }

          dhcpServerName OBJECT-TYPE
              SYNTAX    OCTET STRING (SIZE(0..63))
              ACCESS    read-write
              STATUS    mandatory
              DESCRIPTION
                        "The name the DHCP server uses to identify
                        itself to DHCP clients."
              ::= { dhcpConfig 5 }


          dhcpOptions    OBJECT IDENTIFIER ::= { dhcpConfig 6 }


          --  The DHCP Option Table

          dhcpOptionTable OBJECT-TYPE
              SYNTAX    SEQUENCE OF DhcpOptionEntry
              ACCESS    not-accessible
              STATUS    mandatory
              DESCRIPTION
                        "A list of entries containing information about
                        the DHCP options served to DHCP clients."
              ::= { dhcpOptions 1 }

          dhcpOptionEntry OBJECT-TYPE
              SYNTAX    DhcpOptionEntry
              ACCESS    not-accessible
              STATUS    mandatory
              DESCRIPTION
                        "An entry containing information about one of
                        the DHCP options served to DHCP clients."
              INDEX     { dhcpOptionCode }
              ::= { dhcpOptionTable 1 }

          DhcpOptionEntry ::=
              SEQUENCE {
                  dhcpOptionCode
                      INTEGER (0..255),
                  dhcpOptionName
                      DisplayString,
                  dhcpOptionValueObject
                      OBJECT IDENTIFIER,
                  dhcpOptionStatus
                      INTEGER
              }

          dhcpOptionCode OBJECT-TYPE
              SYNTAX    INTEGER (0..255)
              ACCESS    read-only
              STATUS    mandatory
              DESCRIPTION
                        "The option code for the DHCP option described
                        by this entry."
              REFERENCE
                        "DHCP Options and BOOTP Vendor Extensions, RFC
                        1533"
              ::= { dhcpOptionEntry 1 }

          dhcpOptionName OBJECT-TYPE
              SYNTAX    DisplayString
              ACCESS    read-only
              STATUS    mandatory
              DESCRIPTION
                        "The name of the DHCP option described by this
                        entry."
              ::= { dhcpOptionEntry 2 }

          dhcpOptionValueObject OBJECT-TYPE
              SYNTAX    OBJECT IDENTIFIER
              ACCESS    read-only
              STATUS    mandatory
              DESCRIPTION
                        "The authoritatively-assigned name of the MIB
                        object that is used to configure the value
                        served to clients requesting the DHCP option
                        described by this entry."
              ::= { dhcpOptionEntry 3 }

          dhcpOptionStatus OBJECT-TYPE
              SYNTAX    INTEGER {
                            beingServed(1),
                            notBeingServed(2)
                        }
              ACCESS    read-write
              STATUS    mandatory
              DESCRIPTION
                        "Indicates whether or not the DHCP option
                        described by this entry is currently being
                        served to DHCP clients."
              ::= { dhcpOptionEntry 4 }

          dhcpDefaultGateway OBJECT-TYPE
              SYNTAX    IpAddress
              ACCESS    read-write
              STATUS    mandatory
              DESCRIPTION
                        "The router IP address sent to clients
                        requesting the Router Option (DHCP option code
                        3).

                        The default value for this object will be the IP
                        address of the device's default gateway if that
                        address identifies a router on the DHCP client
                        subnet; otherwise, the default value for this
                        object will be the device's IP address on the
                        DHCP client subnet."
              ::= { dhcpOptions 2 }

          dhcpDNSServerTable OBJECT-TYPE
              SYNTAX    SEQUENCE OF DhcpDNSServerEntry
              ACCESS    not-accessible
              STATUS    mandatory
              DESCRIPTION
                        "A list of entries corresponding to the Domain
                        Name System name servers in the list of such
                        servers sent to DHCP clients requesting the
                        Domain Name Server Option (DHCP option code 6).

                        The default values for the entries in this table
                        are the values of the entries, if any, in the
                        ipDNSServerTable.

                        This table supports 'conceptual row creation'
                        according to section 3.2(3) of RFC 1212:  To add
                        a new row to this table, a management station
                        must provide a value for the new instance of the
                        dhcpDNSServerAddress object, and may, in
                        addition, provide values for any or all of the
                        remaining read-write object instances in the new
                        row.  If no value is supplied for the
                        corresponding instance of the
                        dhcpDNSServerStatus object, its value will
                        default to 'valid(1)'."
              ::= { dhcpOptions 3 }

          dhcpDNSServerEntry OBJECT-TYPE
              SYNTAX    DhcpDNSServerEntry
              ACCESS    not-accessible
              STATUS    mandatory
              DESCRIPTION
                        "An entry corresponding to a Domain Name System
                        name server in the list of such servers sent to
                        DHCP clients requesting the Domain Name Server
                        Option (DHCP option code 6)."
              INDEX     { dhcpDNSServerIndex }
              ::= { dhcpDNSServerTable 1 }

          DhcpDNSServerEntry ::=
              SEQUENCE {
                  dhcpDNSServerIndex
                      INTEGER,
                  dhcpDNSServerAddress
                      IpAddress,
                  dhcpDNSServerStatus
                      INTEGER
              }

          dhcpDNSServerIndex OBJECT-TYPE
              SYNTAX    INTEGER
              ACCESS    read-only
              STATUS    mandatory
              DESCRIPTION
                        "A unique value for each Domain Name System name
                        server in the list of such servers to be sent to
                        DHCP clients requesting the Domain Name Server
                        Option (DHCP option code 6).

                        The value of this object ranges between one and
                        the number of servers in the list.  Servers are
                        listed in order of preference:  A server with a
                        lower-valued dhcpDNSServerIndex is preferred
                        over a server with a higher-valued
                        dhcpDNSServerIndex."
              ::= { dhcpDNSServerEntry 1 }

          dhcpDNSServerAddress OBJECT-TYPE
              SYNTAX    IpAddress
              ACCESS    read-write
              STATUS    mandatory
              DESCRIPTION
                        "The IP address of the Domain Name System name
                        server described by this entry."
              ::= { dhcpDNSServerEntry 2 }

          dhcpDNSServerStatus OBJECT-TYPE
              SYNTAX    INTEGER {
                            valid(1),
                            invalid(2)
                        }
              ACCESS    read-write
              STATUS    mandatory
              DESCRIPTION
                        "The status of this entry.

                        Setting this object to the value 'invalid(2)'
                        has the effect of invalidating the corresponding
                        entry in the dhcpDNSServerTable.  That is, it
                        effectively disassociates the mapping identified
                        with said entry.  It is an implementation-
                        specific matter as to whether the agent removes
                        an invalidated entry from the table.
                        Accordingly, management stations must be
                        prepared to receive from agents tabular
                        information corresponding to entries not
                        currently in use.  Proper interpretation of such
                        entries requires examination of the relevant
                        dhcpDNSServerStatus object."
              ::= { dhcpDNSServerEntry 3 }

          dhcpDomainName OBJECT-TYPE
              SYNTAX    OCTET STRING
              ACCESS    read-write
              STATUS    mandatory
              DESCRIPTION
                        "The domain name sent to DHCP clients requesting
                        the Domain Name Option (DHCP option code 15).

                        The default value for this object is the value
                        of the ipDomainName object."
              ::= { dhcpOptions 4 }

          dhcpNetBiosNameServer OBJECT-TYPE
              SYNTAX    IpAddress
              ACCESS    read-write
              STATUS    mandatory
              DESCRIPTION
                        "Indicates the value of the NetBIOS over TCP/IP
                        Name Server Option (DHCP option code 44) to be
                        sent to DHCP clients."
              ::= { dhcpOptions 5 }

          dhcpNetBiosTcpNodeType OBJECT-TYPE
              SYNTAX    INTEGER {
                            nodeTypeB(1),
                            nodeTypeP(2),
                            nodeTypeM(4),
                            nodeTypeH(8)
                        }
              ACCESS    read-write
              STATUS    mandatory
              DESCRIPTION
                        "Indicates the value of the NetBIOS over TCP/IP
                        Node Type Option (DHCP option code 46) to be
                        sent to DHCP clients."
              ::= { dhcpOptions 6 }

          dhcpNetBiosTcpScope OBJECT-TYPE
              SYNTAX    OCTET STRING (SIZE(0..255))
              ACCESS    read-write
              STATUS    mandatory
              DESCRIPTION
                        "Indicates the value of the NetBIOS over TCP/IP
                        Scope Option (DHCP option code 47) to be sent to
                        DHCP clients."
              ::= { dhcpOptions 7 }


          --  The DHCP Info Group

          dhcpUnassignedClientAddrs OBJECT-TYPE
              SYNTAX    Gauge
              ACCESS    read-only
              STATUS    mandatory
              DESCRIPTION
                        "Indicates the number of unassigned IP addresses
                        available for assignment to clients requesting
                        an IP address via DHCP."
              ::= { dhcpInfo 1 }


          --  The DHCP Client Table

          dhcpClientTable OBJECT-TYPE
              SYNTAX    SEQUENCE OF DhcpClientEntry
              ACCESS    not-accessible
              STATUS    mandatory
              DESCRIPTION
                        "A list of entries containing information about
                        the device's dhcp clients."
              ::= { dhcpInfo 2 }

          dhcpClientEntry OBJECT-TYPE
              SYNTAX    DhcpClientEntry
              ACCESS    not-accessible
              STATUS    mandatory
              DESCRIPTION
                        "An entry containing information about one of
                        the device's dhcp clients."
              INDEX     { dhcpClientIpAddr }
              ::= { dhcpClientTable 1 }

          DhcpClientEntry ::=
              SEQUENCE {
                  dhcpClientIpAddr
                      IpAddress,
                  dhcpClientIdentifier
                      OCTET STRING (SIZE(0..255)),
                  dhcpClientState
                      INTEGER,
                  dhcpClientTimeLeft
                      INTEGER
              }

          dhcpClientIpAddr OBJECT-TYPE
              SYNTAX    IpAddress
              ACCESS    read-only
              STATUS    mandatory
              DESCRIPTION
                        "The IP address assigned to this DHCP client."
              ::= { dhcpClientEntry 1 }

          dhcpClientIdentifier OBJECT-TYPE
              SYNTAX    OCTET STRING (SIZE(0..255))
              ACCESS    read-only
              STATUS    mandatory
              DESCRIPTION
                        "The value of the Client Identifier Option (DHCP
                        option code 61) supplied by this DHCP client."
              ::= { dhcpClientEntry 2 }

          dhcpClientState OBJECT-TYPE
              SYNTAX    INTEGER {
                            offered(1),
                            leased(2)
                        }
              ACCESS    read-only
              STATUS    mandatory
              DESCRIPTION
                        "The status of the IP address assignment to this
                        DHCP client.

                        The value 'offered(1)' indicates that the IP
                        address has been offered to, but not accepted
                        by, this DHCP client.  The value 'leased(2)'
                        indicates that the IP address has been offered
                        to and accepted by this DHCP client."
              ::= { dhcpClientEntry 3 }

          dhcpClientTimeLeft OBJECT-TYPE
              SYNTAX    INTEGER
              ACCESS    read-only
              STATUS    mandatory
              DESCRIPTION
                        "The length of time in seconds remaining on the
                        IP address lease to this DHCP client."
              ::= { dhcpClientEntry 4 }


          --  The DHCP Most Recent Binding Table

          dhcpMRBindingTable OBJECT-TYPE
              SYNTAX    SEQUENCE OF DhcpMRBindingEntry
              ACCESS    not-accessible
              STATUS    mandatory
              DESCRIPTION
                        "A list of entries containing information about
                        the most recent binding of each of the IP
                        addresses in the device's DHCP address pool to a
                        DHCP client."
              ::= { dhcpInfo 3 }

          dhcpMRBindingEntry OBJECT-TYPE
              SYNTAX    DhcpMRBindingEntry
              ACCESS    not-accessible
              STATUS    mandatory
              DESCRIPTION
                        "An entry containing information about the most
                        recent binding of one of the IP addresses in the
                        device's DHCP address pool to a DHCP client."
              INDEX     { dhcpMRBindingIpAddr }
              ::= { dhcpMRBindingTable 1 }

          DhcpMRBindingEntry ::=
              SEQUENCE {
                  dhcpMRBindingIpAddr
                      IpAddress,
                  dhcpMRBindingClientIdentifier
                      OCTET STRING (SIZE(0..255))
              }

          dhcpMRBindingIpAddr OBJECT-TYPE
              SYNTAX    IpAddress
              ACCESS    read-only
              STATUS    mandatory
              DESCRIPTION
                        "The IP address for which this entry describes
                        the most recent binding to a DHCP client."
              ::= { dhcpMRBindingEntry 1 }

          dhcpMRBindingClientIdentifier OBJECT-TYPE
              SYNTAX    OCTET STRING (SIZE(0..255))
              ACCESS    read-only
              STATUS    mandatory
              DESCRIPTION
                        "The value of the Client Identifier Option (DHCP
                        option 61) specified by the client to which the
                        IP address identified by this entry was most
                        recently bound via DHCP.  A zero-length OCTET
                        STRING value indicates that the IP address
                        identified by this entry has never been bound to
                        a DHCP client."
              ::= { dhcpMRBindingEntry 2 }



          aurpConfig     OBJECT IDENTIFIER ::= { aurpParams 1 }
          aurpInfo       OBJECT IDENTIFIER ::= { aurpParams 2 }


          --  The AURP Config Group

          --  The objects in this group provide information for configuring
          --  the device's implementation of the AppleTalk Update-based
          --  Routing Protocol (AURP).  Changes to the values of objects
          --  in this group will take effect when the device is next
          --  restarted.

          --  The objects in this group are not applicable to the Netopia
          --  PN630 or Netopia PN640.


          --  The AURP Tunnel Configuration Table

          aurpTunCfgTable OBJECT-TYPE
              SYNTAX    SEQUENCE OF AurpTunCfgEntry
              ACCESS    not-accessible
              STATUS    mandatory
              DESCRIPTION
                        "A list of entries providing information for
                        configuring the device's AURP tunnels when the
                        device is next restarted."
              ::= { aurpConfig 1 }

          aurpTunCfgEntry OBJECT-TYPE
              SYNTAX    AurpTunCfgEntry
              ACCESS    not-accessible
              STATUS    mandatory
              DESCRIPTION
                        "An entry providing information for configuring
                        one of the device's AURP tunnels when the device
                        is next restarted."
              INDEX     { aurpTunCfgPortIndex }
              ::= { aurpTunCfgTable 1 }

          AurpTunCfgEntry ::=
              SEQUENCE {
                  aurpTunCfgPortIndex
                      INTEGER,
                  aurpTunCfgSupport
                      INTEGER,
                  aurpTunCfgAcceptAnyPartner
                      INTEGER,
                  aurpTunCfgNetworkRemapping
                      INTEGER,
                  aurpTunCfgClustering
                      INTEGER,
                  aurpTunCfgHopCountReduction
                      INTEGER
              }

          aurpTunCfgPortIndex OBJECT-TYPE
              SYNTAX    INTEGER
              ACCESS    read-only
              STATUS    mandatory
              DESCRIPTION
                        "The AppleTalk port associated with the AURP
                        tunnel.  The AppleTalk port identified by a
                        particular value of this object is the same port
                        as is identified by the same value of the
                        atportIndex object."
              ::= { aurpTunCfgEntry 1 }

          aurpTunCfgSupport OBJECT-TYPE
              SYNTAX    INTEGER {
                            enabled(1),
                            disabled(2)
                        }
              ACCESS    read-write
              STATUS    mandatory
              DESCRIPTION
                        "Indicates whether or not AURP support will be
                        enabled when the device is next restarted."
              ::= { aurpTunCfgEntry 2 }

          aurpTunCfgAcceptAnyPartner OBJECT-TYPE
              SYNTAX    INTEGER {
                            acceptAnyPartner(1),
                            dontAcceptAnyPartner(2)
                        }
              ACCESS    read-write
              STATUS    mandatory
              DESCRIPTION
                        "Indicates whether or not the device will accept
                        a connection from an AURP partner for which
                        there is no entry in the aurpCfgPartnerTable."
              ::= { aurpTunCfgEntry 3 }

          aurpTunCfgNetworkRemapping OBJECT-TYPE
              SYNTAX    INTEGER {
                            enabled(1),
                            disabled(2)
                        }
              ACCESS    read-write
              STATUS    mandatory
              DESCRIPTION
                        "Indicates whether or not network number
                        remapping will be enabled when the device is
                        next restarted."
              ::= { aurpTunCfgEntry 4 }

          aurpTunCfgClustering OBJECT-TYPE
              SYNTAX    INTEGER {
                            enabled(1),
                            disabled(2)
                        }
              ACCESS    read-write
              STATUS    mandatory
              DESCRIPTION
                        "Indicates whether or not clustering will be
                        enabled when the device is next restarted.
                        Because clustering assumes network number
                        remapping, the value of this object is
                        meaningful only if the value of the
                        aurpTunCfgNetworkRemapping object is
                        'enabled(1)'."
              ::= { aurpTunCfgEntry 5 }

          aurpTunCfgHopCountReduction OBJECT-TYPE
              SYNTAX    INTEGER {
                            enabled(1),
                            disabled(2)
                        }
              ACCESS    read-write
              STATUS    mandatory
              DESCRIPTION
                        "Indicates whether or not hop count reduction
                        will be enabled when the device is next
                        restarted.  Because hop count reduction assumes
                        network number remapping, the value of this
                        object is meaningful only if the value of the
                        aurpTunCfgNetworkRemapping object is
                        'enabled(1)'."
              ::= { aurpTunCfgEntry 6 }


          --  The AURP Remapping Range Configuration Table

          aurpRemapRangeCfgTable OBJECT-TYPE
              SYNTAX    SEQUENCE OF AurpRemapRangeCfgEntry
              ACCESS    not-accessible
              STATUS    mandatory
              DESCRIPTION
                        "A list of entries providing the AppleTalk
                        network address ranges reserved for use in
                        remapping imported networks on the device's AURP
                        tunnels when the device is next restarted."
              ::= { aurpConfig 2 }

          aurpRemapRangeCfgEntry OBJECT-TYPE
              SYNTAX    AurpRemapRangeCfgEntry
              ACCESS    not-accessible
              STATUS    mandatory
              DESCRIPTION
                        "An entry providing an AppleTalk network address
                        range reserved for use in remapping imported
                        networks on one of the device's AURP tunnels
                        when the device is next restarted."
              INDEX     { aurpRemapRangeCfgPortIndex, aurpRemapRangeCfgIndex }
              ::= { aurpRemapRangeCfgTable 1 }

          AurpRemapRangeCfgEntry ::=
              SEQUENCE {
                  aurpRemapRangeCfgPortIndex
                      INTEGER,
                  aurpRemapRangeCfgIndex
                      INTEGER,
                  aurpRemapRangeCfgNetStart
                      ATNetworkNumber,
                  aurpRemapRangeCfgNetEnd
                      ATNetworkNumber
              }

          aurpRemapRangeCfgPortIndex OBJECT-TYPE
              SYNTAX    INTEGER
              ACCESS    read-only
              STATUS    mandatory
              DESCRIPTION
                        "The AppleTalk port associated with the AURP
                        tunnel for which this entry describes an
                        AppleTalk network number range that will be
                        reserved for use in remapping imported networks
                        when the device is next restarted.  The
                        AppleTalk port identified by a particular value
                        of this object is the same port that is
                        identified by the same value of the atportIndex
                        object."
              ::= { aurpRemapRangeCfgEntry 1 }

          aurpRemapRangeCfgIndex OBJECT-TYPE
              SYNTAX    INTEGER
              ACCESS    read-only
              STATUS    mandatory
              DESCRIPTION
                        "A unique value for each of the AppleTalk
                        network number ranges reserved for use in
                        remapping imported networks on this tunnel when
                        the device is next restarted."
              ::= { aurpRemapRangeCfgEntry 2 }

          aurpRemapRangeCfgNetStart OBJECT-TYPE
              SYNTAX    ATNetworkNumber
              ACCESS    read-only
              STATUS    mandatory
              DESCRIPTION
                        "The first AppleTalk network number of the range
                        of network numbers reserved for remapping
                        imported networks."
              ::= { aurpRemapRangeCfgEntry 3 }

          aurpRemapRangeCfgNetEnd OBJECT-TYPE
              SYNTAX    ATNetworkNumber
              ACCESS    read-write
              STATUS    mandatory
              DESCRIPTION
                        "The last AppleTalk network number of the range
                        of network numbers reserved for remapping
                        imported networks."
              ::= { aurpRemapRangeCfgEntry 4 }


          --  The AURP Configured Partner Table

          aurpCfgPartnerTable OBJECT-TYPE
              SYNTAX    SEQUENCE OF AurpCfgPartnerEntry
              ACCESS    not-accessible
              STATUS    mandatory
              DESCRIPTION
                        "A list of entries containing information about
                        the AURP partners to which the device can place
                        connections and/or from which the device will
                        accept connections.

                        The aurpCfgPartnerTable object supports
                        'conceptual row creation' according to section
                        3.2(3) of RFC 1212:  To add a new row to the
                        aurpCfgPartnerTable, a management station must
                        provide a value for the new instance of the
                        aurpCfgPartnerInitiateConnection object, and
                        may, in addition, provide values for any or all
                        of the remaining object instances in the new row
                        that have read-write ACCESS.

                        If no value is supplied for the corresponding
                        instance of the aurpCfgPartnerStatus object, its
                        value will default to 'valid(1)'.  The value of
                        the instance of the aurpCfgPartnerIpAddr object
                        in a newly created row is always the unknown IP
                        address 0.0.0.0."
              ::= { aurpConfig 3 }

          aurpCfgPartnerEntry OBJECT-TYPE
              SYNTAX    AurpCfgPartnerEntry
              ACCESS    not-accessible
              STATUS    mandatory
              DESCRIPTION
                        "An entry containing information about one of
                        the AURP partners to which the device can
                        initiate a connection and/or from which the
                        device will accept a connection."
              INDEX     { aurpCfgPartnerPortIndex, aurpCfgPartnerName }
              ::= { aurpCfgPartnerTable 1 }

          AurpCfgPartnerEntry ::=
              SEQUENCE {
                  aurpCfgPartnerPortIndex
                      INTEGER,
                  aurpCfgPartnerName
                      HostNameOrIpAddr,
                  aurpCfgPartnerIpAddr
                      IpAddress,
                  aurpCfgPartnerInitiateConnection
                      INTEGER,
                  aurpCfgPartnerStatus
                      INTEGER
              }

          aurpCfgPartnerPortIndex OBJECT-TYPE
              SYNTAX    INTEGER
              ACCESS    read-only
              STATUS    mandatory
              DESCRIPTION
                        "The AppleTalk port associated with the AURP
                        tunnel for which this entry describes a
                        respected AURP partner.  The AppleTalk port
                        identified by a particular value of this object
                        is the same port as is identified by the same
                        value of the atportIndex object."
              ::= { aurpCfgPartnerEntry 1 }

          aurpCfgPartnerName OBJECT-TYPE
              SYNTAX    HostNameOrIpAddr
              ACCESS    read-only
              STATUS    mandatory
              DESCRIPTION
                        "The name of this AURP partner.

                        The value of this object can be a fully- or
                        partially-qualified domain name system (dns)
                        name, or it can be an IP address in the familiar
                        'dotted-quad' notation.

                        If the value of this object is a fully- or
                        partially-qualified dns name, the device will
                        attempt to use the Domain Name System to convert
                        the name to an IP address before initiating a
                        connection with this AURP partner."
              ::= { aurpCfgPartnerEntry 2 }

          aurpCfgPartnerIpAddr OBJECT-TYPE
              SYNTAX    IpAddress
              ACCESS    read-only
              STATUS    mandatory
              DESCRIPTION
                        "The IP address of this AURP partner."
              ::= { aurpCfgPartnerEntry 3 }

          aurpCfgPartnerInitiateConnection OBJECT-TYPE
              SYNTAX    INTEGER {
                            initiate(1),
                            dontInitiate(2)
                        }
              ACCESS    read-write
              STATUS    mandatory
              DESCRIPTION
                        "Indicates whether or not the device will
                        attempt to initiate a connection to this AURP
                        partner when the device is next restarted."
              ::= { aurpCfgPartnerEntry 4 }

          aurpCfgPartnerStatus OBJECT-TYPE
              SYNTAX    INTEGER {
                            valid(1),
                            invalid(2)
                        }
              ACCESS    read-write
              STATUS    mandatory
              DESCRIPTION
                        "Indicates the status of this entry.

                        Setting the value of this object to 'invalid(2)'
                        has the effect of invalidating the corresponding
                        entry in the aurpCfgPartnerTable.

                        Whether an agent removes an invalidated entry
                        from the table is an implementation-specific
                        matter.  Accordingly, management stations must
                        be prepared to receive tabular information from
                        agents that correspond to entries not currently
                        in use.  Proper interpretation of such entries
                        requires examination of the relevant
                        aurpCfgPartnerStatus object."
              ::= { aurpCfgPartnerEntry 5 }


          --  The AURP Info Group

          --  The objects in this group provide information about the
          --  device's implementation of the AppleTalk Update-Based
          --  Routing Protocol (AURP).

          --  The objects in this group are not applicable to the
          --  Netopia PN630 or Netopia PN640.


          --  The AURP Tunnel Table

          aurpTunnelTable OBJECT-TYPE
              SYNTAX    SEQUENCE OF AurpTunnelEntry
              ACCESS    not-accessible
              STATUS    mandatory
              DESCRIPTION
                        "A list of entries containing information about
                        the device's AURP tunnels."
              ::= { aurpInfo 1 }

          aurpTunnelEntry OBJECT-TYPE
              SYNTAX    AurpTunnelEntry
              ACCESS    not-accessible
              STATUS    mandatory
              DESCRIPTION
                        "An entry containing information about one of
                        the device's AURP tunnels."
              INDEX     { aurpTunnelPortIndex }
              ::= { aurpTunnelTable 1 }

          AurpTunnelEntry ::=
              SEQUENCE {
                  aurpTunnelPortIndex
                      INTEGER,
                  aurpTunnelPortType
                      INTEGER,
                  aurpTunnelStatus
                      INTEGER,
                  aurpTunnelAcceptAnyPartner
                      INTEGER,
                  aurpTunnelNetworkRemapping
                      INTEGER,
                  aurpTunnelClustering
                      INTEGER,
                  aurpTunnelHopCountReduction
                      INTEGER,
                  aurpTunnelDomainIdentifier
                      OCTET STRING,
                  aurpTunnelOpenRequests
                      Counter,
                  aurpTunnelRouterDowns
                      Counter,
                  aurpTunnelRemapErrors
                      Counter,
                  aurpTunnelClusterErrors
                      Counter,
                  aurpTunnelBrokenConnections
                      Counter,
                  aurpTunnelInvalidVersionErrors
                      Counter,
                  aurpTunnelAuthenticationErrors
                      Counter
              }

          aurpTunnelPortIndex OBJECT-TYPE
              SYNTAX    INTEGER
              ACCESS    read-only
              STATUS    mandatory
              DESCRIPTION
                        "The AppleTalk port associated with this tunnel.
                        The AppleTalk port identified by a particular
                        value of this object is the same port as is
                        identified by the same value of the atportIndex
                        object."
              ::= { aurpTunnelEntry 1 }

          aurpTunnelPortType OBJECT-TYPE
              SYNTAX    INTEGER {
                            other(1),
                            ip(2),
                            serialPpp(3),
                            serialNonStandard(4),
                            frameRelay(5),
                            x25(6),
                            osi(7),
                            decnetIV(8),
                            ipx(9)
                        }
              ACCESS    read-only
              STATUS    mandatory
              DESCRIPTION
                        "The type of the foreign network underlying the
                        AURP tunnel."
              ::= { aurpTunnelEntry 2 }

          aurpTunnelStatus OBJECT-TYPE
              SYNTAX    INTEGER {
                            other(1),
                            hasActiveConnections(2),
                            noActiveConnections(3),
                            inactive(4),
                            inactiveLoopDetected(5)
                        }
              ACCESS    read-only
              STATUS    mandatory
              DESCRIPTION
                        "The operational status of this AURP tunnel."
              ::= { aurpTunnelEntry 3 }

          aurpTunnelAcceptAnyPartner OBJECT-TYPE
              SYNTAX    INTEGER {
                            accept(1),
                            dontAccept(2)
                        }
              ACCESS    read-only
              STATUS    mandatory
              DESCRIPTION
                        "Indicates whether or not the device will accept
                        connections on this tunnel from AURP partners
                        for which there was no entry in the
                        aurpCfgPartnerTable when the device was last
                        restarted."
              ::= { aurpTunnelEntry 4 }

          aurpTunnelNetworkRemapping OBJECT-TYPE
              SYNTAX    INTEGER {
                            active(1),
                            inactive(2)
                        }
              ACCESS    read-only
              STATUS    mandatory
              DESCRIPTION
                        "Indicates whether or not network number
                        remapping is enabled on this tunnel."
              ::= { aurpTunnelEntry 5 }

          aurpTunnelClustering OBJECT-TYPE
              SYNTAX    INTEGER {
                            active(1),
                            inactive(2)
                        }
              ACCESS    read-only
              STATUS    mandatory
              DESCRIPTION
                        "Indicates whether or not clustering of remapped
                        networks is enabled on this tunnel."
              ::= { aurpTunnelEntry 6 }

          aurpTunnelHopCountReduction OBJECT-TYPE
              SYNTAX    INTEGER {
                            active(1),
                            inactive(2)
                        }
              ACCESS    read-only
              STATUS    mandatory
              DESCRIPTION
                        "Indicates whether or not hop count reduction is
                        enabled on this tunnel."
              ::= { aurpTunnelEntry 7 }

          aurpTunnelDomainIdentifier OBJECT-TYPE
              SYNTAX    OCTET STRING
              ACCESS    read-only
              STATUS    mandatory
              DESCRIPTION
                        "The domain identifier associated with this
                        tunnel."
              ::= { aurpTunnelEntry 8 }

          aurpTunnelOpenRequests OBJECT-TYPE
              SYNTAX    Counter
              ACCESS    read-only
              STATUS    mandatory
              DESCRIPTION
                        "The number of Open Request packets that have
                        been received on this tunnel."
              ::= { aurpTunnelEntry 9 }

          aurpTunnelRouterDowns OBJECT-TYPE
              SYNTAX    Counter
              ACCESS    read-only
              STATUS    mandatory
              DESCRIPTION
                        "The number of Router Down packets that have
                        been received on this tunnel."
              ::= { aurpTunnelEntry 10 }

          aurpTunnelRemapErrors OBJECT-TYPE
              SYNTAX    Counter
              ACCESS    read-only
              STATUS    mandatory
              DESCRIPTION
                        "The number of remapping-specific errors that
                        have occurred on this tunnel."
              ::= { aurpTunnelEntry 11 }

          aurpTunnelClusterErrors OBJECT-TYPE
              SYNTAX    Counter
              ACCESS    read-only
              STATUS    mandatory
              DESCRIPTION
                        "The number of clustering-specific errors that
                        have occurred on this tunnel."
              ::= { aurpTunnelEntry 12 }

          aurpTunnelBrokenConnections OBJECT-TYPE
              SYNTAX    Counter
              ACCESS    read-only
              STATUS    mandatory
              DESCRIPTION
                        "The number of times a point-to-point connection
                        on this tunnel has been broken or dropped."
              ::= { aurpTunnelEntry 13 }

          aurpTunnelInvalidVersionErrors OBJECT-TYPE
              SYNTAX    Counter
              ACCESS    read-only
              STATUS    mandatory
              DESCRIPTION
                        "The number of packets with invalid version
                        errors received on this tunnel."
              ::= { aurpTunnelEntry 14 }

          aurpTunnelAuthenticationErrors OBJECT-TYPE
              SYNTAX    Counter
              ACCESS    read-only
              STATUS    mandatory
              DESCRIPTION
                        "The number of authentication errors received on
                        this tunnel."
              ::= { aurpTunnelEntry 15 }


          --  The AURP Connection Table

          aurpConnectionTable OBJECT-TYPE
              SYNTAX    SEQUENCE OF AurpConnectionEntry
              ACCESS    not-accessible
              STATUS    mandatory
              DESCRIPTION
                        "A list of entries containing information about
                        the device's AURP connections."
              ::= { aurpInfo 2 }

          aurpConnectionEntry OBJECT-TYPE
              SYNTAX    AurpConnectionEntry
              ACCESS    not-accessible
              STATUS    mandatory
              DESCRIPTION
                        "An entry describing one of the device's AURP
                        connections."
              INDEX     { aurpConnectionPortIndex, aurpConnectionIndex }
              ::= { aurpConnectionTable 1 }

          AurpConnectionEntry ::=
              SEQUENCE {
                  aurpConnectionPortIndex
                      INTEGER,
                  aurpConnectionIndex
                      INTEGER,
                  aurpConnectionAddress
                      OCTET STRING,
                  aurpConnectionSentRIs
                      Counter,
                  aurpConnectionRecvRIs
                      Counter,
                  aurpConnectionSentZIs
                      Counter,
                  aurpConnectionRecvZIs
                      Counter,
                  aurpConnectionSentGZNs
                      Counter,
                  aurpConnectionRecvGZNs
                      Counter,
                  aurpConnectionSentGDZLs
                      Counter,
                  aurpConnectionRecvGDZLs
                      Counter,
                  aurpConnectionBadSequence
                      Counter,
                  aurpConnectionUpdateSendingRate
                      INTEGER,
                  aurpConnectionLastHeardFromTimeout
                      INTEGER
              }

          aurpConnectionPortIndex OBJECT-TYPE
              SYNTAX    INTEGER
              ACCESS    read-only
              STATUS    mandatory
              DESCRIPTION
                        "The AppleTalk port associated with this
                        connection.  The AppleTalk port identified by a
                        particular value of this object is the same port
                        as is identified by the same value of the
                        atportIndex object.  The value of this object
                        identifies the same AURP tunnel as is identified
                        by the same value of aurpTunnelPortIndex."
              ::= { aurpConnectionEntry 1 }

          aurpConnectionIndex OBJECT-TYPE
              SYNTAX    INTEGER
              ACCESS    read-only
              STATUS    mandatory
              DESCRIPTION
                        "A unique value for each connection on this
                        port."
              ::= { aurpConnectionEntry 2 }

          aurpConnectionAddress OBJECT-TYPE
              SYNTAX    OCTET STRING
              ACCESS    read-only
              STATUS    mandatory
              DESCRIPTION
                        "The address of the remote router for this
                        connection.  This address is dependent on the
                        underlying network system as indicated by the
                        corresponding instance of aurpTunnelPortType."
              ::= { aurpConnectionEntry 3 }

          aurpConnectionSentRIs OBJECT-TYPE
              SYNTAX    Counter
              ACCESS    read-only
              STATUS    mandatory
              DESCRIPTION
                        "The number of Routing Information packets that
                        have been sent on this connection."
              ::= { aurpConnectionEntry 4 }

          aurpConnectionRecvRIs OBJECT-TYPE
              SYNTAX    Counter
              ACCESS    read-only
              STATUS    mandatory
              DESCRIPTION
                        "The number of Routing Information packets that
                        have been received on this connection."
              ::= { aurpConnectionEntry 5 }

          aurpConnectionSentZIs OBJECT-TYPE
              SYNTAX    Counter
              ACCESS    read-only
              STATUS    mandatory
              DESCRIPTION
                        "The number of Zone Information packets that
                        have been sent on this connection."
              ::= { aurpConnectionEntry 6 }

          aurpConnectionRecvZIs OBJECT-TYPE
              SYNTAX    Counter
              ACCESS    read-only
              STATUS    mandatory
              DESCRIPTION
                        "The number of Zone Information packets that
                        have been received on this connection."
              ::= { aurpConnectionEntry 7 }

          aurpConnectionSentGZNs OBJECT-TYPE
              SYNTAX    Counter
              ACCESS    read-only
              STATUS    mandatory
              DESCRIPTION
                        "The number of Get Zone Nets Request packets
                        that have been sent on this connection."
              ::= { aurpConnectionEntry 8 }

          aurpConnectionRecvGZNs OBJECT-TYPE
              SYNTAX    Counter
              ACCESS    read-only
              STATUS    mandatory
              DESCRIPTION
                        "The number of Get Zone Nets Request packets
                        that have been received on this connection."
              ::= { aurpConnectionEntry 9 }

          aurpConnectionSentGDZLs OBJECT-TYPE
              SYNTAX    Counter
              ACCESS    read-only
              STATUS    mandatory
              DESCRIPTION
                        "The number of Get Domain Zone List Request
                        packets that have sent on this connection."
              ::= { aurpConnectionEntry 10 }

          aurpConnectionRecvGDZLs OBJECT-TYPE
              SYNTAX    Counter
              ACCESS    read-only
              STATUS    mandatory
              DESCRIPTION
                        "The number of Get Domain Zone List Request
                        packets that have received on this connection."
              ::= { aurpConnectionEntry 11 }

          aurpConnectionBadSequence OBJECT-TYPE
              SYNTAX    Counter
              ACCESS    read-only
              STATUS    mandatory
              DESCRIPTION
                        "The number of unexpected sequence numbers
                        detected on this connection."
              ::= { aurpConnectionEntry 12 }

          aurpConnectionUpdateSendingRate OBJECT-TYPE
              SYNTAX    INTEGER
              ACCESS    read-only
              STATUS    mandatory
              DESCRIPTION
                        "The rate at which routing table updates are
                        sent on this connection, in seconds."
              ::= { aurpConnectionEntry 13 }

          aurpConnectionLastHeardFromTimeout OBJECT-TYPE
              SYNTAX    INTEGER
              ACCESS    read-only
              STATUS    mandatory
              DESCRIPTION
                        "The number of seconds to wait after last
                        hearing from the remote router before sending a
                        tickle."
              ::= { aurpConnectionEntry 14 }


          --  The AURP Remap Range Table

          aurpRemapRangeTable OBJECT-TYPE
              SYNTAX    SEQUENCE OF AurpRemapRangeEntry
              ACCESS    not-accessible
              STATUS    mandatory
              DESCRIPTION
                        "The list of tunnel remap ranges for this
                        router.  This contains only one entry for each
                        port in most cases."
              ::= { aurpInfo 3 }

          aurpRemapRangeEntry OBJECT-TYPE
              SYNTAX    AurpRemapRangeEntry
              ACCESS    not-accessible
              STATUS    mandatory
              DESCRIPTION
                        "The description of one of the remap ranges on
                        this router."
              INDEX     { aurpRemapRangePortIndex, aurpRemapRangeNetStart }
              ::= { aurpRemapRangeTable 1 }

          AurpRemapRangeEntry ::=
              SEQUENCE {
                  aurpRemapRangePortIndex
                      INTEGER,
                  aurpRemapRangeNetStart
                      ATNetworkNumber,
                  aurpRemapRangeNetEnd
                      ATNetworkNumber,
                  aurpRemapRangeRouterAddress
                      OCTET STRING
              }

          aurpRemapRangePortIndex OBJECT-TYPE
              SYNTAX    INTEGER
              ACCESS    read-only
              STATUS    mandatory
              DESCRIPTION
                        "The AppleTalk port associated with this remap
                        range."
              ::= { aurpRemapRangeEntry 1 }

          aurpRemapRangeNetStart OBJECT-TYPE
              SYNTAX    ATNetworkNumber
              ACCESS    read-only
              STATUS    mandatory
              DESCRIPTION
                        "The first AppleTalk network address in the
                        range of network addresses to be used for
                        remapping imported networks."
              ::= { aurpRemapRangeEntry 2 }

          aurpRemapRangeNetEnd OBJECT-TYPE
              SYNTAX    ATNetworkNumber
              ACCESS    read-only
              STATUS    mandatory
              DESCRIPTION
                        "The last AppleTalk network address in the range
                        of network addresses to be used for remapping
                        imported networks."
              ::= { aurpRemapRangeEntry 3 }

          aurpRemapRangeRouterAddress OBJECT-TYPE
              SYNTAX    OCTET STRING
              ACCESS    read-only
              STATUS    mandatory
              DESCRIPTION
                        "The address of the router for which this remap
                        range applies.  A null string indicates the
                        remap range will be used for all connections on
                        this port."
              ::= { aurpRemapRangeEntry 4 }


          --  The AURP Remap Table

          aurpRemapTable OBJECT-TYPE
              SYNTAX    SEQUENCE OF AurpRemapEntry
              ACCESS    not-accessible
              STATUS    mandatory
              DESCRIPTION
                        "The list of remapped networks."
              ::= { aurpInfo 4 }

          aurpRemapEntry OBJECT-TYPE
              SYNTAX    AurpRemapEntry
              ACCESS    not-accessible
              STATUS    mandatory
              DESCRIPTION
                        "The description of an imported, remapped
                        network."
              INDEX     { aurpRemapPortIndex, aurpRemapNetStart }
              ::= { aurpRemapTable 1 }

          AurpRemapEntry ::=
              SEQUENCE {
                  aurpRemapPortIndex
                      INTEGER,
                  aurpRemapNetStart
                      ATNetworkNumber,
                  aurpRemapNetEnd
                      ATNetworkNumber,
                  aurpRemapUIDI
                      OCTET STRING,
                  aurpRemapUINetStart
                      ATNetworkNumber,
                  aurpRemapUINetEnd
                      ATNetworkNumber
              }

          aurpRemapPortIndex OBJECT-TYPE
              SYNTAX    INTEGER
              ACCESS    read-only
              STATUS    mandatory
              DESCRIPTION
                        "The AppleTalk port associated with this
                        remapped network."
              ::= { aurpRemapEntry 1 }

          aurpRemapNetStart OBJECT-TYPE
              SYNTAX    ATNetworkNumber
              ACCESS    read-only
              STATUS    mandatory
              DESCRIPTION
                        "The first AppleTalk network address of the
                        remap range for this imported network."
              ::= { aurpRemapEntry 2 }

          aurpRemapNetEnd OBJECT-TYPE
              SYNTAX    ATNetworkNumber
              ACCESS    read-only
              STATUS    mandatory
              DESCRIPTION
                        "The last AppleTalk network address of the remap
                        range for this imported network."
              ::= { aurpRemapEntry 3 }

          aurpRemapUIDI OBJECT-TYPE
              SYNTAX    OCTET STRING
              ACCESS    read-only
              STATUS    mandatory
              DESCRIPTION
                        "The domain identifier portion of the unique
                        identifier associated with the imported network
                        that is being remapped."
              ::= { aurpRemapEntry 4 }

          aurpRemapUINetStart OBJECT-TYPE
              SYNTAX    ATNetworkNumber
              ACCESS    read-only
              STATUS    mandatory
              DESCRIPTION
                        "The first AppleTalk network address of the
                        range portion of the unique identifier
                        associated with the imported network that is
                        being remapped."
              ::= { aurpRemapEntry 5 }

          aurpRemapUINetEnd OBJECT-TYPE
              SYNTAX    ATNetworkNumber
              ACCESS    read-only
              STATUS    mandatory
              DESCRIPTION
                        "The last AppleTalk network address of the range
                        portion of the unique identifier associated with
                        the imported network that is being remapped."
              ::= { aurpRemapEntry 6 }


          --  The AURP Cluster Table

          aurpClusterTable OBJECT-TYPE
              SYNTAX    SEQUENCE OF AurpClusterEntry
              ACCESS    not-accessible
              STATUS    mandatory
              DESCRIPTION
                        "A list of entries describing the device's
                        clusters of imported, remapped networks."
              ::= { aurpInfo 5 }

          aurpClusterEntry OBJECT-TYPE
              SYNTAX    AurpClusterEntry
              ACCESS    not-accessible
              STATUS    mandatory
              DESCRIPTION
                        "An entry describing one of the device's
                        clusters of imported, remapped networks."
              INDEX     { aurpClusterPortIndex, aurpClusterIndex }
              ::= { aurpClusterTable 1 }

          AurpClusterEntry ::=
              SEQUENCE {
                  aurpClusterPortIndex
                      INTEGER,
                  aurpClusterIndex
                      INTEGER,
                  aurpClusterNetStart
                      ATNetworkNumber,
                  aurpClusterNetEnd
                      ATNetworkNumber,
                  aurpClusterUIDI
                      OCTET STRING,
                  aurpClusterNumberOfNetworks
                      INTEGER,
                  aurpClusterHopCount
                      INTEGER
              }

          aurpClusterPortIndex OBJECT-TYPE
              SYNTAX    INTEGER
              ACCESS    read-only
              STATUS    mandatory
              DESCRIPTION
                        "The AppleTalk port associated with this
                        cluster."
              ::= { aurpClusterEntry 1 }

          aurpClusterIndex OBJECT-TYPE
              SYNTAX    INTEGER
              ACCESS    read-only
              STATUS    mandatory
              DESCRIPTION
                        "A unique value for each of the device's
                        clusters on a port."
              ::= { aurpClusterEntry 2 }

          aurpClusterNetStart OBJECT-TYPE
              SYNTAX    ATNetworkNumber
              ACCESS    read-only
              STATUS    mandatory
              DESCRIPTION
                        "The first AppleTalk network address of the
                        range associated with this cluster."
              ::= { aurpClusterEntry 3 }

          aurpClusterNetEnd OBJECT-TYPE
              SYNTAX    ATNetworkNumber
              ACCESS    read-only
              STATUS    mandatory
              DESCRIPTION
                        "The last AppleTalk network address of the range
                        associated with this cluster. "
              ::= { aurpClusterEntry 4 }

          aurpClusterUIDI OBJECT-TYPE
              SYNTAX    OCTET STRING
              ACCESS    read-only
              STATUS    mandatory
              DESCRIPTION
                        "The domain identifier portion of the unique
                        identifier associated with the imported networks
                        that are being clustered."
              ::= { aurpClusterEntry 5 }

          aurpClusterNumberOfNetworks OBJECT-TYPE
              SYNTAX    INTEGER
              ACCESS    read-only
              STATUS    mandatory
              DESCRIPTION
                        "The number of imported, remapped networks
                        contained in this cluster."
              ::= { aurpClusterEntry 6 }

          aurpClusterHopCount OBJECT-TYPE
              SYNTAX    INTEGER
              ACCESS    read-only
              STATUS    mandatory
              DESCRIPTION
                        "The number of hops that this cluster is away
                        from this router."
              ::= { aurpClusterEntry 7 }


          --  The AURP Cluster Member Table

          aurpClusterMemberTable OBJECT-TYPE
              SYNTAX    SEQUENCE OF AurpClusterMemberEntry
              ACCESS    not-accessible
              STATUS    mandatory
              DESCRIPTION
                        "A list of entries describing the imported,
                        remapped network ranges comprising the device's
                        clusters of imported, remapped networks."
              ::= { aurpInfo 6 }

          aurpClusterMemberEntry OBJECT-TYPE
              SYNTAX    AurpClusterMemberEntry
              ACCESS    not-accessible
              STATUS    mandatory
              DESCRIPTION
                        "An entry describing a network range in one of
                        the device's clusters of imported, remapped
                        networks."
              INDEX     { aurpClusterMemberPortIndex, aurpClusterMemberIndex,
                          aurpClusterMemberUINetStart }
              ::= { aurpClusterMemberTable 1 }

          AurpClusterMemberEntry ::=
              SEQUENCE {
                  aurpClusterMemberPortIndex
                      INTEGER,
                  aurpClusterMemberIndex
                      INTEGER,
                  aurpClusterMemberUINetStart
                      ATNetworkNumber,
                  aurpClusterMemberUINetEnd
                      ATNetworkNumber
              }

          aurpClusterMemberPortIndex OBJECT-TYPE
              SYNTAX    INTEGER
              ACCESS    read-only
              STATUS    mandatory
              DESCRIPTION
                        "The AppleTalk port corresponding to the tunnel
                        associated with this clustered network range."
              ::= { aurpClusterMemberEntry 1 }

          aurpClusterMemberIndex OBJECT-TYPE
              SYNTAX    INTEGER
              ACCESS    read-only
              STATUS    mandatory
              DESCRIPTION
                        "The unique value associated with the cluster to
                        which this clustered imported network range
                        belongs.  The cluster represented by a
                        particular value of this object is the same
                        cluster as is represented by the same value of
                        the aurpClusterIndex object."
              ::= { aurpClusterMemberEntry 2 }

          aurpClusterMemberUINetStart OBJECT-TYPE
              SYNTAX    ATNetworkNumber
              ACCESS    read-only
              STATUS    mandatory
              DESCRIPTION
                        "The first AppleTalk network address of the
                        range portion of the unique identifier
                        associated with the imported network range that
                        is being clustered."
              ::= { aurpClusterMemberEntry 3 }

          aurpClusterMemberUINetEnd OBJECT-TYPE
              SYNTAX    ATNetworkNumber
              ACCESS    read-only
              STATUS    mandatory
              DESCRIPTION
                        "The last AppleTalk network address of the range
                        portion of the unique identifier associated with
                        the imported network range that is being
                        clustered."
              ::= { aurpClusterMemberEntry 4 }


          --  The bootParams group

          deviceRestart OBJECT-TYPE
              SYNTAX    INTEGER {
                            dontRestart(1),
                            restart(2)
                        }
              ACCESS    read-write
              STATUS    mandatory
              DESCRIPTION
                        "The value of this object returned in response
                        to an SNMP Get or Get-Next request is always
                        'dontRestart(1)'.  Setting this object to the
                        value 'restart(2)' will cause the device to
                        restart."
              ::= { bootParams 1 }

          restoreDefaultConfig OBJECT-TYPE
              SYNTAX    INTEGER {
                            dontRestore(1),
                            restore(2)
                        }
              ACCESS    read-write
              STATUS    mandatory
              DESCRIPTION
                        "The value of this object returned in response
                        to an SNMP Get or Get-Next Request is always
                        'dontRestore(1)'.  Setting this object to the
                        value 'restore(2)' will cause the device to
                        replace its running configuration stored in
                        non-volatile memory with the default
                        configuration stored in ROM."
              ::= { bootParams 2 }


          --  The tftpParams group

          tftpParams     OBJECT IDENTIFIER ::= { bootParams 3 }

          tftpMaxRetries OBJECT-TYPE
              SYNTAX    INTEGER
              ACCESS    read-write
              STATUS    mandatory
              DESCRIPTION
                        "The maximum number of times the device will
                        retransmit a Trivial File Transfer Protocol
                        (TFTP) packet before terminating a TFTP
                        transfer.  The total number of times TFTP will
                        transmit a packet before terminating a TFTP
                        transfer will be between one and the value of
                        this object plus one."
              ::= { tftpParams 1 }

          tftpServerName OBJECT-TYPE
              SYNTAX    HostNameOrIpAddr
              ACCESS    read-write
              STATUS    mandatory
              DESCRIPTION
                        "The name of the TFTP server from which to read
                        or write the device's configuration or from
                        which to read a firmware image.

                        The value of this object can be a fully- or
                        partially-qualified domain name system (dns)
                        name, or it can be an IP address in the familiar
                        'dotted-quad' notation.

                        If the value of this object is a fully- or
                        partially-qualified dns name, the device will
                        attempt to use the Domain Name System to convert
                        the name to an IP address before initiating a
                        transaction with this TFTP server."
              ::= { tftpParams 2 }

          tftpFwFileName OBJECT-TYPE
              SYNTAX    OCTET STRING
              ACCESS    read-write
              STATUS    mandatory
              DESCRIPTION
                        "The file name of the firmware image file to
                        read from the TFTP server."
              ::= { tftpParams 3 }

          tftpConfigFileName OBJECT-TYPE
              SYNTAX    OCTET STRING
              ACCESS    read-write
              STATUS    mandatory
              DESCRIPTION
                        "The file name of the configuration file to read
                        from or write to the TFTP server."
              ::= { tftpParams 4 }

          tftpReadFw OBJECT-TYPE
              SYNTAX    INTEGER {
                            -- the following two values are states:
                            -- these values may be read, but not
                            -- written
                            readingFw(1),
                            notReadingFw(2),

                            -- the following value is an action:
                            -- this value may be written, but is
                            -- never read
                            readFw(3)
                        }
              ACCESS    read-write
              STATUS    mandatory
              DESCRIPTION
                        "Specifying the value 'readFw(3)' in an SNMP Set
                        Request causes the device to attempt to replace
                        its firmware image stored in Flash-Erasable
                        Programmable Read-Only Memory (Flash-EPROM) with
                        one read via TFTP.

                        The tftpServerAddr object indicates the host
                        name or IP address of the TFTP server and the
                        tftpFwFileName object indicates the file name of
                        the firmware image file.

                        The value 'readFw(3)' may be specified only if
                        the values of this object, the tftpReadConfig
                        object, and the tftpWriteConfig object are
                        'notReadingFw(2)', 'notReadingConfig(2)', and
                        'notWritingConfig(2)', respectively.  (That is,
                        the device supports only one TFTP transfer at a
                        time.)

                        The value of this object returned in response to
                        an SNMP Get or Get-Next Request will be either
                        'readingFw(1)' or 'notReadingFw(2)'.

                        The device will reset itself after successfully
                        replacing its firmware image."
              ::= { tftpParams 5 }

          tftpReadConfig OBJECT-TYPE
              SYNTAX    INTEGER {
                            -- the following two values are states:
                            -- these values may be read, but not
                            -- written
                            readingConfig(1),
                            notReadingConfig(2),

                            -- the following value is an action:
                            -- this value may be written, but is
                            -- never read
                            readConfig(3)
                        }
              ACCESS    read-write
              STATUS    mandatory
              DESCRIPTION
                        "Specifying the value 'readConfig(3)' in an SNMP
                        Set Request causes the device to attempt to
                        replace its configuration stored in non-volatile
                        read-only memory (NVRAM) with one read via TFTP.

                        The tftpServerAddr object indicates the host
                        name or IP address of the TFTP server and the
                        tftpConfigFileName object indicates the file
                        name of the configuration file.

                        The value 'readConfig(3)' may be specified only
                        if the values of this object, the tftpReadFw
                        object, and the tftpWriteConfig object are
                        'notReadingConfig(2)', 'notReadingFw(2)', and
                        'notWritingConfig(2)', respectively.  (That is,
                        the device supports only one TFTP transfer at a
                        time.)

                        The value of this object returned in response to
                        an SNMP Get or Get-Next Request will be either
                        'readingConfig(1)' or 'notReadingConfig(2)'."
              ::= { tftpParams 6 }

          tftpWriteConfig OBJECT-TYPE
              SYNTAX    INTEGER {
                            -- the following two values are states:
                            -- these values may be read, but not
                            -- written
                            writingConfig(1),
                            notWritingConfig(2),

                            -- the following value is an action:
                            -- this value may be written, but is
                            -- never read
                            writeConfig(3)
                        }
              ACCESS    read-write
              STATUS    mandatory
              DESCRIPTION
                        "Specifying the value 'writeConfig(3)' in an
                        SNMP Set Request causes the device to attempt to
                        write its configuration stored in non-volatile
                        read-only memory (NVRAM) to a configuration file
                        via TFTP.

                        The tftpServerAddr object indicates the host
                        name or IP address of the TFTP server and the
                        tftpConfigFileName object indicates the file
                        name of the configuration file.

                        The value 'writeConfig(3)' may be specified only
                        if the values of this object, the tftpReadFw
                        object, and the tftpReadConfig object are
                        'notWritingConfig(2)', 'notReadingFw(2)', and
                        'notReadingConfig(2)', respectively.  (That is,
                        the device supports only one TFTP transfer at a
                        time.)

                        The value of this object returned in response to
                        an SNMP Get or Get-Next Request will be either
                        'writingConfig(1)' or 'notWritingConfig(2)'."
              ::= { tftpParams 7 }

          tftpCurrentTransferOctets OBJECT-TYPE
              SYNTAX    UInteger
              ACCESS    read-only
              STATUS    mandatory
              DESCRIPTION
                        "Indicates the number of octets transferred
                        during the current TFTP transfer.  The value of
                        this object is reset to zero when a TFTP
                        transfer is initiated via a successful set of
                        one of the tftpReadFw, tftpReadConfig, or
                        tftpWriteConfig objects and is updated during
                        the transfer."
              ::= { tftpParams 8 }


          --  The snmpParams group

          --  This group contains definitions of objects relating to the
          --  device's implementation of the Simple Network Management
          --  Protocol (SNMP).  The objects defined in this group
          --  supplement the objects defined in the MIB-II snmp group.

          --  The objects in the snmpAtTrapRcvrTable and the
          --  snmpAtTrapRcvrCacheEntryLifetime object are not applicable
          --  to a Netopia PN630 or a Netopia PN640.

          snmpIpTrapRcvrTable OBJECT-TYPE
              SYNTAX    SEQUENCE OF SnmpIpTrapRcvrEntry
              ACCESS    not-accessible
              STATUS    mandatory
              DESCRIPTION
                        "A list of entries containing information about
                        network management stations with IP addresses
                        that are to receive traps generated by this
                        device over UDP.

                        The snmpIpTrapRcvrTable object supports
                        'conceptual row creation' according to section
                        3.2(3) of RFC 1212:  To add a new row to the
                        snmpIpTrapRcvrTable, a management station must
                        provide a value for the new instance of the
                        snmpIpTrapRcvrCommunity object, and may, in
                        addition, provide values for any or all of the
                        remaining object instances in the new row with
                        read-write ACCESS.

                        If no value is supplied for the corresponding
                        instance of the snmpIpTrapRcvrStatus object, its
                        value will default to 'valid(1)'.  The value of
                        the instance of the snmpIpTrapRcvrIpAddress
                        object in a newly created row is always the
                        unknown IP address 0.0.0.0."
              ::= { snmpParams 1 }

          snmpIpTrapRcvrEntry OBJECT-TYPE
              SYNTAX    SnmpIpTrapRcvrEntry
              ACCESS    not-accessible
              STATUS    mandatory
              DESCRIPTION
                        "An entry containing information about a single
                        network management station with an IP address
                        that is to receive traps generated by this
                        device over UDP."
              INDEX     { snmpIpTrapRcvrName }
              ::= { snmpIpTrapRcvrTable 1 }

          SnmpIpTrapRcvrEntry ::=
              SEQUENCE {
                  snmpIpTrapRcvrName
                      HostNameOrIpAddr,
                  snmpIpTrapRcvrCommunity
                      OCTET STRING,
                  snmpIpTrapRcvrIpAddress
                      IpAddress,
                  snmpIpTrapRcvrStatus
                      INTEGER
              }

          snmpIpTrapRcvrName OBJECT-TYPE
              SYNTAX    HostNameOrIpAddr
              ACCESS    read-only
              STATUS    mandatory
              DESCRIPTION
                        "The name of this IP trap receiver.

                        The value of this object can be a fully- or
                        partially-qualified domain name system (dns)
                        name, or it can be an IP address in the familiar
                        'dotted-quad' notation.

                        If the value of this object is a fully- or
                        partially-qualified dns name, the device will
                        attempt to use the Domain Name System to convert
                        the name to an IP address before sending a trap
                        to this IP trap receiver."
              ::= { snmpIpTrapRcvrEntry 1 }

          snmpIpTrapRcvrCommunity OBJECT-TYPE
              SYNTAX    OCTET STRING
              ACCESS    read-write
              STATUS    mandatory
              DESCRIPTION
                        "The community string to be specified in traps
                        sent to this IP trap receiver."
              ::= { snmpIpTrapRcvrEntry 2 }

          snmpIpTrapRcvrIpAddress OBJECT-TYPE
              SYNTAX    IpAddress
              ACCESS    read-only
              STATUS    mandatory
              DESCRIPTION
                        "The IP address of this IP trap receiver.

                        The value of this object is the IP address that
                        was most recently obtained by the device from
                        the Domain Name System for this IP trap
                        receiver.  The value of this object will be the
                        unknown IP address 0.0.0.0 if the device has not
                        yet attempted to obtain an IP address for this
                        IP trap receiver, or if an error (other than a
                        timeout) occurred during the most recent attempt
                        to obtain an IP address for this IP trap
                        receiver."
              ::= { snmpIpTrapRcvrEntry 3 }

          snmpIpTrapRcvrStatus OBJECT-TYPE
              SYNTAX    INTEGER {
                            valid(1),        -- a  valid   entry
                            invalid(2)       -- an invalid entry
                        }
              ACCESS    read-write
              STATUS    mandatory
              DESCRIPTION
                        "The value of this object indicates whether the
                        associated entry in the snmpIpTrapRcvrTable is
                        in use or not.  Setting this object to the value
                        'invalid(2)' has the effect of invalidating the
                        corresponding entry in the snmpIpTrapRcvrTable.
                        It is an implementation-specific matter as to
                        whether the agent removes an invalidated entry
                        from the table.  Accordingly, network management
                        stations must be prepared to receive tabular
                        information from agents that corresponds to
                        entries not currently in use.  Proper
                        interpretation of such entries requires
                        examination of the relevant snmpIpTrapRcvrStatus
                        object."
              ::= { snmpIpTrapRcvrEntry 4 }


          snmpAtTrapRcvrTable OBJECT-TYPE
              SYNTAX    SEQUENCE OF SnmpAtTrapRcvrEntry
              ACCESS    not-accessible
              STATUS    mandatory
              DESCRIPTION
                        "A list of entries containing information about
                        network management stations with AppleTalk
                        addresses that are to receive traps generated by
                        this device over DDP.

                        The snmpAtTrapRcvrTable object supports
                        'conceptual row creation' according to section
                        3.2(3) of RFC 1212:  To add a new row to the
                        snmpAtTrapRcvrTable, a management station must
                        provide values for the new instance of the
                        snmpAtTrapRcvrCommunity object, and may, in
                        addition, provide values for any or all of the
                        remaining object instances in the new row.

                        If no value is supplied for the corresponding
                        instance of the snmpAtTrapRcvrNBPObject or
                        snmpAtTrapRcvrNBPZone objects, their values will
                        be derived from the snmpAtTrapRcvrCommunity
                        object instance.  If no value is supplied for
                        the corresponding instance of the
                        snmpAtTrapRcvrStatus object, its value will
                        default to 'valid(1)'."
              ::= { snmpParams 2 }

          snmpAtTrapRcvrEntry OBJECT-TYPE
              SYNTAX    SnmpAtTrapRcvrEntry
              ACCESS    not-accessible
              STATUS    mandatory
              DESCRIPTION
                        "An entry containing information about a single
                        network management station with an AppleTalk
                        address that is to receive traps generated by
                        this device over DDP."
              INDEX     { snmpAtTrapRcvrNBPObject, snmpAtTrapRcvrNBPZone }
              ::= { snmpAtTrapRcvrTable 1 }

          SnmpAtTrapRcvrEntry ::=
              SEQUENCE {
                  snmpAtTrapRcvrNBPObject
                      OCTET STRING (SIZE(1..32)),
                  snmpAtTrapRcvrNBPZone
                      OCTET STRING (SIZE(1..32)),
                  snmpAtTrapRcvrCommunity
                      OCTET STRING,
                  snmpAtTrapRcvrDdpAddress
                      DdpAddress,
                  snmpAtTrapRcvrLastConfirmTime
                      DisplayString,
                  snmpAtTrapRcvrStatus
                      INTEGER
              }

          snmpAtTrapRcvrNBPObject OBJECT-TYPE
              SYNTAX    OCTET STRING (SIZE(1..32))
              ACCESS    read-write
              STATUS    mandatory
              DESCRIPTION
                        "The object component of the AppleTalk Name
                        Binding Protocol (NBP) name of this trap
                        receiver."
              ::= { snmpAtTrapRcvrEntry 1 }

          snmpAtTrapRcvrNBPZone OBJECT-TYPE
              SYNTAX    OCTET STRING (SIZE(1..32))
              ACCESS    read-write
              STATUS    mandatory
              DESCRIPTION
                        "The zone component of the AppleTalk Name
                        Binding Protocol (NBP) name of this trap
                        receiver."
              ::= { snmpAtTrapRcvrEntry 2 }

          snmpAtTrapRcvrCommunity OBJECT-TYPE
              SYNTAX    OCTET STRING
              ACCESS    read-write
              STATUS    mandatory
              DESCRIPTION
                        "The community string to be specified in traps
                        sent to this trap receiver."
              ::= { snmpAtTrapRcvrEntry 3 }

          snmpAtTrapRcvrDdpAddress OBJECT-TYPE
              SYNTAX    DdpAddress
              ACCESS    read-only
              STATUS    mandatory
              DESCRIPTION
                        "The DDP address of this trap receiver, as
                        determined by the most recent NBP Lookup.  The
                        value of this object will be three octets of
                        zero if the DDP address of this trap receiver
                        has not yet been determined by an NBP Lookup, or
                        could not be confirmed by an NBP Confirm and has
                        not yet been re-determined by another NBP
                        Lookup."
              ::= { snmpAtTrapRcvrEntry 4 }

          snmpAtTrapRcvrLastConfirmTime OBJECT-TYPE
              SYNTAX    DisplayString
              ACCESS    read-only
              STATUS    mandatory
              DESCRIPTION
                        "The time (in human-readable form) at which the
                        DDP address of this trap receiver was last
                        determined by an NBP Lookup or confirmed by an
                        NBP Confirm.  The value of this object will be
                        an empty string if the DDP address of this trap
                        receiver has not yet been determined by an NBP
                        Lookup, or could not be confirmed by an NBP
                        Confirm and has not yet been re-determined by
                        another NBP Lookup."
              ::= { snmpAtTrapRcvrEntry 5 }

          snmpAtTrapRcvrStatus OBJECT-TYPE
              SYNTAX    INTEGER {
                            valid(1),        -- a  valid   entry
                            invalid(2)       -- an invalid entry
                        }
              ACCESS    read-write
              STATUS    mandatory
              DESCRIPTION
                        "The value of this object indicates whether the
                        associated entry in the snmpAtTrapRcvrTable is
                        in use or not.  Setting this object to the value
                        'invalid(2)' has the effect of invalidating the
                        corresponding entry in the snmpAtTrapRcvrTable.
                        It is an implementation-specific matter as to
                        whether the agent removes an invalidated entry
                        from the table.  Accordingly, network management
                        stations must be prepared to receive tabular
                        information from agents that corresponds to
                        entries not currently in use.  Proper
                        interpretation of such entries requires
                        examination of the relevant snmpAtTrapRcvrStatus
                        object."
              ::= { snmpAtTrapRcvrEntry 6 }

          snmpAtTrapRcvrCacheEntryLifetime OBJECT-TYPE
              SYNTAX    INTEGER
              ACCESS    read-write
              STATUS    mandatory
              DESCRIPTION
                        "The cache entry lifetime, in seconds, of
                        bindings between NBP names and DDP addresses in
                        the snmpAtTrapRcvrTable.  The value of this
                        object must be at least 60 seconds."
              ::= { snmpParams 3 }

          snmpUnAuthIpAddr OBJECT-TYPE
              SYNTAX    IpAddress
              ACCESS    read-only
              STATUS    mandatory
              DESCRIPTION
                        "The IP address of the last management station
                        that attempted to access this agent with an
                        invalid community string.  This object is used
                        as a variable binding in an Authentication
                        Failure Trap-PDU."
              ::= { snmpParams 4 }

          snmpUnAuthCommunity OBJECT-TYPE
              SYNTAX    OCTET STRING
              ACCESS    read-only
              STATUS    mandatory
              DESCRIPTION
                        "The community string specified by the most
                        recent unauthenticated attempt to access this
                        agent.  This object is used as a variable
                        binding in an Authentication Failure Trap-PDU."
              ::= { snmpParams 5 }


          --  The isdnParams group

          --  This group contains configuration information for the device's
          --  ISDN Basic Rate Interface (BRI) line.

          isdnSwitchType OBJECT-TYPE
              SYNTAX    INTEGER {
                            ntDms100Custom(1),  -- Northern Telecom DMS-100
                                                --   (in "custom" mode)
                            att5essCustom(2),   -- AT&T 5ESS
                                                --   (in "custom" mode)
                            nationalIsdn1(3)    -- Either of the above in
                                                --   National ISDN-1 mode
                        }
              ACCESS    read-write
              STATUS    mandatory
              DESCRIPTION
                        "The type of telephone company central office
                        switch to which the device's ISDN Basic Rate
                        Interface (BRI) line is connected."
              ::= { isdnParams 1 }

          isdnDirNum1 OBJECT-TYPE
              SYNTAX    OCTET STRING
              ACCESS    read-write
              STATUS    mandatory
              DESCRIPTION
                        "The device's primary ISDN directory number."
              ::= { isdnParams 2 }

          isdnSpid1 OBJECT-TYPE
              SYNTAX    OCTET STRING
              ACCESS    read-write
              STATUS    mandatory
              DESCRIPTION
                        "The device's primary service profile identifier
                        (SPID)."
              ::= { isdnParams 3 }

          isdnDirNum2 OBJECT-TYPE
              SYNTAX    OCTET STRING
              ACCESS    read-write
              STATUS    mandatory
              DESCRIPTION
                        "The device's secondary ISDN directory number."
              ::= { isdnParams 4 }

          isdnSpid2 OBJECT-TYPE
              SYNTAX    OCTET STRING
              ACCESS    read-write
              STATUS    mandatory
              DESCRIPTION
                        "The device's secondary service profile
                        identifier (SPID)."
              ::= { isdnParams 5 }

          connProfileTable OBJECT-TYPE
              SYNTAX    SEQUENCE OF ConnProfileEntry
              ACCESS    not-accessible
              STATUS    mandatory
              DESCRIPTION
                        "A list of entries providing configuration
                        information for the device's possible on-demand
                        WAN connections to remote peers via ISDN.

                        This table supports 'conceptual row creation'
                        according to section 3.2(3) of RFC 1212:  To add
                        a new row to this table, a management station
                        may provide a value for any or all of the read-
                        write object instances in the new row.  If the
                        management station fails to provide a value for
                        any object instance in the new row, the instance
                        will have the value indicated by the
                        corresponding object's DEFVAL clause."
              ::= { isdnParams 6 }

          connProfileEntry OBJECT-TYPE
              SYNTAX    ConnProfileEntry
              ACCESS    not-accessible
              STATUS    mandatory
              DESCRIPTION
                        "An entry containing configuration information
                        for one of the device's possible on-demand WAN
                        connections to remote peers via ISDN."
              INDEX     { connProfIndex }
              ::= { connProfileTable 1 }

          ConnProfileEntry ::=
              SEQUENCE {
                  connProfIndex
                      INTEGER,
                  connProfName
                      OCTET STRING,
                  connProfEnable
                      INTEGER,
                  connProfPermittedUse
                      INTEGER,
                  connProfIsdnDialNum
                      OCTET STRING,
                  connProfIsdnBandwidth
                      INTEGER,
                  connProfDialOnDemand
                      INTEGER,
                  connProfDialBack
                      INTEGER,
                  connProfIsdnOutDataRate
                      INTEGER,
                  connProfRemIpAddr
                      IpAddress,
                  connProfRemSubnetMask
                      IpAddress,
                  connProfRxRip
                      INTEGER,
                  connProfTxRip
                      INTEGER,
                  connProfFilterSetIndex
                      INTEGER,
                  connProfIdleSeconds
                      INTEGER (0..2147483647),
                  connProfPppMaxRecvUnit
                      INTEGER,
                  connProfPppLinkCompression
                      INTEGER,
                  connProfPppSendAuthProt
                      INTEGER,
                  connProfPppSendAuthName
                      OCTET STRING,
                  connProfPppSendAuthSecret
                      OCTET STRING,
                  connProfPppRecvAuthName
                      OCTET STRING,
                  connProfPppRecvAuthSecret
                      OCTET STRING,
                  connProfStatus
                      INTEGER
              }

          connProfIndex OBJECT-TYPE
              SYNTAX    INTEGER
              ACCESS    read-only
              STATUS    mandatory
              DESCRIPTION
                        "A unique value for each of the device's
                        possible on-demand WAN connections via ISDN."
              ::= { connProfileEntry 1 }

          connProfName OBJECT-TYPE
              SYNTAX    OCTET STRING
              ACCESS    read-write
              STATUS    mandatory
              DESCRIPTION
                        "The name of the remote peer described by this
                        connection profile."
              DEFVAL    { ''H }
              ::= { connProfileEntry 2 }

          connProfEnable OBJECT-TYPE
              SYNTAX    INTEGER {
                            enabled(1),
                            disabled(2)
                        }
              ACCESS    read-write
              STATUS    mandatory
              DESCRIPTION
                        "Indicates whether or not this connection
                        profile is currently 'enabled.'  A disabled
                        connection profile retains its values, but may
                        not be used to establish a connection."
              DEFVAL    { disabled }
              ::= { connProfileEntry 3 }

          connProfPermittedUse OBJECT-TYPE
              SYNTAX    INTEGER {
                            dialIn(1),
                            dialOut(2),
                            dialInOrOut(3)
                        }
              ACCESS    read-write
              STATUS    mandatory
              DESCRIPTION
                        "The permitted use of this connection profile.

                        If the value of this object is 'dialIn(1)', the
                        device will accept an incoming call from, but
                        will not originate an outgoing call to, the
                        remote peer described by this connection
                        profile.

                        If the value of this object is 'dialOut(2)', the
                        device will originate an outgoing call to, but
                        will not accept an incoming call from, the
                        remote peer described by this connection
                        profile.

                        If the value of this object is 'dialInOrOut(3)',
                        the device will accept an incoming call from
                        and/or originate an outgoing call to the remote
                        peer described by this connection profile."
              DEFVAL    { dialInOrOut }
              ::= { connProfileEntry 4 }

          connProfIsdnDialNum OBJECT-TYPE
              SYNTAX    OCTET STRING
              ACCESS    read-write
              STATUS    mandatory
              DESCRIPTION
                        "The string of digits required to place a call
                        to the remote peer described by this connection
                        profile."
              DEFVAL    { ''H }
              ::= { connProfileEntry 5 }

          connProfIsdnBandwidth OBJECT-TYPE
              SYNTAX    INTEGER {
                            oneBChannel(1),
                            twoBChannels(2),
                            dynamicBandwidth(3)
                        }
              ACCESS    read-write
              STATUS    mandatory
              DESCRIPTION
                        "The number of ISDN B-channels the device will
                        use for the connection to the remote peer
                        described by this connection profile.

                        If the value of this object is 'oneBChannel(1)',
                        the connection will always use exactly one B-
                        channel.

                        If the value of this object is
                        'twoBChannels(2)', the connection will always
                        use exactly two B-channels.

                        If the value of this object is
                        'dynamicBandwidth(3)', the connection will use
                        one or two B-channels.  The number of B-channels
                        in use at any particular point in time will
                        depend on the traffic level to/from the remote
                        peer and the existence of, or need to establish,
                        a simultaneous connection to another remote
                        peer."
              DEFVAL    { oneBChannel }
              ::= { connProfileEntry 6 }

          connProfDialOnDemand OBJECT-TYPE
              SYNTAX    INTEGER {
                            enabled(1),
                            disabled(2)
                        }
              ACCESS    read-write
              STATUS    mandatory
              DESCRIPTION
                        "Indicates whether or not the device will
                        initiate an outgoing call to establish a
                        connection with the remote peer described by
                        this connection profile when it receives a
                        packet for which the remote peer is the next
                        hop."
              DEFVAL    { enabled }
              ::= { connProfileEntry 7 }

          connProfDialBack OBJECT-TYPE
              SYNTAX    INTEGER {
                            enabled(1),
                            disabled(2)
                        }
              ACCESS    read-write
              STATUS    mandatory
              DESCRIPTION
                        "Indicates whether or not the device will hang
                        up and initiate an outgoing call to the remote
                        peer described in this connection profile upon
                        receiving an incoming call from the remote
                        peer."
              DEFVAL    { disabled }
              ::= { connProfileEntry 8 }

          connProfIsdnOutDataRate OBJECT-TYPE
              SYNTAX    INTEGER {
                            place64KCall(1),
                            place56KCall(2)
                        }
              ACCESS    read-write
              STATUS    mandatory
              DESCRIPTION
                        "The type of circuit-switched data service to
                        use when placing an outgoing call to the remote
                        peer described by this connection profile.

                        If the value of this object is
                        'place64KCall(1)', the device will place a 64K
                        circuit-switched data call to the remote peer.

                        If the value of this object is
                        'place56KCall(2)', the device will place a 56K
                        circuit-switched data call to the remote peer."
              DEFVAL    { place56KCall }
              ::= { connProfileEntry 9 }

          connProfRemIpAddr OBJECT-TYPE
              SYNTAX    IpAddress
              ACCESS    read-write
              STATUS    mandatory
              DESCRIPTION
                        "The IP address of the remote peer's LAN
                        interface."
              DEFVAL    { ''H }
              ::= { connProfileEntry 10 }

          connProfRemSubnetMask OBJECT-TYPE
              SYNTAX    IpAddress
              ACCESS    read-write
              STATUS    mandatory
              DESCRIPTION
                        "The subnet mask of the remote peer's LAN
                        interface."
              DEFVAL    { ''H }
              ::= { connProfileEntry 11 }

          connProfRxRip OBJECT-TYPE
              SYNTAX    INTEGER {
                            dontRxRip(1),
                            rxRip(2)
                        }
              ACCESS    read-write
              STATUS    mandatory
              DESCRIPTION
                        "Indicates whether or not the device will
                        receive RIP packets over the WAN connection from
                        the remote peer."
              DEFVAL    { dontRxRip }
              ::= { connProfileEntry 12 }

          connProfTxRip OBJECT-TYPE
              SYNTAX    INTEGER {
                            dontTxRip(1),
                            txRip(2)
                        }
              ACCESS    read-write
              STATUS    mandatory
              DESCRIPTION
                        "Indicates whether or not the device will
                        transmit RIP packets over the WAN connection to
                        the remote peer."
              DEFVAL    { dontTxRip }
              ::= { connProfileEntry 13 }

          connProfFilterSetIndex OBJECT-TYPE
              SYNTAX    INTEGER
              ACCESS    read-write
              STATUS    mandatory
              DESCRIPTION
                        "Indicates the set of filters to be used to
                        filter packets received and transmitted over the
                        WAN connection to the remote peer.

                        The filter set identified by a particular value
                        of this object is the same filter set as is
                        identified by the same value of the
                        filterSetIndex object.

                        The value zero indicates that no filter set is
                        associated with this connection profile."
              DEFVAL    { 0 }
              ::= { connProfileEntry 14 }

          connProfIdleSeconds OBJECT-TYPE
              SYNTAX    INTEGER (0..2147483647)
              ACCESS    read-write
              STATUS    mandatory
              DESCRIPTION
                        "Indicates the number of seconds during which
                        there must be no outbound traffic over a demand
                        connection to the remote peer for the device to
                        clear the call.

                        The value zero prevents the device from clearing
                        the call due to lack of traffic.

                        Note that the remote peer may implement its own
                        policy that may cause the call to be cleared
                        sooner than it would otherwise be cleared based
                        on the value of this object."
              DEFVAL    { 120 }
              ::= { connProfileEntry 15 }

          connProfPppMaxRecvUnit OBJECT-TYPE
              SYNTAX    INTEGER
              ACCESS    read-write
              STATUS    mandatory
              DESCRIPTION
                        "Indicates the size of the largest PPP packet
                        that can be received over the WAN connection
                        with the remote peer."
              DEFVAL    { 1500 }
              ::= { connProfileEntry 16 }

          connProfPppLinkCompression OBJECT-TYPE
              SYNTAX    INTEGER {
                            negotiateStacCompression(1),
                            noCompression(2)
                        }
              ACCESS    read-write
              STATUS    mandatory
              DESCRIPTION
                        "Indicates whether or not the device will
                        attempt to negotiate PPP link compression when
                        establishing a connection to the remote peer.

                        If this object has the value
                        'negotiateStacCompression(1)', then device will
                        attempt to negotiate use of the Stac Electronics
                        proprietary STACKER LZS (tm) compression-
                        decompression algorithm when establishing a
                        connection with the remote peer."
              DEFVAL    { noCompression }
              ::= { connProfileEntry 17 }

          connProfPppSendAuthProt OBJECT-TYPE
              SYNTAX    INTEGER {
                            authNone(1),
                            authPAP(2),
                            authCHAP(3)
                        }
              ACCESS    read-write
              STATUS    mandatory
              DESCRIPTION
                        "Indicates the PPP authentication protocol that
                        the device will use to authenticate itself to
                        the remote peer described by this connection
                        profile.

                        If the value of this object is 'authNone(1)',
                        the device will not authenticate itself to the
                        remote peer.  If the remote peer requests
                        authentication, the request will be rejected,
                        and if the remote peer requires authentication,
                        then the connection will fail.

                        If the value of this object is 'authPAP(2)', the
                        device will use the Password Authentication
                        Protocol (PAP) described in RFC 1334 to
                        authenticate itself to the remote peer.  The
                        connProfPppSendAuthName and
                        connProfPppSendAuthSecret objects indicate the
                        Peer-ID and Password, respectively, that this
                        device will send to the remote peer in PAP
                        Authenticate-Request packets during the
                        Authentication Phase of PPP link establishment.

                        If the value of this object is 'authCHAP(3)',
                        the device will use the Challenge-Handshake
                        Authentication Protocol (CHAP) described in RFC
                        1334 to authenticate itself to the remote peer.
                        The connProfPppSendAuthName object indicates the
                        Name that the device will use to identify itself
                        in a CHAP Response packet; the
                        connProfPppSendAuthSecret object indicates the
                        Secret that the device will use to compute the
                        Response Value that it sends to the remote peer
                        in a CHAP Response packet.

                        If the remote peer requests the use of a
                        different authentication protocol than the one
                        specified by the value of this object, the
                        request will be rejected."
              REFERENCE
                        "PPP Authentication Protocols, RFC 1334"
              DEFVAL    { authNone }
              ::= { connProfileEntry 18 }

          connProfPppSendAuthName OBJECT-TYPE
              SYNTAX    OCTET STRING
              ACCESS    read-write
              STATUS    mandatory
              DESCRIPTION
                        "If the value of the connProfPppSendAuthProt
                        object is 'authPAP(2)', then the value of this
                        object is the Peer-ID that the device will send
                        to the remote peer in PAP Authenticate-Request
                        packets during the Authentication Phase of PPP
                        link establishment.

                        If the value of the connProfPppSendAuthProt
                        object is 'authCHAP(3)', then the value of this
                        object is the Name that the device will use to
                        identify itself in CHAP Response packets sent to
                        the remote peer.

                        The value of this object is meaningless if the
                        value of the connProfPppSendAuthProt object is
                        'authNone(1)'."
              DEFVAL    { ''H }
              ::= { connProfileEntry 19 }

          connProfPppSendAuthSecret OBJECT-TYPE
              SYNTAX    OCTET STRING
              ACCESS    read-write
              STATUS    mandatory
              DESCRIPTION
                        "If the value of the connProfPppSendAuthProt
                        object is 'authPAP(2)', then the value of this
                        object is the Password that the device will send
                        to the remote peer in PAP Authenticate-Request
                        packets during the Authentication Phase of PPP
                        link establishment.

                        If the value of the connProfPppSendAuthProt
                        object is 'authCHAP(3)', then the value of this
                        object is the Secret that the device will use to
                        compute the Response Value that it sends to the
                        remote peer in a CHAP Response packet.

                        The value of this object is meaningless if the
                        value of the connProfPppSendAuthProt object is
                        'authNone(1)'.

                        Although the value of this variable may be
                        altered by a management operation (e.g., an SNMP
                        Set Request), its value can never be retrieved
                        by a management operation:  When read, the value
                        of this variable is a zero-length OCTET STRING."
              DEFVAL    { ''H }
              ::= { connProfileEntry 20 }

          connProfPppRecvAuthName OBJECT-TYPE
              SYNTAX    OCTET STRING
              ACCESS    read-write
              STATUS    mandatory
              DESCRIPTION
                        "If the value of the ansProfPppRecvAuthProt
                        object is 'authPAP(2)', then the value of this
                        object is the Peer-ID that the remote peer must
                        specify in its PAP Authenticate-Request packets.

                        If the value of the ansProfPppRecvAuthProt
                        object is 'authCHAP(3)', then the value of this
                        object is the Name that the remote peer must use
                        to identify itself in its CHAP Challenge and
                        CHAP Response packets.

                        The value of this object is meaningless if the
                        value of the ansProfConnProfRequired object is
                        'connProfNotRequired(2)' or the value of the
                        ansProfPppRecvAuthProt object is 'authNone(1)'."
              DEFVAL    { ''H }
              ::= { connProfileEntry 21 }

          connProfPppRecvAuthSecret OBJECT-TYPE
              SYNTAX    OCTET STRING
              ACCESS    read-write
              STATUS    mandatory
              DESCRIPTION
                        "If the value of the ansProfPppRecvAuthProt
                        object is 'authPAP(2)', then the value of this
                        object is the Password that the remote peer must
                        specify in its PAP Authenticate-Request packets.

                        If the value of the ansProfPppRecvAuthProt
                        object is 'authCHAP(3)', then the value of this
                        object is the Secret that the device will use to
                        verify the Response Value contained in the
                        remote peer's CHAP Response packets.

                        The value of this object is meaningless if the
                        value of the ansProfConnProfRequired object is
                        'connProfNotRequired(2)' or the value of the
                        ansProfPppRecvAuthProt object is 'authNone(1)'.

                        Although the value of this variable may be
                        altered by a management operation (e.g., an SNMP
                        Set Request), its value can never be retrieved
                        by a management operation:  When read, the value
                        of this variable is a zero-length OCTET STRING."
              DEFVAL    { ''H }
              ::= { connProfileEntry 22 }

          connProfStatus OBJECT-TYPE
              SYNTAX    INTEGER {
                            valid(1),
                            invalid(2)
                        }
              ACCESS    read-write
              STATUS    mandatory
              DESCRIPTION
                        "The status of this connection profile.

                        Setting the value of this object to 'invalid(4)'
                        has the effect of invalidating the corresponding
                        entry in the connProfileTable.

                        Whether an agent removes an invalidated entry
                        from the table is an implementation-specific
                        matter. Accordingly, management stations must be
                        prepared to receive tabular information from
                        agents that correspond to entries not currently
                        in use.  Proper interpretation of such entries
                        requires examination of the relevant
                        connProfStatus object."
              DEFVAL    { valid }
              ::= { connProfileEntry 23 }

          ansProfConnProfRequired OBJECT-TYPE
              SYNTAX    INTEGER {
                              connProfRequired(1),
                              connProfNotRequired(2)
                        }
              ACCESS    read-write
              STATUS    mandatory
              DESCRIPTION
                        "Indicates whether or not an incoming call must
                        match a connection profile entry in the
                        connProfileTable.

                        If the value of this object is
                        'connProfRequired(1)', incoming calls not
                        matching a connection profile entry in the
                        connProfileTable will be rejected.

                        If the value of this object is
                        'connProfNotRequired(2)', then incoming calls
                        not matching a connection profile entry in the
                        connProfileTable will be accepted, and will be
                        governed by a temporary connection profile
                        created from the values of the following
                        objects:

                            ansProfIsdnBandwidth
                            ansProfRxRip
                            ansProfTxRip
                            ansProfFilterSetIndex
                            ansProfIdleSeconds
                            ansProfPppMaxRecvUnit
                            ansProfPppLinkCompression
                            ansProfIsdnInForce56K

                        If the value of this object is
                        'connProfNotRequired(2)', the actual value of
                        the ansProfPppRecvAuthProt object is ignored,
                        and the device behaves as if the value of that
                        object is 'authNone(1)'."
              ::= { isdnParams 7 }

          ansProfIsdnBandwidth OBJECT-TYPE
              SYNTAX    INTEGER {
                            oneBChannel(1),
                            twoBChannels(2),
                            dynamicBandwidth(3)
                        }
              ACCESS    read-write
              STATUS    mandatory
              DESCRIPTION
                        "The number of ISDN B-channels the device will
                        use for incoming calls from remote peers not
                        matching a connection profile in the
                        connProfileTable.

                        If the value of this object is 'oneBChannel(1)',
                        the connection will always use exactly one B-
                        channel.

                        If the value of this object is
                        'twoBChannels(2)', the connection will always
                        use exactly two B-channels.

                        If the value of this object is
                        'dynamicBandwidth(3)', the connection will use
                        one or two B-channels.  The number of B-channels
                        in use at any particular point in time will
                        depend on the traffic level to/from the remote
                        peer and the existence of, or need to establish,
                        a simultaneous connection to another remote
                        peer."
              ::= { isdnParams 8 }

          ansProfIsdnInForce56K OBJECT-TYPE
              SYNTAX    INTEGER {
                            dontForce56K(1),
                            force56K(2)
                        }
              ACCESS    read-write
              STATUS    mandatory
              DESCRIPTION
                        "Indicates whether or not the device will ignore
                        the data rate indicated in incoming ISDN calls
                        and assume a data rate of 56K.

                        If the value of this object is
                        'dontForce56K(1)', the device will honor the
                        data rate indicated in incoming ISDN calls.

                        If the value of this object is 'force56K(2)',
                        the device will ignore the data rate indicated
                        in incoming ISDN calls and assume a data rate of
                        56K.

                        The value 'force56K(2)' may be required when a
                        device located outside the United States
                        receives an incoming call that originated from
                        the United States, if the telephone company made
                        a 56K to 64K rate adaption that is not indicated
                        in the incoming ISDN call."
              ::= { isdnParams 9 }

          ansProfRxRip OBJECT-TYPE
              SYNTAX    INTEGER {
                            dontRxRip(1),
                            rxRip(2)
                        }
              ACCESS    read-write
              STATUS    mandatory
              DESCRIPTION
                        "Indicates whether or not the device will
                        receive RIP packets over a WAN connection from a
                        remote peer established for an incoming call not
                        matching a connection profile in the
                        connProfileTable."
              ::= { isdnParams 10 }

          ansProfTxRip OBJECT-TYPE
              SYNTAX    INTEGER {
                            dontTxRip(1),
                            txRip(2)
                        }
              ACCESS    read-write
              STATUS    mandatory
              DESCRIPTION
                        "Indicates whether or not the device will
                        transmit RIP packets over a WAN connection to a
                        remote peer established for an incoming call not
                        matching a connection profile in the
                        connProfileTable."
              ::= { isdnParams 11 }

          ansProfFilterSetIndex OBJECT-TYPE
              SYNTAX    INTEGER
              ACCESS    read-write
              STATUS    mandatory
              DESCRIPTION
                        "Indicates the set of filters to be used to
                        filter packets received and transmitted over the
                        WAN connection to a remote peer not matching a
                        connection profile in the connProfileTable.

                        The filter set identified by a particular value
                        of this object is the same filter set as is
                        identified by the same value of the
                        filterSetIndex object."
              ::= { isdnParams 12 }

          ansProfIdleSeconds OBJECT-TYPE
              SYNTAX    INTEGER (0..2147483647)
              ACCESS    read-write
              STATUS    mandatory
              DESCRIPTION
                        "Indicates the number of seconds during which
                        there must be no outbound traffic over a WAN
                        connection to a remote peer not matching a
                        connection profile in the connProfileTable for
                        the device to clear the call.

                        The value zero prevents the device from clearing
                        the call due to lack of traffic.

                        Note that the remote peer may implement its own
                        policy that may cause the call to be cleared
                        sooner than it would otherwise be cleared based
                        on the value of this object."
              ::= { isdnParams 13 }

          ansProfPppMaxRecvUnit OBJECT-TYPE
              SYNTAX    INTEGER
              ACCESS    read-write
              STATUS    mandatory
              DESCRIPTION
                        "Indicates the size of the largest PPP packet
                        that can be received over a WAN connection with
                        a remote peer established for an incoming call
                        not matching a connection profile in the
                        connProfileTable."
              ::= { isdnParams 14 }

          ansProfPppLinkCompression OBJECT-TYPE
              SYNTAX    INTEGER {
                            negotiateStacCompression(1),
                            noCompression(2)
                        }
              ACCESS    read-write
              STATUS    mandatory
              DESCRIPTION
                        "Indicates whether or not the device will
                        attempt to negotiate PPP link compression for a
                        WAN connection with a remote peer established
                        for an incoming call not matching a connection
                        profile in the connProfileTable.

                        If this object has the value
                        'negotiateStacCompression(1)', then device will
                        attempt to negotiate use of the Stac Electronics
                        proprietary STACKER LZS (tm) compression-
                        decompression algorithm."
              ::= { isdnParams 15 }

          ansProfPppRecvAuthProt OBJECT-TYPE
              SYNTAX    INTEGER {
                            authNone(1),
                            authPAP(2),
                            authCHAP(3)
                        }
              ACCESS    read-write
              STATUS    mandatory
              DESCRIPTION
                        "Indicates the PPP authentication protocol that
                        the device will require a remote peer to use to
                        authenticate itself when the device receives an
                        incoming call from the remote peer.  (The device
                        never requires a remote peer to authenticate
                        itself when the device initiates an outgoing
                        call to a remote peer.)

                        If the value of the ansProfConnProfRequired
                        object is 'connProfNotRequired(2)', the device
                        ignores the actual value of this object and
                        behaves as if it has the value 'authNone(1)'.

                        If the value of this object is 'authNone(1)',
                        the device will not request the use of an
                        authentication protocol during the Link
                        Establishment phase of PPP link establishment,
                        and the remote peer will not be required to
                        authenticate itself.  The device will attempt to
                        match the remote peer's IP address with an
                        instance of the connProfRemIpAddr object.  If it
                        successfully matches a connProfileTable entry,
                        the connection will be governed by the
                        parameters specified by the connProfileTable
                        entry.  If the device is unable to match a
                        connProfileTable entry, the connection will be
                        governed by a temporary connection profile
                        created from the values of the following
                        objects:

                            ansProfIsdnBandwidth
                            ansProfRxRip
                            ansProfTxRip
                            ansProfFilterSetIndex
                            ansProfIdleSeconds
                            ansProfPppMaxRecvUnit
                            ansProfPppLinkCompression
                            ansProfIsdnInForce56K

                        If the value of this object is 'authPAP(2)', and
                        the value of the ansProfConnProfRequired object
                        is 'connProfRequired(1)', the device will
                        require the remote peer to authenticate itself
                        using the Password Authentication Protocol (PAP)
                        described in RFC 1334.  The device will attempt
                        to match the Peer-ID and Password sent by the
                        remote peer in its PAP Authenticate-Request
                        packet to the connProfPppRecvAuthName and
                        connProfPppRecvAuthSecret objects, respectively,
                        in a connProfileTable entry.  If the device
                        successfully matches a connProfileTable entry,
                        the call will be accepted, and the connection
                        will be governed by the parameters specified by
                        the connProfileTable entry.  If the device is
                        unable to match a connProfileTable entry, the
                        call will be rejected.

                        If the value of this object is 'authCHAP(3)',
                        and the value of the ansProfConnProfRequired
                        object is 'connProfRequired(1)', the device will
                        require the remote peer to authenticate itself
                        using the Challenge-Handshake Authentication
                        Protocol (CHAP) described in RFC 1334.  During
                        the Authentication phase of PPP link
                        establishment, the device will send a CHAP
                        Challenge packet to, and expect a CHAP Response
                        packet from, the remote peer.  The
                        ansProfChapChallengeName object indicates the
                        Name that the device will send in its CHAP
                        Challenge packet.  The device will attempt to
                        match the Name sent by the remote peer in its
                        CHAP Response packet to the
                        connProfPppRecvAuthName object in a
                        connProfileTable entry.  The device use the
                        connProfPppRecvAuthSecret value in each matching
                        connProfileTable entry to attempt to verify the
                        Response Value in the remote peer's CHAP
                        Response packet.  If the device successfully
                        matches a connProfileTable entry, the call will
                        be accepted, and the connection will be governed
                        by the parameters specified by the
                        connProfileTable entry.  If the device is unable
                        to match a connProfileTable entry, the call will
                        be rejected."
              REFERENCE
                        "PPP Authentication Protocols, RFC 1334"
              ::= { isdnParams 16 }

          ansProfChapChallengeName OBJECT-TYPE
              SYNTAX    OCTET STRING
              ACCESS    read-write
              STATUS    mandatory
              DESCRIPTION
                        "If the value of the ansProfConnProfRequired
                        object is 'connProfRequired(1)', and the value
                        of the ansProfPppRecvAuthProt object is
                        'authCHAP(3)', then the value of this object is
                        the Name that the device will use to identify
                        itself in CHAP Challenge packets sent to the
                        remote peer when the device answers an incoming
                        call.

                        The value of this object is meaningless if the
                        value of the ansProfConnProfRequired object is
                        'connProfNotRequired(2)' or the value of the
                        ansProfPppRecvAuthProt object is 'authNone(1)'
                        or 'authPAP(2)'."
              ::= { isdnParams 17 }


          --  The Scheduled Connections Table

          schedConnTable OBJECT-TYPE
              SYNTAX    SEQUENCE OF SchedConnEntry
              ACCESS    not-accessible
              STATUS    mandatory
              DESCRIPTION
                        "A list of entries describing automatic,
                        scheduled establishment of connections to the
                        device's remote peers.

                        This table supports 'conceptual row creation'
                        according to section 3.2(3) of RFC 1212:  To add
                        a new row to this table, a management station
                        must provide a value for the new instances of
                        the schedConnDayMask, schedConnStartTime,
                        schedConnDuration, and schedConnRemPeer objects,
                        and may, in addition, provide a value for the
                        corresponding instance of the schedConnEnable
                        and schedConnStatus objects.  If no value is
                        supplied for the corresponding instance of the
                        schedConnEnable object, its value will default
                        to 'disabled(2)'; if no value is supplied for
                        the corresponding instance of the
                        schedConnStatus object, its value will default
                        to 'valid(1)'."
              ::= { isdnParams 18 }

          schedConnEntry OBJECT-TYPE
              SYNTAX    SchedConnEntry
              ACCESS    not-accessible
              STATUS    mandatory
              DESCRIPTION
                        "An entry containing information describing the
                        automatic, scheduled establishment of a
                        connection to one of the device's remote peers."
              INDEX     { schedConnIndex }
              ::= { schedConnTable 1 }

          SchedConnEntry ::=
              SEQUENCE {
                  schedConnIndex
                      INTEGER,
                  schedConnEnable
                      INTEGER,
                  schedConnDayMask
                      INTEGER (1..128),
                  schedConnStartTime
                      OCTET STRING (SIZE(4 | 12)),
                  schedConnDuration
                      INTEGER,
                  schedConnRemPeer
                      INTEGER,
                  schedConnStatus
                      INTEGER
              }

          schedConnIndex OBJECT-TYPE
              SYNTAX    INTEGER
              ACCESS    read-only
              STATUS    mandatory
              DESCRIPTION
                        "A unique value that identifies this scheduled
                        connection."
              ::= { schedConnEntry 1 }

          schedConnEnable OBJECT-TYPE
              SYNTAX    INTEGER {
                            enabled(1),
                            disabled(2)
                        }
              ACCESS    read-write
              STATUS    mandatory
              DESCRIPTION
                        "Indicates whether or not the scheduled
                        connection described by this entry is enabled."
              DEFVAL    { disabled }
              ::= { schedConnEntry 2 }

          schedConnDayMask OBJECT-TYPE
              SYNTAX    INTEGER (1..128)
              ACCESS    read-write
              STATUS    mandatory
              DESCRIPTION
                        "The value of this object indicates whether this
                        entry corresponds to a one-time scheduled
                        connection or a recurring scheduled connection,
                        and, for a recurring connection, indicates the
                        days of the week on which the connection will be
                        attempted.

                        If the value of this object is between 1 and
                        127, then this entry corresponds to a recurring
                        scheduled connection that occurs weekly on one
                        or more days of the week.  The value of this
                        object is a sum of one or more of the following
                        values and indicates the days of the week on
                        which the connection will be attempted:

                             1     Sunday
                             2     Monday
                             4     Tuesday
                             8     Wednesday
                            16     Thursday
                            32     Friday
                            64     Saturday

                        For a recurring connection, the value of the
                        corresponding instance of the schedConnStartTime
                        object consists of four decimal-ASCII digits (in
                        the form 'HHMM') that encode the start time for
                        the connection on the specified days.

                        If the value of this object is 128, then this
                        entry corresponds to a one-time scheduled
                        connection.  The value of the corresponding
                        instance of the schedConnStartTime object
                        consists of twelve decimal-ASCII digits (in the
                        form 'YYMMDDHHMM') that encode the date and time
                        at which the connection will be attempted."
              ::= { schedConnEntry 3 }

          schedConnStartTime OBJECT-TYPE
              SYNTAX    OCTET STRING (SIZE(4 | 12))
              ACCESS    read-write
              STATUS    mandatory
              DESCRIPTION
                        "The time at which the device will attempt to
                        originate a connection with the remote peer.

                        If the value of the schedConnDayMask object is
                        between 1 and 127, then the value of this object
                        consists of four decimal-ASCII digits (in the
                        form 'HHMM') that encode the hour and minute at
                        which the device will attempt to establish the
                        recurring scheduled connection described by this
                        entry.

                        If the value of the schedConnDayMask object is
                        128, then the value of this object consists of
                        twelve decimal-ASCII digits (in the form
                        'YYYYMMDDHHMM') that indicate the date and time
                        at which the device will attempt to establish
                        the one-time scheduled connection described by
                        this entry."
              ::= { schedConnEntry 4 }

          schedConnDuration OBJECT-TYPE
              SYNTAX    INTEGER
              ACCESS    read-write
              STATUS    mandatory
              DESCRIPTION
                        "The duration of this scheduled connection in
                        seconds."
              ::= { schedConnEntry 5 }

          schedConnRemPeer OBJECT-TYPE
              SYNTAX    INTEGER
              ACCESS    read-write
              STATUS    mandatory
              DESCRIPTION
                        "The value of this object identifies the remote
                        peer with which the device will attempt to
                        originate the scheduled connection described by
                        this entry.

                        The remote peer identified by a particular value
                        of this object is the same remote peer as is
                        identified by the same value of the
                        connProfIndex object.

                        The value of the connProfPermittedUse object in
                        the connection profile for the remote peer
                        identified by this object must be either
                        'dialOut(2)' or 'dialInOrOut(3)'."
              ::= { schedConnEntry 6 }

          schedConnStatus OBJECT-TYPE
              SYNTAX    INTEGER {
                            valid(1),
                            invalid(2)
                        }
              ACCESS    read-write
              STATUS    mandatory
              DESCRIPTION
                        "Indicates the status of this scheduled
                        connection.

                        Setting the value of this object to 'invalid(2)'
                        has the effect of invalidating the corresponding
                        entry in the schedConnTable.

                        Whether an agent removes an invalidated entry
                        from the table is an implementation-specific
                        matter.  Accordingly, management stations must
                        be prepared to receive tabular information from
                        agents that correspond to entries not currently
                        in use.  Proper interpretation of such entries
                        requires examination of the relevant
                        schedConnStatus object."
              DEFVAL    { valid }
              ::= { schedConnEntry 7 }


          --  The consoleParams group

          --  This group contains configuration information for the device's
          --  console port.

          consolePortSpeed OBJECT-TYPE
              SYNTAX    INTEGER
              ACCESS    read-write
              STATUS    mandatory
              DESCRIPTION
                        "The speed of the console port in bits per
                        second."
              ::= { consoleParams 1 }

          consolePortDataBits OBJECT-TYPE
              SYNTAX    INTEGER (7..8)
              ACCESS    read-write
              STATUS    mandatory
              DESCRIPTION
                        "The console port's number of data bits."
              ::= { consoleParams 2 }

          consolePortStopBits OBJECT-TYPE
              SYNTAX    INTEGER {
                            one(1),
                            two(2),
                            onePointFive(3)
                        }
              ACCESS    read-write
              STATUS    mandatory
              DESCRIPTION
                        "The console port's number of stop bits."
              ::= { consoleParams 3 }

          consolePortParity OBJECT-TYPE
              SYNTAX    INTEGER {
                            none(1),
                            odd(2),
                            even(3)
                        }
              ACCESS    read-write
              STATUS    mandatory
              DESCRIPTION
                        "The console port's parity setting."
              ::= { consoleParams 4 }

          consolePortRxChars OBJECT-TYPE
              SYNTAX    Counter
              ACCESS    read-only
              STATUS    mandatory
              DESCRIPTION
                        "The number of good characters received by the
                        console port."
              ::= { consoleParams 5 }

          consolePortTxChars OBJECT-TYPE
              SYNTAX    Counter
              ACCESS    read-only
              STATUS    mandatory
              DESCRIPTION
                        "The number of characters transmitted by the
                        console port."
              ::= { consoleParams 6 }

          consolePortParityErrors OBJECT-TYPE
              SYNTAX    Counter
              ACCESS    read-only
              STATUS    mandatory
              DESCRIPTION
                        "The number of characters received by the
                        console port with a parity error indication."
              ::= { consoleParams 7 }

          consolePortFramingErrors OBJECT-TYPE
              SYNTAX    Counter
              ACCESS    read-only
              STATUS    mandatory
              DESCRIPTION
                        "The number of characters received by the
                        console port with a framing error indication."
              ::= { consoleParams 8 }

          consolePortOverrunErrors OBJECT-TYPE
              SYNTAX    Counter
              ACCESS    read-only
              STATUS    mandatory
              DESCRIPTION
                        "The number of characters received by the
                        console port with an overrun error indication."
              ::= { consoleParams 9 }


          --  The pcCardParams group

          --  This group contains objects providing information about
          --  the device's PC Card slots and the PC Cards, if any, in
          --  those slots.


          --  The PC Card Slot Table

          pcCardSlotTable OBJECT-TYPE
              SYNTAX    SEQUENCE OF PcCardSlotEntry
              ACCESS    not-accessible
              STATUS    mandatory
              DESCRIPTION
                        "A list of entries providing information about
                        the device's PC Card slots."
              ::= { pcCardParams 1 }

          pcCardSlotEntry OBJECT-TYPE
              SYNTAX    PcCardSlotEntry
              ACCESS    not-accessible
              STATUS    mandatory
              DESCRIPTION
                        "A entry providing information about one of the
                        device's PC Card slots."
              INDEX     { pcCardSlotIndex }
              ::= { pcCardSlotTable 1 }

          PcCardSlotEntry ::=
              SEQUENCE {
                  pcCardSlotIndex
                      INTEGER,
                  pcCardSlotCardPresent
                      INTEGER
              }

          pcCardSlotIndex OBJECT-TYPE
              SYNTAX    INTEGER
              ACCESS    read-only
              STATUS    mandatory
              DESCRIPTION
                        "A unique integer for each of the device's PC
                        Card slots."
              ::= { pcCardSlotEntry 1 }

          pcCardSlotCardPresent OBJECT-TYPE
              SYNTAX    INTEGER {
                            present(1),
                            notPresent(2)
                        }
              ACCESS    read-only
              STATUS    mandatory
              DESCRIPTION
                        "Indicates whether or not a PC Card is present
                        in this PC Card slot."
              ::= { pcCardSlotEntry 2 }


          --  The PC Card Card Table

          pcCardCardTable OBJECT-TYPE
              SYNTAX    SEQUENCE OF PcCardCardEntry
              ACCESS    not-accessible
              STATUS    mandatory
              DESCRIPTION
                        "A list of entries providing information about
                        the PC Cards present in the device's PC Card
                        slots."
              ::= { pcCardParams 2 }

          pcCardCardEntry OBJECT-TYPE
              SYNTAX    PcCardCardEntry
              ACCESS    not-accessible
              STATUS    mandatory
              DESCRIPTION
                        "An entry providing information about one of the
                        PC Cards present in one of the device's PC Card
                        slots."
              INDEX     { pcCardSlotIndex }
              ::= { pcCardCardTable 1 }

          PcCardCardEntry ::=
              SEQUENCE {
                  pcCardCardMfrName
                      OCTET STRING (SIZE(0..255)),
                  pcCardCardProdName
                      OCTET STRING (SIZE(0..255)),
                  pcCardCardProdInfo1
                      OCTET STRING (SIZE(0..255)),
                  pcCardCardProdInfo2
                      OCTET STRING (SIZE(0..255)),
                  pcCardCardFunction
                      INTEGER (0..256)
              }

          pcCardCardMfrName OBJECT-TYPE
              SYNTAX    OCTET STRING (SIZE(0..255))
              ACCESS    read-only
              STATUS    mandatory
              DESCRIPTION
                        "The manufacturer name of the PC Card described
                        by this entry.  The value of this object is the
                        first ASCIIZ string in the TPLLV1_INFO field of
                        the 'Level 1 Version/Product Information' tuple
                        (CISTPL_VERS_1).

                        If the PC Card has no Level 1 Version/Product
                        information tuple, the value of this object will
                        be a zero-length OCTET STRING."
              ::= { pcCardCardEntry 1 }

          pcCardCardProdName OBJECT-TYPE
              SYNTAX    OCTET STRING (SIZE(0..255))
              ACCESS    read-only
              STATUS    mandatory
              DESCRIPTION
                        "The product name of the PC Card described by
                        this entry.  The value of this object is the
                        second ASCIIZ string in the TPLLV1_INFO field of
                        the 'Level 1 Version/Product Information' tuple
                        (CISTPL_VERS_1).

                        If the PC Card has no Level 1 Version/Product
                        information tuple, the value of this object will
                        be a zero-length OCTET STRING."
              ::= { pcCardCardEntry 2 }

          pcCardCardProdInfo1 OBJECT-TYPE
              SYNTAX    OCTET STRING (SIZE(0..255))
              ACCESS    read-only
              STATUS    mandatory
              DESCRIPTION
                        "The first additional product information string
                        of the PC Card described by this entry.  The
                        value of this object is the third ASCIIZ string
                        in the TPLLV1_INFO field of the 'Level 1
                        Version/Product Information' tuple
                        (CISTPL_VERS_1).

                        If the PC Card has no Level 1 Version/Product
                        information tuple, the value of this object will
                        be a zero-length OCTET STRING."
              ::= { pcCardCardEntry 3 }

          pcCardCardProdInfo2 OBJECT-TYPE
              SYNTAX    OCTET STRING (SIZE(0..255))
              ACCESS    read-only
              STATUS    mandatory
              DESCRIPTION
                        "The second additional product information
                        string of the PC Card described by this entry.
                        The value of this object is the fourth ASCIIZ
                        string in the TPLLV1_INFO field of the 'Level 1
                        Version/Product Information' tuple
                        (CISTPL_VERS_1).

                        If the PC Card has no Level 1 Version/Product
                        information tuple, the value of this object will
                        be a zero-length OCTET STRING."
              ::= { pcCardCardEntry 4 }

          pcCardCardFunction OBJECT-TYPE
              SYNTAX    INTEGER (0..256)
              ACCESS    read-only
              STATUS    mandatory
              DESCRIPTION
                        "A code indicating the major function of the PC
                        Card described by this entry.  The value of this
                        object is the value of the third octet of the
                        Function ID tuple (CISTPL_FUNCID).  The
                        following values are defined:

                            0   Multifunction card
                            1   Memory card
                            2   Serial Port/Modem
                            3   Parallel Port
                            4   Fixed Disk
                            5   Video Adapter
                            6   Network/LAN Adapter
                            7   AIMS Memory card

                        If the PC Card has no Function ID tuple, then
                        the value of this object will be 256."
              ::= { pcCardCardEntry 5 }


          --  The PC Card Modem Table

          pcCardModemTable OBJECT-TYPE
              SYNTAX    SEQUENCE OF PcCardModemEntry
              ACCESS    not-accessible
              STATUS    mandatory
              DESCRIPTION
                        "A list of entries providing information about
                        the PC Card modems present in the device's PC
                        Card slots."
              ::= { pcCardParams 3 }

          pcCardModemEntry OBJECT-TYPE
              SYNTAX    PcCardModemEntry
              ACCESS    not-accessible
              STATUS    mandatory
              DESCRIPTION
                        "An entry providing information about one of the
                        PC Card modems present in one of the device's PC
                        Card slots."
              INDEX     { pcCardSlotIndex }
              ::= { pcCardModemTable 1 }

          PcCardModemEntry ::=
              SEQUENCE {
                  pcCardModemActive
                      INTEGER,
                  pcCardModemSessions
                      Counter,
                  pcCardModemTotalRxChars
                      Counter,
                  pcCardModemTotalTxChars
                      Counter
              }

          pcCardModemActive OBJECT-TYPE
              SYNTAX    INTEGER {
                            active(1),
                            inactive(2)
                        }
              ACCESS    read-only
              STATUS    mandatory
              DESCRIPTION
                        "The state of the PC Card modem described by
                        this entry.

                        The value 'inactive(1)' indicates that there is
                        no active connection.  The value 'active(2)'
                        indicates that there is an active connection."
              ::= { pcCardModemEntry 1 }

          pcCardModemSessions OBJECT-TYPE
              SYNTAX    Counter
              ACCESS    read-only
              STATUS    mandatory
              DESCRIPTION
                        "The number of sessions initiated using this PC
                        Card modem since it was last inserted.  The
                        value of this object is incremented each time
                        the modem goes off hook."
              ::= { pcCardModemEntry 2 }

          pcCardModemTotalRxChars OBJECT-TYPE
              SYNTAX    Counter
              ACCESS    read-only
              STATUS    mandatory
              DESCRIPTION
                        "The total number of good characters received
                        from this PC Card modem since it was last
                        inserted."
              ::= { pcCardModemEntry 3 }

          pcCardModemTotalTxChars OBJECT-TYPE
              SYNTAX    Counter
              ACCESS    read-only
              STATUS    mandatory
              DESCRIPTION
                        "The total number of characters transmitted to
                        this PC Card modem since it was last inserted."
              ::= { pcCardModemEntry 4 }


          --  The PC Card Modem Connection Table

          pcCardModemConnTable OBJECT-TYPE
              SYNTAX    SEQUENCE OF PcCardModemConnEntry
              ACCESS    not-accessible
              STATUS    mandatory
              DESCRIPTION
                        "A list of entries providing information about
                        the active sessions using the PC Card modems
                        present in the device's PC Card slots."
              ::= { pcCardParams 4 }

          pcCardModemConnEntry OBJECT-TYPE
              SYNTAX    PcCardModemConnEntry
              ACCESS    not-accessible
              STATUS    mandatory
              DESCRIPTION
                        "An entry providing information about an active
                        session using the PC Card modem present in one
                        of the device's PC Card slots."
              INDEX     { pcCardSlotIndex }
              ::= { pcCardModemConnTable 1 }

          PcCardModemConnEntry ::=
              SEQUENCE {
                  pcCardModemConnSpeed
                      INTEGER,
                  pcCardModemConnDataBits
                      INTEGER (7..8),
                  pcCardModemConnStopBits
                      INTEGER,
                  pcCardModemConnParity
                      INTEGER,
                  pcCardModemConnRxChars
                      Counter,
                  pcCardModemConnTxChars
                      Counter
              }

          pcCardModemConnSpeed OBJECT-TYPE
              SYNTAX    INTEGER
              ACCESS    read-only
              STATUS    mandatory
              DESCRIPTION
                        "The speed, in bits per second, of the active
                        modem connection described by this entry."
              ::= { pcCardModemConnEntry 1 }

          pcCardModemConnDataBits OBJECT-TYPE
              SYNTAX    INTEGER (7..8)
              ACCESS    read-only
              STATUS    mandatory
              DESCRIPTION
                        "The number of data bits for the active modem
                        connection described by this entry."
              ::= { pcCardModemConnEntry 2 }

          pcCardModemConnStopBits OBJECT-TYPE
              SYNTAX    INTEGER {
                            one(1),
                            two(2),
                            onePointFive(3)
                        }
              ACCESS    read-only
              STATUS    mandatory
              DESCRIPTION
                        "The number of stop bits for the active modem
                        connection described by this entry."
              ::= { pcCardModemConnEntry 3 }

          pcCardModemConnParity OBJECT-TYPE
              SYNTAX    INTEGER {
                            none(1),
                            odd(2),
                            even(3)
                        }
              ACCESS    read-only
              STATUS    mandatory
              DESCRIPTION
                        "The parity setting for the active modem
                        connection described by this entry."
              ::= { pcCardModemConnEntry 4 }

          pcCardModemConnRxChars OBJECT-TYPE
              SYNTAX    Counter
              ACCESS    read-only
              STATUS    mandatory
              DESCRIPTION
                        "The number of good characters received from the
                        PC Card modem during the active modem connection
                        described by this entry."
              ::= { pcCardModemConnEntry 5 }

          pcCardModemConnTxChars OBJECT-TYPE
              SYNTAX    Counter
              ACCESS    read-only
              STATUS    mandatory
              DESCRIPTION
                        "The number of characters transmitted to the PC
                        Card modem during the active modem connection
                        described by this entry."
              ::= { pcCardModemConnEntry 6 }


          --  The logParams group

          --  This group contains definitions of objects that control the
          --  device's various logging mechanisms.


          --  The System Event Log

          eventLogEnable OBJECT-TYPE
              SYNTAX    INTEGER {
                            enabled(1),
                            disabled(2)
                        }
              ACCESS    read-write
              STATUS    mandatory
              DESCRIPTION
                        "The value of this object indicates whether or
                        not system event logging is currently enabled.
                        Changes to this object take effect immediately."
              ::= { logParams 1 }

          eventLogSize OBJECT-TYPE
              SYNTAX    INTEGER
              ACCESS    read-only
              STATUS    mandatory
              DESCRIPTION
                        "The maximum number of entries retrievable from
                        the system event log.  If the value of this
                        object is greater than the value of the
                        eventLogCount object, then only eventLogCount
                        entries have been logged and can be retrieved."
              ::= { logParams 2 }

          eventLogCount OBJECT-TYPE
              SYNTAX    Counter
              ACCESS    read-write
              STATUS    mandatory
              DESCRIPTION
                        "The total number of events logged to the system
                        event log.  If the value of this object exceeds
                        the value of the eventLogSize object, only the
                        most recent eventLogSize entries can be
                        retrieved.

                        Setting the value of this object to zero clears
                        the device's system event log."
              ::= { logParams 3 }


          --  The System Event Log Table

          eventLogTable OBJECT-TYPE
              SYNTAX    SEQUENCE OF EventLogEntry
              ACCESS    not-accessible
              STATUS    mandatory
              DESCRIPTION
                        "A list of system event log entries."
              ::= { logParams 4 }

          eventLogEntry OBJECT-TYPE
              SYNTAX    EventLogEntry
              ACCESS    not-accessible
              STATUS    mandatory
              DESCRIPTION
                        "A single system event log entry."
              INDEX     { eventLogIndex }
              ::= { eventLogTable 1 }

          EventLogEntry ::=
              SEQUENCE {
                  eventLogIndex
                      INTEGER,
                  eventLogTime
                      DisplayString,
                  eventLogDescr
                      DisplayString,
                  eventLogDetail
                      DisplayString,
                  eventLogRawEntry
                      OCTET STRING
              }

          eventLogIndex OBJECT-TYPE
              SYNTAX    INTEGER
              ACCESS    read-only
              STATUS    mandatory
              DESCRIPTION
                        "A unique value for each entry in the event log.
                        Its value is between 1 and the minimum of the
                        value of the eventLogSize and eventLogCount
                        objects.  The oldest event in the log
                        corresponds to index 1."
              ::= { eventLogEntry 1 }

          eventLogTime OBJECT-TYPE
              SYNTAX    DisplayString
              ACCESS    read-only
              STATUS    mandatory
              DESCRIPTION
                        "The time (according to the system clock) in
                        human-readable form at which this system event
                        log entry was logged."
              ::= { eventLogEntry 2 }

          eventLogDescr OBJECT-TYPE
              SYNTAX    DisplayString
              ACCESS    read-only
              STATUS    mandatory
              DESCRIPTION
                        "A human-readable string describing the event
                        represented by this system event log entry."
              ::= { eventLogEntry 3 }

          eventLogDetail OBJECT-TYPE
              SYNTAX    DisplayString
              ACCESS    read-only
              STATUS    mandatory
              DESCRIPTION
                        "A human-readable string providing more detailed
                        information about the event represented by this
                        system event log entry."
              ::= { eventLogEntry 4 }

          eventLogRawEntry OBJECT-TYPE
              SYNTAX    OCTET STRING
              ACCESS    read-only
              STATUS    mandatory
              DESCRIPTION
                        "The raw, unformatted system event log entry as
                        it appears internally."
              ::= { eventLogEntry 5 }


          --  The ISDN Event Log

          isdnLogEnable OBJECT-TYPE
              SYNTAX    INTEGER {
                            enabled(1),
                            disabled(2)
                        }
              ACCESS    read-write
              STATUS    mandatory
              DESCRIPTION
                        "The value of this object indicates whether or
                        not ISDN event logging is currently enabled.
                        Changes to this object take effect immediately."
              ::= { logParams 5 }

          isdnLogSize OBJECT-TYPE
              SYNTAX    INTEGER
              ACCESS    read-only
              STATUS    mandatory
              DESCRIPTION
                        "The maximum number of entries retrievable from
                        the device's ISDN event log.  If the value of
                        this object is greater than the value of the
                        isdnLogCount object, then only isdnLogCount
                        entries have been logged and can be retrieved."
              ::= { logParams 6 }

          isdnLogCount OBJECT-TYPE
              SYNTAX    Counter
              ACCESS    read-write
              STATUS    mandatory
              DESCRIPTION
                        "The total number of events logged to the ISDN
                        event log.  If the value of this object exceeds
                        the value of the isdnLogSize object, only the
                        most recent isdnLogSize entries can be
                        retrieved.

                        Setting the value of this object to zero clears
                        the device's ISDN event log."
              ::= { logParams 7 }


          --  The ISDN Log Table

          isdnLogTable OBJECT-TYPE
              SYNTAX    SEQUENCE OF IsdnLogEntry
              ACCESS    not-accessible
              STATUS    mandatory
              DESCRIPTION
                        "A list of ISDN event log entries."
              ::= { logParams 8 }

          isdnLogEntry OBJECT-TYPE
              SYNTAX    IsdnLogEntry
              ACCESS    not-accessible
              STATUS    mandatory
              DESCRIPTION
                        "A single ISDN event log entry."
              INDEX     { eventLogIndex }
              ::= { isdnLogTable 1 }

          IsdnLogEntry ::=
              SEQUENCE {
                  isdnLogIndex
                      INTEGER,
                  isdnLogTime
                      DisplayString,
                  isdnLogDescr
                      DisplayString,
                  isdnLogDetail
                      DisplayString,
                  isdnLogRawEntry
                      OCTET STRING
              }

          isdnLogIndex OBJECT-TYPE
              SYNTAX    INTEGER
              ACCESS    read-only
              STATUS    mandatory
              DESCRIPTION
                        "A unique value for each entry in the ISDN event
                        log.  Its value is between 1 and the minimum of
                        the value of the isdnLogSize and isdnLogCount
                        objects.  The oldest event in the log
                        corresponds to index 1."
              ::= { isdnLogEntry 1 }

          isdnLogTime OBJECT-TYPE
              SYNTAX    DisplayString
              ACCESS    read-only
              STATUS    mandatory
              DESCRIPTION
                        "The time (according to the system clock) in
                        human-readable form at which this ISDN event log
                        entry was logged."
              ::= { isdnLogEntry 2 }

          isdnLogDescr OBJECT-TYPE
              SYNTAX    DisplayString
              ACCESS    read-only
              STATUS    mandatory
              DESCRIPTION
                        "A human-readable string describing the ISDN
                        event represented by this ISDN event log entry."
              ::= { isdnLogEntry 3 }

          isdnLogDetail OBJECT-TYPE
              SYNTAX    DisplayString
              ACCESS    read-only
              STATUS    mandatory
              DESCRIPTION
                        "A human-readable string providing more detailed
                        information about the ISDN event represented by
                        this ISDN event log entry."
              ::= { isdnLogEntry 4 }

          isdnLogRawEntry OBJECT-TYPE
              SYNTAX    OCTET STRING
              ACCESS    read-only
              STATUS    mandatory
              DESCRIPTION
                        "The raw, unformatted ISDN log entry as it
                        appears internally."
              ::= { isdnLogEntry 5 }


          --  The filterParams group

          --  This group contains definitions of objects that control
          --  the device's packet filtering mechanism.


          --  The Filter Set Table

          filterSetTable OBJECT-TYPE
              SYNTAX    SEQUENCE OF FilterSetEntry
              ACCESS    not-accessible
              STATUS    mandatory
              DESCRIPTION
                        "A list of entries providing information about
                        the device's packet filter sets.

                        This table supports 'conceptual row creation'
                        according to section 3.2(3) of RFC 1212:  To add
                        a new row to this table, a management station
                        must provide a value for at least one of the
                        read-write object instances in the new row.  If
                        the management station fails to provide a value
                        for a read-write object instance in the new row,
                        the instance will have the value indicated by
                        the corresponding object's DEFVAL clause.

                        Note that the device will implicitly create a
                        new row in this table if a management station
                        adds an entry to the ipFilterTable or
                        genericFilterTable corresponding to a filter set
                        for which there is not already a row in this
                        table.  Each object instance in the new row will
                        have the value indicated by the corresponding
                        object's DEFVAL clause."
              ::= { filterParams 1 }

          filterSetEntry OBJECT-TYPE
              SYNTAX    FilterSetEntry
              ACCESS    not-accessible
              STATUS    mandatory
              DESCRIPTION
                        "An entry providing information about one of the
                        device's packet filter sets."
              INDEX     { filterSetIndex }
              ::= { filterSetTable 1 }

          FilterSetEntry ::=
              SEQUENCE {
                  filterSetIndex
                      INTEGER,
                  filterSetEnable
                      INTEGER,
                  filterSetName
                      OCTET STRING,
                  filterSetStatus
                      INTEGER
              }

          filterSetIndex OBJECT-TYPE
              SYNTAX    INTEGER
              ACCESS    read-only
              STATUS    mandatory
              DESCRIPTION
                        "A unique value for each of the device's packet
                        filter sets."
              ::= { filterSetEntry 1 }

          filterSetEnable OBJECT-TYPE
              SYNTAX    INTEGER {
                            enabled(1),
                            disabled(2)
                        }
              ACCESS    read-only
              STATUS    mandatory
              DESCRIPTION
                        "Indicates whether or not the filter set
                        described by this entry is enabled."
              DEFVAL    { enabled }
              ::= { filterSetEntry 2 }

          filterSetName OBJECT-TYPE
              SYNTAX    OCTET STRING
              ACCESS    read-write
              STATUS    mandatory
              DESCRIPTION
                        "An optional descriptive name for the packet
                        filter set described by this entry."
              DEFVAL    { ''H }
              ::= { filterSetEntry 3 }

          filterSetStatus OBJECT-TYPE
              SYNTAX    INTEGER {
                            valid(1),
                            invalid(2)
                        }
              ACCESS    read-only
              STATUS    mandatory
              DESCRIPTION
                        "The status of this filter set entry.

                        Setting this object to the value 'invalid(2)'
                        has the effect of invalidating the corresponding
                        entry in the filterSetTable.  That is, it
                        effectively disassociates the mapping identified
                        with said entry.  It is an implementation-
                        specific matter as to whether the agent removes
                        an invalidated entry from the table.
                        Accordingly, management stations must be
                        prepared to receive from agents tabular
                        information corresponding to entries not
                        currently in use.  Proper interpretation of such
                        entries requires examination of the relevant
                        filterSetStatus object.

                        Note:  Invalidating a filter set entry in this
                        table will also invalidate any entries in the
                        ipFilterTable and genericFilterTable that are
                        associated with the filter set."
              DEFVAL    { valid }
              ::= { filterSetEntry 4 }


          --  The IP Filter Table

          ipFilterTable OBJECT-TYPE
              SYNTAX    SEQUENCE OF IpFilterEntry
              ACCESS    not-accessible
              STATUS    mandatory
              DESCRIPTION
                        "A list of entries providing information about
                        the device's IP packet filters.

                        This table supports 'conceptual row creation'
                        according to section 3.2(3) of RFC 1212:  To add
                        a new row to this table, a management station
                        must provide a value for at least one of the
                        read-write object instances in the new row.  If
                        the management station fails to provide a value
                        for a read-write object instance in the new row,
                        the instance will have the value indicated by
                        the corresponding object's DEFVAL clause.

                        Note that the device will implicitly create a
                        new row in the filterSetTable if a management
                        station adds an entry to the ipFilterTable
                        corresponding to a filter set for which there is
                        not already a row in the filterSetTable.  Each
                        object instance in the new row in the
                        filterSetTable will have the value indicated by
                        the corresponding object's DEFVAL clause."
              ::= { filterParams 2 }

          ipFilterEntry OBJECT-TYPE
              SYNTAX    IpFilterEntry
              ACCESS    not-accessible
              STATUS    mandatory
              DESCRIPTION
                        "An entry providing information about one of the
                        device's IP packet filters."
              INDEX     { filterSetIndex, ipFilterDirection, ipFilterIndex }
              ::= { ipFilterTable 1 }

          IpFilterEntry ::=
              SEQUENCE {
                  ipFilterDirection
                      INTEGER,
                  ipFilterIndex
                      INTEGER,
                  ipFilterEnable
                      INTEGER,
                  ipFilterForward
                      INTEGER,
                  ipFilterSrcMask
                      IpAddress,
                  ipFilterSrcAddr
                      IpAddress,
                  ipFilterDstMask
                      IpAddress,
                  ipFilterDstAddr
                      IpAddress,
                  ipFilterProtType
                      INTEGER (0..255),
                  ipFilterSrcPortComparison
                      INTEGER,
                  ipFilterSrcPort
                      INTEGER (0..65535),
                  ipFilterDstPortComparison
                      INTEGER,
                  ipFilterDstPort
                      INTEGER (0..65535),
                  ipFilterStatus
                      INTEGER
              }

          ipFilterDirection OBJECT-TYPE
              SYNTAX    INTEGER {
                            input(1),
                            output(2)
                        }
              ACCESS    read-only
              STATUS    mandatory
              DESCRIPTION
                        "Indicates whether the IP packet filter
                        described by this entry is an input filter or an
                        output filter."
              ::= { ipFilterEntry 1 }

          ipFilterIndex OBJECT-TYPE
              SYNTAX    INTEGER
              ACCESS    read-only
              STATUS    mandatory
              DESCRIPTION
                        "A unique value for each of the input and output
                        packet filters in the filter set associated with
                        this IP packet filter."
              ::= { ipFilterEntry 2 }

          ipFilterEnable OBJECT-TYPE
              SYNTAX    INTEGER {
                            enabled(1),
                            disabled(2)
                        }
              ACCESS    read-write
              STATUS    mandatory
              DESCRIPTION
                        "Indicates whether the IP packet filter
                        described by this entry is enabled or disabled."
              DEFVAL    { disabled }
              ::= { ipFilterEntry 3 }

          ipFilterForward OBJECT-TYPE
              SYNTAX    INTEGER {
                            forward(1),
                            drop(2)
                        }
              ACCESS    read-write
              STATUS    mandatory
              DESCRIPTION
                        "Indicates whether the device will forward or
                        drop an IP packet matching the parameters of
                        this IP packet filter."
              DEFVAL    { forward }
              ::= { ipFilterEntry 4 }

          ipFilterSrcMask OBJECT-TYPE
              SYNTAX    IpAddress
              ACCESS    read-write
              STATUS    mandatory
              DESCRIPTION
                        "Indicates the value that the device will
                        logically AND with the source IP address in an
                        IP packet being passed through this filter
                        before that address is compared with the value
                        of the corresponding instance of
                        ipFilterSrcAddr."
              DEFVAL    { ''H }
              ::= { ipFilterEntry 5 }

          ipFilterSrcAddr OBJECT-TYPE
              SYNTAX    IpAddress
              ACCESS    read-write
              STATUS    mandatory
              DESCRIPTION
                        "Indicates the value that must be produced by
                        the logical AND of the source IP address in an
                        IP packet and the value of ipFilterSrcMask for
                        the IP packet to satisfy this filter."
              DEFVAL    { ''H }
              ::= { ipFilterEntry 6 }

          ipFilterDstMask OBJECT-TYPE
              SYNTAX    IpAddress
              ACCESS    read-write
              STATUS    mandatory
              DESCRIPTION
                        "Indicates the value that the device will
                        logically AND with the destination IP address in
                        an IP packet being passed through this filter
                        before that address is compared with the value
                        of the corresponding instance of
                        ipFilterDstAddr."
              DEFVAL    { ''H }
              ::= { ipFilterEntry 7 }

          ipFilterDstAddr OBJECT-TYPE
              SYNTAX    IpAddress
              ACCESS    read-write
              STATUS    mandatory
              DESCRIPTION
                        "Indicates the value that must be produced by
                        the logical AND of the destination IP address in
                        an IP packet and the value of ipFilterDstMask
                        for the IP packet to satisfy this filter."
              DEFVAL    { ''H }
              ::= { ipFilterEntry 8 }

          ipFilterProtType OBJECT-TYPE
              SYNTAX    INTEGER (0..255)
              ACCESS    read-write
              STATUS    mandatory
              DESCRIPTION
                        "Indicates the value that must be present in the
                        protocol field (octet 10) of the IP header of an
                        IP packet for the packet to satisfy this filter.
                        The value zero matches any protocol field
                        value."
              DEFVAL    { 0 }
              ::= { ipFilterEntry 9 }

          ipFilterSrcPortComparison OBJECT-TYPE
              SYNTAX    INTEGER {
                            none(1),      -- no comparison
                            lt(2),        -- less than
                            le(3),        -- less than or equal
                            eq(4),        -- equal
                            ne(5),        -- not equal
                            gt(6),        -- greater than
                            ge(7)         -- greater than or equal
                        }
              ACCESS    read-write
              STATUS    mandatory
              DESCRIPTION
                        "Indicates the relational operator that the
                        device will use to compare the udp or tcp source
                        port specified in a udp or tcp packet with the
                        value of the corresponding instance of the
                        ipFilterSrcPort object.

                        The value of this object is meaningful only when
                        the value of the corresponding instance of the
                        ipFilterProtType object is 6 (tcp) or 17 (udp).

                        If the value of this object is 'none(1)', no
                        comparison is performed."
              DEFVAL    { none }
              ::= { ipFilterEntry 10 }

          ipFilterSrcPort OBJECT-TYPE
              SYNTAX    INTEGER (0..65535)
              ACCESS    read-write
              STATUS    mandatory
              DESCRIPTION
                        "Indicates the value to which the device will
                        compare the udp or tcp source port specified in
                        an udp or tcp packet to determine whether or not
                        the packet satisfies this filter.  The value of
                        the corresponding instance of the
                        ipFilterSrcPortComparison object indicates the
                        relational operator that the device will use for
                        the comparison.

                        The value of this object is meaningful only when
                        the value of the corresponding instance of the
                        ipFilterProtType object is 6 (tcp) or 17 (udp),
                        and the value of the corresponding instance of
                        the ipFilterSrcPortComparison object is not
                        'none(1)'."
              DEFVAL    { 0 }
              ::= { ipFilterEntry 11 }

          ipFilterDstPortComparison OBJECT-TYPE
              SYNTAX    INTEGER {
                            none(1),      -- no comparison
                            lt(2),        -- less than
                            le(3),        -- less than or equal
                            eq(4),        -- equal
                            ne(5),        -- not equal
                            gt(6),        -- greater than
                            ge(7)         -- greater than or equal
                        }
              ACCESS    read-write
              STATUS    mandatory
              DESCRIPTION
                        "Indicates the relational operator that the
                        device will use to compare the udp or tcp
                        destination port specified in a udp or tcp
                        packet with the value of the corresponding
                        instance of the ipFilterDstPort object.

                        The value of this object is meaningful only when
                        the value of the corresponding instance of the
                        ipFilterProtType object is 6 (tcp) or 17 (udp).

                        If the value of this object is 'none(1)', no
                        comparison is performed."
              DEFVAL    { none }
              ::= { ipFilterEntry 12 }

          ipFilterDstPort OBJECT-TYPE
              SYNTAX    INTEGER (0..65535)
              ACCESS    read-write
              STATUS    mandatory
              DESCRIPTION
                        "Indicates the value to which the device will
                        compare the udp or tcp destination port
                        specified in an udp or tcp packet to determine
                        whether or not the packet satisfies this filter.
                        The value of the corresponding instance of the
                        ipFilterDstPortComparison object indicates the
                        relational operator that the device will use for
                        the comparison.

                        The value of this object is meaningful only when
                        the value of the corresponding instance of the
                        ipFilterProtType object is 6 (tcp) or 17 (udp)
                        and the value of the corresponding instance of
                        the ipFilterDstPortComparison object is not
                        'none(1)'."
              DEFVAL    { 0 }
              ::= { ipFilterEntry 13 }

          ipFilterStatus OBJECT-TYPE
              SYNTAX    INTEGER {
                            valid(1),
                            invalid(2)
                        }
              ACCESS    read-write
              STATUS    mandatory
              DESCRIPTION
                        "Indicates the status of this IP filter entry.

                        Setting this object to the value 'invalid(2)'
                        has the effect of invalidating the corresponding
                        entry in the ipFilterTable.  That is, it
                        effectively disassociates the mapping identified
                        with said entry.  It is an implementation-
                        specific matter as to whether the agent removes
                        an invalidated entry from the table.
                        Accordingly, management stations must be
                        prepared to receive from agents tabular
                        information corresponding to entries not
                        currently in use.  Proper interpretation of such
                        entries requires examination of the relevant
                        ipFilterStatus object."
              DEFVAL    { valid }
              ::= { ipFilterEntry 14 }


          --  The Generic Filter Table

          genericFilterTable OBJECT-TYPE
              SYNTAX    SEQUENCE OF GenericFilterEntry
              ACCESS    not-accessible
              STATUS    mandatory
              DESCRIPTION
                        "A list of entries providing information about
                        the device's generic packet filters.

                        This table supports 'conceptual row creation'
                        according to section 3.2(3) of RFC 1212:  To add
                        a new row to this table, a management station
                        must provide a value for at least one of the
                        read-write object instances in the new row.  If
                        the management station fails to provide a value
                        for a read-write object instance in the new row,
                        the instance will have the value indicated by
                        the corresponding object's DEFVAL clause.

                        Note that the device will implicitly create a
                        new row in the filterSetTable if a management
                        station adds an entry to the genericFilterTable
                        corresponding to a filter set for which there is
                        not already a row in the filterSetTable.  Each
                        object instance in the new row in the
                        filterSetTable will have the value indicated by
                        the corresponding object's DEFVAL clause."
              ::= { filterParams 3 }

          genericFilterEntry OBJECT-TYPE
              SYNTAX    GenericFilterEntry
              ACCESS    not-accessible
              STATUS    mandatory
              DESCRIPTION
                        "An entry providing information about one of the
                        device's generic packet filters."
              INDEX     { filterSetIndex, genericFilterDirection,
                          genericFilterIndex }
              ::= { genericFilterTable 1 }

          GenericFilterEntry ::=
              SEQUENCE {
                  genericFilterDirection
                      INTEGER,
                  genericFilterIndex
                      INTEGER,
                  genericFilterEnable
                      INTEGER,
                  genericFilterForward
                      INTEGER,
                  genericFilterOffset
                      INTEGER (0..65535),
                  genericFilterMask
                      OCTET STRING (SIZE(0..8)),
                  genericFilterValue
                      OCTET STRING (SIZE(0..8)),
                  genericFilterComparison
                      INTEGER,
                  genericFilterChained
                      INTEGER,
                  genericFilterStatus
                      INTEGER
              }

          genericFilterDirection OBJECT-TYPE
              SYNTAX    INTEGER {
                            input(1),
                            output(2)
                        }
              ACCESS    read-only
              STATUS    mandatory
              DESCRIPTION
                        "Indicates whether the generic packet filter
                        described by this entry is an input filter or an
                        output filter."
              ::= { genericFilterEntry 1 }

          genericFilterIndex OBJECT-TYPE
              SYNTAX    INTEGER
              ACCESS    read-only
              STATUS    mandatory
              DESCRIPTION
                        "A unique value for each of the input and output
                        packet filters in the filter set associated with
                        this generic packet filter."
              ::= { genericFilterEntry 2 }

          genericFilterEnable OBJECT-TYPE
              SYNTAX    INTEGER {
                            enabled(1),
                            disabled(2)
                        }
              ACCESS    read-write
              STATUS    mandatory
              DESCRIPTION
                        "Indicates whether the generic packet filter
                        described by this entry is enabled or disabled."
              DEFVAL    { disabled }
              ::= { genericFilterEntry 3 }

          genericFilterForward OBJECT-TYPE
              SYNTAX    INTEGER {
                            forward(1),
                            drop(2)
                        }
              ACCESS    read-write
              STATUS    mandatory
              DESCRIPTION
                        "Indicates whether the device will forward or
                        drop a packet matching the parameters of this
                        generic packet filter."
              DEFVAL    { forward }
              ::= { genericFilterEntry 4 }

          genericFilterOffset OBJECT-TYPE
              SYNTAX    INTEGER (0..65535)
              ACCESS    read-write
              STATUS    mandatory
              DESCRIPTION
                        "Indicates the offset (in octets) from the start
                        of the packet to the data to which this filter
                        will be applied."
              DEFVAL    { 0 }
              ::= { genericFilterEntry 5 }

          genericFilterMask OBJECT-TYPE
              SYNTAX    OCTET STRING (SIZE(0..8))
              ACCESS    read-write
              STATUS    mandatory
              DESCRIPTION
                        "Indicates the mask that the device will
                        logically AND with the data in a packet being
                        passed through this filter before that data is
                        compared with the value of the corresponding
                        instance of genericFilterValue.

                        While the agent will accept a request to set an
                        instance of this object to a mask that is fewer
                        than eight octets long, when read an instance of
                        this object will always be exactly eight octets
                        long, the least-significant octets having been
                        zero-filled."
              DEFVAL    { ''H }
              ::= { genericFilterEntry 6 }

          genericFilterValue OBJECT-TYPE
              SYNTAX    OCTET STRING (SIZE(0..8))
              ACCESS    read-write
              STATUS    mandatory
              DESCRIPTION
                        "Indicates the value against which the device
                        will compare the value produced by the logical
                        AND of the data in a packet and the value of the
                        corresponding instance of genericFilterMask for
                        the packet to satisfy this filter.

                        While the agent will accept a request to set an
                        instance of this object to a value that is fewer
                        than eight octets long, when read, an instance
                        of this object will always be exactly eight
                        octets long, the least-significant octets having
                        been zero-filled."
              DEFVAL    { ''H }
              ::= { genericFilterEntry 7 }

          genericFilterComparison OBJECT-TYPE
              SYNTAX    INTEGER {
                            none(1),      -- no comparison
                            lt(2),        -- less than
                            le(3),        -- less than or equal
                            eq(4),        -- equal
                            ne(5),        -- not equal
                            gt(6),        -- greater than
                            ge(7)         -- greater than or equal
                        }
              ACCESS    read-write
              STATUS    mandatory
              DESCRIPTION
                        "Indicates the relational operator that the
                        device will use when comparing the value
                        produced by the logical AND of the data in a
                        packet and the value of the corresponding
                        instance of genericFilterMask to the value of
                        the corresponding instance of
                        genericFilterValue.

                        If the value of this object is 'none(1)', no
                        comparison is performed; the packet is forwarded
                        or dropped based solely on the value of
                        genericFilterForward."
              DEFVAL    { none }
              ::= { genericFilterEntry 8 }

          genericFilterChained OBJECT-TYPE
              SYNTAX    INTEGER {
                            chained(1),
                            notChained(2)
                        }
              ACCESS    read-write
              STATUS    mandatory
              DESCRIPTION
                        "Indicates whether or not the device will chain
                        this filter together with the next generic
                        filter in the associated filter set when
                        deciding whether or not to forward a packet."
              DEFVAL    { notChained }
              ::= { genericFilterEntry 9 }

          genericFilterStatus OBJECT-TYPE
              SYNTAX    INTEGER {
                            valid(1),
                            invalid(2)
                        }
              ACCESS    read-write
              STATUS    mandatory
              DESCRIPTION
                        "Indicates the status of this generic filter
                        entry.

                        Setting this object to the value 'invalid(2)'
                        has the effect of invalidating the corresponding
                        entry in the genericFilterTable.  That is, it
                        effectively disassociates the mapping identified
                        with said entry.  It is an implementation-
                        specific matter as to whether the agent removes
                        an invalidated entry from the table.
                        Accordingly, management stations must be
                        prepared to receive from agents tabular
                        information corresponding to entries not
                        currently in use.  Proper interpretation of such
                        entries requires examination of the relevant
                        genericFilterStatus object."
              DEFVAL    { valid }
              ::= { genericFilterEntry 10 }

          END
