MATIP-MIB DEFINITIONS ::= BEGIN

	IMPORTS
		OBJECT-TYPE							FROM RFC-1212
		Counter, enterprises, TimeTicks		FROM RFC1155-SMI
		TRAP-TYPE							FROM RFC-1215;


--	matipMIB MODULE-IDENTITY
--		LAST-UPDATED "9702260000Z"
--		ORGANIZATION "Northrop Grumman-Canada, Ltd."
--		CONTACT-INFO
--			"		Brian Richards, Fulko K. Hew
--
--			Postal:	Northrop Grumman-Canada, Ltd.
--					777 Walkers Line
--					Burlington, Ontario
--					Canada
--					L7N 2G1
--
--			Tel:	+1 905 333 6000
--			Fax:	+1 905 333 6050
--
--			E-mail: fulko@ngcan.com
--					brichards@ngcan.com"
--		DESCRIPTION
--			"The MIB module to describe MATIP sessions and users."

	ngcan				OBJECT IDENTIFIER ::= { enterprises 1978 }	-- Northrop Grumman-Canada, Ltd.
	tiger				OBJECT IDENTIFIER ::= { ngcan 2 }			-- Tiger (Network Access Device)

	matipMIB			OBJECT IDENTIFIER ::= { tiger 7 }

	matipUser			OBJECT IDENTIFIER ::= { matipMIB 2 }
	matipSession		OBJECT IDENTIFIER ::= { matipMIB 3 }
	matipTraps			OBJECT IDENTIFIER ::= { matipMIB 4 }

	matipUserTraps		OBJECT IDENTIFIER ::= { matipTraps 1 }
	matipSessionTraps	OBJECT IDENTIFIER ::= { matipTraps 2 }

	--
	-- NOTE:	Although this module maintains its own statistics and counters,
	--			Clearing them is controlled by ifClearStats and ifClearStatsTime
	--			on the interface associated with MATIP as defined in Tigers MIBII.
	--

	--
	-- Generic MATIP configuration information
	--

	--
	-- MATIP User Configuration Parameters
	--

	matipNumUsers OBJECT-TYPE
		SYNTAX		INTEGER (1..100)
		ACCESS		read-only
		STATUS		mandatory
		DESCRIPTION
			"Number of users in the table."
	::= { matipUser 1 }

	matipUserTable OBJECT-TYPE
		SYNTAX		SEQUENCE OF MatipUserEntry
		ACCESS		not-accessible
		STATUS		mandatory
		DESCRIPTION
			"A list of line table entries.
			The number of entries is given by the value of matipNumUsers."
		::= { matipUser 2 }

	matipUserEntry OBJECT-TYPE
		SYNTAX		MatipUserEntry
		ACCESS		not-accessible
		STATUS		mandatory
		DESCRIPTION
			"An entry containing information applicable to a particular MATIP user."
		INDEX		{ matipUserIndex }
		::= { matipUserTable 1 }

	MatipUserEntry ::= SEQUENCE {
		matipUserIndex					INTEGER,
		matipUserHLD					INTEGER,
		matipUserA1						INTEGER,
		matipUserA2						INTEGER,
		matipUserSessionRef				INTEGER,
		matipUserCoding					INTEGER,
		matipUserPresentationMode		INTEGER,
		matipUserQueueThresholdHi		INTEGER,
		matipUserQueueThresholdLow		INTEGER,

		--
		-- User Statistics and Status
		--

		matipUserStateTime				TimeTicks,
		matipUserStatus					INTEGER,

		matipUserMsgsIn					Counter,
		matipUserMsgsOut				Counter,
		matipUserCharIn					Counter,
		matipUserCharOut				Counter,
		matipUserDisconnects			Counter,

		--
		-- Trap Controls
		--
		matipUserTrapReason				INTEGER,
		matipUserStateChangeTrapEnable	INTEGER
		}

	matipUserIndex OBJECT-TYPE
		SYNTAX		INTEGER (1..100)
		ACCESS		read-write
		STATUS		mandatory
		DESCRIPTION
			"The user identifier."
		::= { matipUserEntry 1 }

	matipUserHLD OBJECT-TYPE
		SYNTAX		INTEGER (0..65535)
		ACCESS		read-write
		STATUS		mandatory
		DESCRIPTION
			"The HLD associated with this device."
		DEFVAL		{ 0 }
		::= { matipUserEntry 2 }

	matipUserA1 OBJECT-TYPE
		SYNTAX		INTEGER (0..255)
		ACCESS		read-write
		STATUS		mandatory
		DESCRIPTION
			"The A1 associated with this device."
		DEFVAL		{ 0 }
		::= { matipUserEntry 3 }

	matipUserA2 OBJECT-TYPE
		SYNTAX		INTEGER (0..255)
		ACCESS		read-write
		STATUS		mandatory
		DESCRIPTION
			"The A2 associated with this device."
		DEFVAL		{ 0 }
		::= { matipUserEntry 4 }

	matipUserSessionRef OBJECT-TYPE
		SYNTAX		INTEGER (0..100)
		ACCESS		read-write
		STATUS		mandatory
		DESCRIPTION
			"The MATIP session identifier (i.e. the interface index of the associated MATIP session).
			At configuration time, if the value is zero, then session has not been pre-allocated;
			otherwise, this value signifies the configured session to use."
		DEFVAL		{ 0 }
		::= { matipUserEntry 5 }

	matipUserCoding OBJECT-TYPE
		SYNTAX		INTEGER {
			paddedbaudot	(1),
			ipars			(2),
			ascii			(3),
			ebcdic			(4)
			}
		ACCESS		read-write
		STATUS		mandatory
		DESCRIPTION
			"Defines the coding or data that is associated with this entry:
				paddedbaudot:	5 bits
				ipars:			6 bits
				ascii:			7 bits
				ebcdic:			8 bits"
		::= { matipUserEntry 6 }

	matipUserPresentationMode OBJECT-TYPE
		SYNTAX		INTEGER {
			p1024b			(1),
			p1024c			(2),
			sna3270			(3)
			}
		ACCESS		read-write
		STATUS		mandatory
		DESCRIPTION
			"The type of presentation:
				p1024b
				p1024c
				sna3270		(not currently supported)"
		::= { matipUserEntry 7 }

	matipUserQueueThresholdHi OBJECT-TYPE
		SYNTAX		INTEGER (0..100)
		ACCESS		read-write
		STATUS		mandatory
		DESCRIPTION
			"Count of messages queued to the MATIP user before flow control
			is initiated by 'pushing back' on the MATIP session stream."
		DEFVAL		{ 64 }
		::= { matipUserEntry 8 }

	matipUserQueueThresholdLow OBJECT-TYPE
		SYNTAX		INTEGER (0..100)
		ACCESS		read-write
		STATUS		mandatory
		DESCRIPTION
			"Count of messages queued to the MATIP user before re-enabling on
			the MATIP session stream."
		DEFVAL		{ 8 }
		::= { matipUserEntry 9 }

	--
	-- Statistics and state information


	matipUserStateTime OBJECT-TYPE
		SYNTAX		TimeTicks
		ACCESS		read-only
		STATUS		mandatory
		DESCRIPTION
			"The amount of time (in hundredths of a second) since this
			user entered the current state."
		::= { matipUserEntry 10 }

	matipUserStatus OBJECT-TYPE
		SYNTAX		INTEGER {
			closed		(1),
			activated	(2),
			bound		(3),
			connected	(4)
			}
		ACCESS		read-only
		STATUS		mandatory
		DESCRIPTION
			"Connect State of the MATIP User"
		::= { matipUserEntry 11 }

	matipUserMsgsIn OBJECT-TYPE
		SYNTAX		Counter
		ACCESS		read-only
		STATUS		mandatory
		DESCRIPTION
			"The total number of messages from the Type A device."
		::= { matipUserEntry 12 }

	matipUserMsgsOut OBJECT-TYPE
		SYNTAX		Counter
		ACCESS		read-only
		STATUS		mandatory
		DESCRIPTION
			"The total number of messages sent to the Type A device."
		::= { matipUserEntry 13 }

	matipUserCharIn OBJECT-TYPE
		SYNTAX		Counter
		ACCESS		read-only
		STATUS		mandatory
		DESCRIPTION
			"The total number of characters from the Type A device."
		::= { matipUserEntry 14 }

	matipUserCharOut OBJECT-TYPE
		SYNTAX		Counter
		ACCESS		read-only
		STATUS		mandatory
		DESCRIPTION
			"The total number of characters sent to the Type A device."
		::= { matipUserEntry 15 }

	matipUserDisconnects OBJECT-TYPE
		SYNTAX		Counter
		ACCESS		read-only
		STATUS		mandatory
		DESCRIPTION
			"The total number of MATIP User disconnects."
		::= { matipUserEntry 16 }

	matipUserTrapReason OBJECT-TYPE
		SYNTAX		INTEGER {
			none	(1),
			up		(2),
			down	(3)
			}
		ACCESS		read-only
		STATUS		mandatory
		DESCRIPTION
			"The reason that the matipUserStateChange trap was generated:
				up		- when the MATIP User enters 'connected' state.
				down	- when the MATIP User enters 'disconnected' state."
		::= { matipUserEntry 17 }

	--
	-- Trap Controls
	--

	matipUserStateChangeTrapEnable OBJECT-TYPE
		SYNTAX		INTEGER {
			disabled	(1),
			enabled		(2),
			partial		(3)
			}
		ACCESS		read-write
		STATUS		mandatory
		DESCRIPTION
			"Indicates whether matipUserStateChange traps should be generated for this interface.
				disabled	- do not generate a trap
				enabled		- generate trap when a user enters either the connected or disconnected state.
				partial		- same as 'enabled' except only for those MATIP sessions initiated by this end."
		DEFVAL		{ enabled }
		::= { matipUserEntry 18 }

	--
	-- Traps
	--
	-- This section defines the well-known notifications sent by MATIP Line agents.
	-- These are sent when the corresponding threshold is exceeded.

	matipUserStateChange TRAP-TYPE
		ENTERPRISE		matipUserTraps
		VARIABLES		{ matipUserIndex, matipUserTrapReason }
		DESCRIPTION
			"This trap signifies that one of the users has changed state to/from
			connected/disconnected as given by matipUserTrapReason."
	::= 1


	--
	-- MATIP Session
	--

	matipSessionTable OBJECT-TYPE
		SYNTAX		SEQUENCE OF MatipSessionEntry
		ACCESS		not-accessible
		STATUS		mandatory
		DESCRIPTION
			"A list of MATIP sessions."
		::= { matipSession 3 }

	matipSessionEntry OBJECT-TYPE
		SYNTAX		MatipSessionEntry
		ACCESS		not-accessible
		STATUS		mandatory
		DESCRIPTION
			"An entry containing information applicable to a particular MATIP session."
		INDEX		{ matipSessionIndex }
		::= { matipSessionTable 1 }

	MatipSessionEntry ::= SEQUENCE {
		matipSessionIndex					INTEGER,
		matipSessionClientServer			INTEGER,
		matipSessionMuxMode					INTEGER,
		matipSessionPresentationMode		INTEGER,
		matipSessionCoding					INTEGER,
		matipSessionRestartTimer			INTEGER,
		matipSessionDialOnDemand			INTEGER,
		matipSessionActivityTimer			INTEGER,
		matipSessionQueueThresholdHi		INTEGER,
		matipSessionQueueThresholdLow		INTEGER,

		-- MATIP Session Status/Statistics

		matipSessionConnectTime				TimeTicks,
		matipSessionStatus					INTEGER,

		matipSessionDisconnects				Counter,
		matipSessionSOSent					Counter,
		matipSessionSOReceived				Counter,
		matipSessionOCSent					Counter,
		matipSessionOCReceived				Counter,
		matipSessionSCSent					Counter,
		matipSessionSCReceived				Counter,
		matipSessionDataSent				Counter,
		matipSessionDataReceived			Counter,

		matipSessionStateChangeTrapEnable	INTEGER,
		matipSessionTrapReason				INTEGER
		}

	matipSessionIndex OBJECT-TYPE
		SYNTAX		INTEGER (1..100)
		ACCESS		read-write
		STATUS		mandatory
		DESCRIPTION
			"The identifier that can be used to locate this session."
		::= { matipSessionEntry 1 }

	matipSessionClientServer OBJECT-TYPE
		SYNTAX		INTEGER {
			client			(1),
			server			(2),
			both			(3)
		}
		ACCESS		read-write
		STATUS		mandatory
		DESCRIPTION
			"Flag defining the Client/Server nature of the product.
			'both' is not supported by TIGER because 'client' serves
			as both client and server."
		DEFVAL		{ client }
		::= { matipSessionEntry 2 }

	matipSessionMuxMode OBJECT-TYPE
		SYNTAX		INTEGER {
			hlda1a2			(1),
			a1a2			(2),
			single			(3)
		}
		ACCESS		read-write
		STATUS		mandatory
		DESCRIPTION
			"Multiplexor Mode for this session defined as follows:

			HLD/A1/A2: 	4 Byte ASCU definition
			A1/A2:		2 Byte ASCU definition
			Single:		No multiplexing."
		DEFVAL		{ hlda1a2 }
		::= { matipSessionEntry 3 }

	matipSessionPresentationMode OBJECT-TYPE
		SYNTAX		INTEGER {
			p1024b			(1),
			p1024c			(2),
			sna3270			(3)
			}
		ACCESS		read-write
		STATUS		mandatory
		DESCRIPTION
			"The type of presentation:
				p1024b
				p1024c
				sna3270		(not currently supported)"
		::= { matipSessionEntry 4 }

	matipSessionCoding OBJECT-TYPE
		SYNTAX		INTEGER {
			paddedbaudot	(1),
			ipars			(2),
			ascii			(3),
			ebcdic			(4)
			}
		ACCESS		read-write
		STATUS		mandatory
		DESCRIPTION
			"Defines the coding or data that is associated with this entry:
				paddedbaudot:		5 bits,
				ipars:				6 bits,
				ascii:				7 bits,
				ebcdic:				8 bits"
		::= { matipSessionEntry 5 }

	matipSessionRestartTimer OBJECT-TYPE
		SYNTAX		INTEGER (0..100)
		ACCESS		read-write
		STATUS		mandatory
		DESCRIPTION
			"The number of seconds that will be waited before the MATIP session will be restarted.
			A value of zero indicates that timing will not occur.
			The session restart timer is only used when matipSessionClientServer is set to 'client'
			and matipSessionDialOnDemand is 'disabled'."
		DEFVAL		{ 5 }
		::= { matipSessionEntry 6 }

	matipSessionDialOnDemand OBJECT-TYPE
		SYNTAX		INTEGER {
			disabled	(1),
			enabled		(2)
			}
		ACCESS		read-write
		STATUS		mandatory
		DESCRIPTION
			"When dial on demand is enabled, the TCP session will
			only be started upon received data from the MATIP user."
		DEFVAL		{ disabled }
		::= { matipSessionEntry 7 }

	matipSessionActivityTimer	OBJECT-TYPE
		SYNTAX		INTEGER (1..600)
		ACCESS		read-write
		STATUS		mandatory
		DESCRIPTION
			"The number of seconds of inactivity before the TCP session will be disconnected."
		DEFVAL	{ 300 }
		::= { matipSessionEntry 8 }

	matipSessionQueueThresholdHi	OBJECT-TYPE
		SYNTAX		INTEGER (1..100)
		ACCESS		read-write
		STATUS		mandatory
		DESCRIPTION
			"The queueing limit for traffic being sent to the AUTIF module.
			 When this is reached, the software will push back against the MATIP users."
		DEFVAL	{ 64 }
		::= { matipSessionEntry 9 }

	matipSessionQueueThresholdLow	OBJECT-TYPE
		SYNTAX		INTEGER (1..100)
		ACCESS		read-write
		STATUS		mandatory
		DESCRIPTION
			"The level at which the user queues will be re-enabled."
		DEFVAL	{ 8 }
		::= { matipSessionEntry 10 }

	--
	-- MATIP Session Statistics
	--

	matipSessionConnectTime OBJECT-TYPE
		SYNTAX		TimeTicks
		ACCESS		read-only
		STATUS		mandatory
		DESCRIPTION
			"The amount of time (in hundredths of a second) since this transport
			connection last entered the 'connected' state.
			A value of zero means this transport connection has never been established."
		::= { matipSessionEntry 11 }

	matipSessionStatus OBJECT-TYPE
		SYNTAX		INTEGER {
			sessionDown			(1),
			sessionActivated	(2),
			sessionConnected	(3)
			}
		ACCESS		read-only
		STATUS		mandatory
		DESCRIPTION
			"The state of this transport connection:

			'sessionDown'		- when this MATIP session is created by the configuration,
								  or when the TCP connection fails.
			'sessionActivated'	- when the MATIP state machine has sent an SO command
								  and is waiting for an OC response.
			'sessionConnected'	- when the MATIP session layer can begin Data Transfer."
		::= { matipSessionEntry 12 }

	matipSessionDisconnects OBJECT-TYPE
		SYNTAX		Counter
		ACCESS		read-only
		STATUS		mandatory
		DESCRIPTION
			"The Total number of MATIP session Disconnects."
		::= { matipSessionEntry 13 }

	matipSessionSOSent OBJECT-TYPE
		SYNTAX		Counter
		ACCESS		read-only
		STATUS		mandatory
		DESCRIPTION
			"The count of SO Commands sent."
		::= { matipSessionEntry 14 }

	matipSessionSOReceived OBJECT-TYPE
		SYNTAX		Counter
		ACCESS		read-only
		STATUS		mandatory
		DESCRIPTION
			"The count of SO Commands received."
		::= { matipSessionEntry 15 }

	matipSessionOCSent	 OBJECT-TYPE
		SYNTAX		Counter
		ACCESS		read-only
		STATUS		mandatory
		DESCRIPTION
			"The count of OC Commands sent."
		::= { matipSessionEntry 16 }

	matipSessionOCReceived	 OBJECT-TYPE
		SYNTAX		Counter
		ACCESS		read-only
		STATUS		mandatory
		DESCRIPTION
			"The count of OC Commands received."
		::= { matipSessionEntry 17 }

	matipSessionSCSent	 OBJECT-TYPE
		SYNTAX		Counter
		ACCESS		read-only
		STATUS		mandatory
		DESCRIPTION
			"The count of SC Commands sent."
		::= { matipSessionEntry 18 }

	matipSessionSCReceived	 OBJECT-TYPE
		SYNTAX		Counter
		ACCESS		read-only
		STATUS		mandatory
		DESCRIPTION
			"The count of SC Commands received."
		::= { matipSessionEntry 19 }

	matipSessionDataSent	 OBJECT-TYPE
		SYNTAX		Counter
		ACCESS		read-only
		STATUS		mandatory
		DESCRIPTION
			"The count of data packets sent."
		::= { matipSessionEntry 20 }

	matipSessionDataReceived	 OBJECT-TYPE
		SYNTAX		Counter
		ACCESS		read-only
		STATUS		mandatory
		DESCRIPTION
			"The count of data packets received."
		::= { matipSessionEntry 21 }

	matipSessionStateChangeTrapEnable OBJECT-TYPE
		SYNTAX		INTEGER {
			disabled	(1),
			enabled		(2),
			partial		(3)
			}
		ACCESS		read-write
		STATUS		mandatory
		DESCRIPTION
			"Indicates whether matipSessionStateChange traps should be generated for this interface.
				disabled	- do not generate a trap
				enabled		- generate trap when a session enters either the connected or disconnected state.
							  or when any 'partner reject' occurs.
				partial		- same as 'enabled' except only when the session is closed with busy."
		DEFVAL		{ enabled }
		::= { matipSessionEntry 22 }

	matipSessionTrapReason OBJECT-TYPE
		SYNTAX		INTEGER {
			none	(1),
			up		(2),
			down	(3)
			}
		ACCESS		read-only
		STATUS		mandatory
		DESCRIPTION
			"The reason that the matipSessionStateChange trap was generated:
				up		- when the session enters 'connected' state.
				down	- when the session enters 'disconnected' state."
		::= { matipSessionEntry 23 }

	--
	-- Traps
	--
	-- This section defines the well-known notifications sent by MATIP session agent.

	matipSessionStateChange TRAP-TYPE
		ENTERPRISE		matipSessionTraps
		VARIABLES		{ matipSessionIndex, matipSessionTrapReason }
		DESCRIPTION
			"This trap signifies that one of the sessions has changed state to/from
			connected/disconnected as given by matipSessionTrapReason."
	::= 1

	END
