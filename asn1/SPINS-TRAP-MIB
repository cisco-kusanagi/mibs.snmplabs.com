SPINS-TRAP-MIB DEFINITIONS ::= BEGIN

IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    TruthValue, DisplayString, TestAndIncr, TimeStamp, RowStatus
        FROM SNMPv2-TC;

        lucent              OBJECT IDENTIFIER  ::=  {  enterprises  1751  }
        products            OBJECT IDENTIFIER  ::=  {  lucent  1  }
        softSwitch          OBJECT IDENTIFIER  ::=  {  products 1198  }
	    spinsDeviceServer   OBJECT IDENTIFIER  ::=  {  softSwitch 8 }

spinsTraps  MODULE-IDENTITY    
        LAST-UPDATED "240701"
        ORGANIZATION "Lucent Technologies"    
        CONTACT-INFO 
                ""    
        DESCRIPTION
                "The MIB module for entities implementing the xxxx
                protocol."  

::=  {  spinsDeviceServer 0 }

    -- The traps group. Listed below are the traps currently supported by SPINS



     spinsSmbiSocketConnError NOTIFICATION-TYPE
             STATUS current
             DESCRIPTION
                     "Indicates that the socket connection between
                      SPINS and SMBI cannot be made.
                             VARIABLE DEFINITIONS: NONE
                     Severity: CRITICAL"
                      ::= { spinsTraps  0 }

     spinsSmbiSocketConnOpen NOTIFICATION-TYPE
             STATUS current
             DESCRIPTION
                     "Indicates that the socket connection between
                      SPINS and SMBI is successful.
                             VARIABLE DEFINITIONS: NONE
                     Severity: INFO"
                      ::= { spinsTraps  1 }

     spinsSbiSocketConnLost NOTIFICATION-TYPE
             STATUS current
             DESCRIPTION
                     "Indicates that the socket connection between
                      SPINS and SMBI is closed.
                             VARIABLE DEFINITIONS: NONE
                     Severity: CRITICAL"
                      ::= { spinsTraps  2 }

     spinsSwitchRegnError NOTIFICATION-TYPE
                     STATUS current
                     DESCRIPTION
                     "Registration of SPINS with the switch for Tollfree
                     and LNP services has failed.
                     VARIABLE DEFINITIONS: NONE
                     Severity: CRITICAL"
                     ::= { spinsTraps  3 }

     spinsSwitchRegnSucc NOTIFICATION-TYPE
                     STATUS current
                     DESCRIPTION
                     "Registration of SPINS with the switch for Tollfree
                     and LNP services is successful.
                     VARIABLE DEFINITIONS: NONE
                     Severity: INFO"
                     ::= { spinsTraps  4 }

     spinsAddLLCNodeError NOTIFICATION-TYPE
                     STATUS current
                     DESCRIPTION
                             "The second step of registration with the switch
                              (add_LLC_Node) has failed.
                             VARIABLE DEFINITIONS: NONE
                     Severity: CRITICAL"
            ::= { spinsTraps  5 }

     spinsAddLLCNodeSucc NOTIFICATION-TYPE
                     STATUS current
                     DESCRIPTION
                             "The second step of registration with the switch
                              (add_LLC_Node) is successful.
                             VARIABLE DEFINITIONS: NONE
                     Severity: INFO"
            ::= { spinsTraps  6 }

END
