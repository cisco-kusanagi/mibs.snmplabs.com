Wellfleet-OCX-MIB DEFINITIONS ::= BEGIN

-- Created 1998


    IMPORTS

      TimeTicks
        FROM RFC1155-SMI
      OBJECT-TYPE
        FROM RFC-1212
      wfSonetGroup
        FROM Wellfleet-COMMON-MIB;

    wfOcxConfigTable OBJECT-TYPE
        SYNTAX	SEQUENCE OF WfOcxConfigEntry
        ACCESS	not-accessible
        STATUS	mandatory
        DESCRIPTION
                "Ocx Configuration Table"
        ::= { wfSonetGroup 21 }

    wfOcxConfigEntry OBJECT-TYPE
        SYNTAX	WfOcxConfigEntry
        ACCESS	not-accessible
        STATUS	mandatory
        DESCRIPTION
                "An entry in the Ocx Configuration table"
        INDEX	{ wfOcxConfigIndex }
        ::= { wfOcxConfigTable 1 }

    WfOcxConfigEntry ::= SEQUENCE {
    	    wfOcxConfigDelete
    		INTEGER,
    	    wfOcxConfigDisable
    		INTEGER,
    	    wfOcxConfigIndex
    		INTEGER,
    	    wfOcxConfigIfIndex
    		INTEGER,
	    wfOcxConfigState
		INTEGER,
	    wfOcxConfigLineStatus
		INTEGER,
	    wfOcxConfigLastChange
		TimeTicks,
	    wfOcxConfigConnType
		INTEGER,
    	    wfOcxConfigType
    		INTEGER,
    	    wfOcxConfigLineCoding
    		INTEGER,
    	    wfOcxConfigLineType
    		INTEGER,
	    wfOcxConfigLoopbackConfig
    		INTEGER,
	    wfOcxConfigManagerMethod
    		INTEGER,
	    wfOcxConfigApsEnable
    		INTEGER,
	    wfOcxConfigScrambling
		INTEGER,
	    wfOcxConfigClkSource
		INTEGER
        }

    wfOcxConfigDelete OBJECT-TYPE
        SYNTAX  INTEGER {
                    created(1),
                    deleted(2)
                }
        ACCESS  read-write
        STATUS  mandatory
        DESCRIPTION
                "Create/Delete parameter"
        DEFVAL  { created }
        ::= { wfOcxConfigEntry 1 }

    wfOcxConfigDisable OBJECT-TYPE
        SYNTAX  INTEGER {
                    enabled(1),
                    disabled(2)
                }
        ACCESS  read-write
        STATUS  mandatory
        DESCRIPTION
                "Create/Delete parameter"
        DEFVAL  { enabled }
        ::= { wfOcxConfigEntry 2 }

    wfOcxConfigIndex OBJECT-TYPE
        SYNTAX	INTEGER
        ACCESS	read-only
        STATUS	mandatory
        DESCRIPTION
                "Index for this physical Sonet interface."
        ::= { wfOcxConfigEntry 3 }

    wfOcxConfigIfIndex OBJECT-TYPE
        SYNTAX  INTEGER
        ACCESS  read-only
        STATUS  mandatory
        DESCRIPTION
                "this is value of ifIndex from the Interfaces table of
                MIB II (RFC 1213)."
        ::= { wfOcxConfigEntry 4 }

    wfOcxConfigState OBJECT-TYPE
        SYNTAX  INTEGER {
                    up(1),
                    down(2),
                    los(3),
                    lof(4),
                    ais(5),
                    rdi(6),
                    loopback(7),
                    notpresent(20)
                }
        ACCESS  read-only
        STATUS  mandatory
        DESCRIPTION
                "State of the OCX Port."
        DEFVAL  { notpresent }
        ::= { wfOcxConfigEntry 5 }

    wfOcxConfigLineStatus OBJECT-TYPE
        SYNTAX  INTEGER {
                    noalarm(1),
                    los(2),
                    lof(4),
                    ais(8),
                    rdi(16),
                    loopback(128),
                    otherfailure(512)
                }
        ACCESS  read-only
        STATUS  mandatory
        DESCRIPTION
                "the status of the OCX"
        DEFVAL  { noalarm }
        ::= { wfOcxConfigEntry 6 }

    wfOcxConfigLastChange OBJECT-TYPE
        SYNTAX  TimeTicks
        ACCESS  read-only
        STATUS  mandatory
        DESCRIPTION
                "The value of sysUpTime at the time the interface entered
                its current operational state."
        ::= { wfOcxConfigEntry 7 }

    wfOcxConfigConnType OBJECT-TYPE
        SYNTAX	INTEGER {
    		    oc3(1),
    		    oc12(2),
    		    oc48(3)
    		}
        ACCESS	read-write
        STATUS	mandatory
        DESCRIPTION
                "This variable describes the Connector Type for this interface.
		 This Mib is used for various types, OC3, OC12, etc..."
        ::= { wfOcxConfigEntry 8 }

    wfOcxConfigType OBJECT-TYPE
	SYNTAX  INTEGER {
		    sonet(1),
		    sdh(2)
    		}
        ACCESS	read-only
        STATUS	mandatory
        DESCRIPTION
                "This variable identifies whether a SONET or a SDH signal is used
                across this interface."
        ::= { wfOcxConfigEntry 9 }

    wfOcxConfigLineCoding OBJECT-TYPE
        SYNTAX	INTEGER {
    		    other(1),
    		    b3zs(2),
    		    cmi(3),
    		    nrz(4),
    		    rz(5)
    		}
        ACCESS	read-write
        STATUS	mandatory
        DESCRIPTION
                "This variable describes the line coding for this interface."
        DEFVAL	{ nrz }
        ::= { wfOcxConfigEntry 10 }

    wfOcxConfigLineType OBJECT-TYPE
        SYNTAX	INTEGER {
    		    other(1),
    		    shortsinglemode(2),
    		    longsinglemode(3),
    		    multimode(4),
    		    coax(5),
    		    utp(6)
    		}
        ACCESS	read-write
        STATUS	mandatory
        DESCRIPTION
                "This variable describes the line type for this interface."
        DEFVAL	{ shortsinglemode }
        ::= { wfOcxConfigEntry 11 }

    wfOcxConfigLoopbackConfig OBJECT-TYPE
        SYNTAX  INTEGER {
                    noloop(1),
                    selfloop(2),
                    lineloop(3)
                }
        ACCESS  read-write
        STATUS  mandatory
        DESCRIPTION
                "the loopback configuration of the OCX interface"
        DEFVAL { noloop }
        ::= { wfOcxConfigEntry 12 }

    wfOcxConfigManagerMethod OBJECT-TYPE
        SYNTAX  INTEGER {
                    frac(1),
                    clear(2)
        }
        ACCESS  read-write
        STATUS  mandatory
        DESCRIPTION
                "This attribute has no affect on the Hardware configuration.
                This attribute is purely for any Network Management Tool
                to determine whether it configured the OCX as Fractional
                or Clear."
        DEFVAL  { frac }
        ::= { wfOcxConfigEntry 13 }

    wfOcxConfigApsEnable OBJECT-TYPE
        SYNTAX  INTEGER {
                    enabled(1),
                    disabled(2)
        }
        ACCESS  read-write
        STATUS  mandatory
        DESCRIPTION
                "This attribute Enables or Disables the APS failover."
        DEFVAL  { disabled }
        ::= { wfOcxConfigEntry 14 }

    wfOcxConfigScrambling OBJECT-TYPE
	SYNTAX  INTEGER {
		    on(1),
		    off(2)
	}
	ACCESS  read-write
	STATUS  mandatory
	DESCRIPTION
		"This attribute turns scrambling on or off."
	DEFVAL  { on }
	::= { wfOcxConfigEntry 15 }

    wfOcxConfigClkSource OBJECT-TYPE
	SYNTAX  INTEGER {
		    intrn(1),
		    extrn(2)
	}
	ACCESS  read-write
	STATUS  mandatory
	DESCRIPTION
		"The source of the physical interface clocking signal, either
		internal or external."
	DEFVAL  { intrn }
	::= { wfOcxConfigEntry 16 }

    END  -- Wellfleet-OCX-MIB
